# Json2ReqIF Transformation

# Specification: DIAG_Drive_Recorder
- JDA Snapshot Date: 2025-10-31 08:01:10

## TFDCX32348-57058: DIAG_Drive_Recorder (Heading)

## TFDCX32348-7568: History (Heading)

### TFDCX32348-10552: History (Information)
| Version | Date | Author | Description of change | SRD Baseline |
| --- | --- | --- | --- | --- |
| 0 | 11/10/2022 | Tejaswini Baviskar | New create 1681573: [SYS][38xD][DIAG] Drive Recorder |  |
| 1 | 20/10/2022 | Tejaswini Baviskar | Peer Review done |  |
| 3 | 11/11/2022 | Tejaswini Baviskar | Walkthrough Done | BL_20221114_01 |
| 4 | 07/12/2022 | Tejaswini Baviskar | Updated RNW_COND signal Processing 1851335: [SYS][38xD][DIAG] Drive Recorder_RNW_COND Update | BL_20221213_01 |
| 5 | 12/01/2023 | Tejaswini Baviskar | Updated 2779281 and 2779282 processing. Impediment 1878191 |  |
| 6 | 15/06/2023 | Tejaswini Baviskar | 2053714: [SYS][38xD][DEFECT][APP] Driver Recoder FL_Comp Signal Update Updated Processing for FL_Comp Signal. | BL_20230616_01 |
| 7 | 12/09/2023 | TejaswiniBaviskar | [SYS][38xD][DEFECT][APP] ACTV_TST update in Drive Recorder SRD(T38XD29284-23091) Clarified ACTV_TST output condition. | BL_20231102_01 |
| 8 | 20/11/2024 | Takuya Tamura | [SYS-Story] :TFDCX32348-34135: [SYS][12.3FDC][APP][Trip Computer] Drive recorder ・Added Refuel_cause_comp_data and changed the logic of RNW_COND. ・Changed the range of Disp_Data_H, Comp_Data_C, Comp_Data_Clid. ・Made a new logic table of D_N_INF. ・Changed Rheostat_Status to WheelVolRatioMon. ・Deleted the cases where the ILLDuty are Unknown or Undefined. ・Added UP & DOWN of Rheostat and ODO SW. ・Changed the logic table of SW_INF. ・Just Corrected errors(12401, 12468) | BL_20241203_01 |
| 9 | 29/08/2025 | Tejaswini Baviskar | Added SP1_in signal instead of CAN Signal -SP1 TFDCX32348-106946: [SYS][12.3FDC][APP][IMP][Gauges] Update Speedometer interface for DID 2A01 | BL_20250919_01 |

## TFDCX32348-7570: Reference Documents (Heading)

### TFDCX32348-10557: # (Information)
| # | Reference document No. |
| --- | --- |
| 1 | MET-M_DVRD-CSTD-1-00-A-C0.doc |
| 2 | MET-M_DMRNGE-CSTD-3-02-A-C4.docs |
| 3 | MET-M_DMAFFC-CSTD-1-02-A-C0.doc |

## TFDCX32348-7572: Overview (Heading)

### TFDCX32348-10559: This module transmits and store the s... (Information)
This module transmits and store the signal data for the failure analysis of the meter fuel system.
It gathers the signals information related to Fuel and not related to Fuel.

## TFDCX32348-57064: Input Requirements (Heading)

### TFDCX32348-57164: Input Requirements - Transmission signals of FUEL system (Heading)

#### TFDCX32348-17488: InternalSignal - Fuel_ST (System Interface)

#### TFDCX32348-58396: InternalSignal - Refuel_cause_comp_data (System Interface)
InternalSignal - Refuel_cause_comp_data
Range : 0[None], 1[Comp_Data_Clid], 2[Comp_Data_C]

#### TFDCX32348-17471: InternalSignal - VehicleStopFlag Me... (System Interface)
InternalSignal - VehicleStopFlag
Meaning: This parameter indicates the status whether vehicle is stopped.
Range: OFF, ON
Note: ON means vehicle is stopped.

#### TFDCX32348-17472: InternalSignal - Refuel_Judge (On/Off) (System Interface)

#### TFDCX32348-17474: InternalSignal - IgnMode (System Interface)

#### TFDCX32348-17478: CANSignal - B_ST (1: ST=ON, 0: ST=OFF... (System Interface)
CANSignal - B_ST (1: ST=ON, 0: ST=OFF, Message Label: ENG1G92)

#### TFDCX32348-17476: InternalSignal - Fuel_Enpty_Warn (On/... (System Interface)
InternalSignal - Fuel_Enpty_Warn (On/Off)

#### TFDCX32348-17484: InternalSignal - Disp_Data_H (System Interface)
InternalSignal - Disp_Data_H
Range:
0.00 to 60 700.00

#### TFDCX32348-17482: InternalSignal - Comp_Data_C (System Interface)
InternalSignal - Comp_Data_C
Range:
0.00 to 60 700.00

#### TFDCX32348-17480: InternalSignal - Comp_Data_Clid (System Interface)
InternalSignal - Comp_Data_Clid
Range:
0.00 to 60 700.00

### TFDCX32348-57165: Input Requirements - Transmission signals other than FUEL system (Heading)

#### TFDCX32348-12426: InternalSignal - IlumDayNightStatus ... (System Interface)
InternalSignal - IlumDayNightStatus
Meaning: This parameter indicates the illumination luminance status.
Range: $0 (UNKNOWN), $1 (DAY), $2 (NIGHT)
- Key Requirement: False

#### TFDCX32348-58997: InternalSignal - AppMode (System Interface)

#### TFDCX32348-58998: CANSignal - ADIM (Message Label : BDB1S01) (System Interface)

#### TFDCX32348-12428: Internal Signal - WheelVolRatioMon (System Interface)
Internal Signal - WheelVolRatioMon
Description : Wheel volume input ratio value. (For SID$22 DID$1024 output)
Type : UINT8
Range : 0x00 (0%) to 0xFE (100%), 0xFF (UNDECIDED)
InternalSignal - Rheostat_Status

#### TFDCX32348-12435: Internal Signal - ILLDuty (System Interface)
Internal Signal - ILLDuty
Meaning: This parameter outputs the backlight duty ratio of TFT.
Type: UINT8
Resolution: 1%
Range: 0 to 100%

#### TFDCX32348-12437: InternalSignal - TargetSW (System Interface)

#### TFDCX32348-12439: Internal Signal - RHEO_SW_Status (System Interface)

#### TFDCX32348-58251: Internal Signal - RHUP_Dbc (System Interface)
Internal Signal - RHUP_Dbc
Description : Rheostat UP switch debounce status.
Type : BOOL
Range : OFF, ON

#### TFDCX32348-58252: Internal Signal - RHDW_Dbc (System Interface)
Internal Signal - RHDW_Dbc
Description : Rheostat DOWN switch debounce status.
Type : BOOL
Range : OFF, ON

#### TFDCX32348-58982: Internal Signal - OdoSw_Dbc (System Interface)
Internal Signal - OdoSw_Dbc
Meaning: This parameter provides the debounce status of ODO-SW.
Type: BOOLEAN
Range: OFF, ON

#### TFDCX32348-12442: HW A/D - IGN_AD (System Interface)
HW A/D - IGN_AD
Resolution -12 bits

#### TFDCX32348-12444: CANSignal - SP1P (System Interface)
CANSignal - SP1P (Message Label: VSC1G13)

#### TFDCX32348-12447: CAN Signal - B_FC (System Interface)
CANSignal - B_FC (16bit, Message Label: ENG1S28)

#### TFDCX32348-12430: InternalSignal - KAM_Range_Cg (learni... (System Interface)
InternalSignal - KAM_Range_Cg (learning fuel consumption)

#### TFDCX32348-17469: CANSignal – SP1 (16bit, 0 to 327.67km... (System Interface)
CANSignal – SP1 (16bit, 0 to 327.67km/h, Message Label: VSC1G13)

#### TFDCX32348-12433: InternalSignal - Range_Fuel_Economy (... (System Interface)
InternalSignal - Range_Fuel_Economy (refueling interval fuel consumption)

#### TFDCX32348-107224: InternalSignal - SP1_in (System Interface)
- System Requirement State: Draft
- Primary Discipline: TBD
- ASIL Rating: TBD

## TFDCX32348-57065: Output Requirements (Heading)

### TFDCX32348-57160: Output Requirements - Transmission signals of FUEL system (Heading)

#### TFDCX32348-17489: CANSignal - DATA_NUM (System Interface)
CANSignal - DATA_NUM (Frame data number, Message Label: MET1D50)

#### TFDCX32348-17491: CANSignal - RNW_COND (System Interface)
CANSignal - RNW_COND (Display update condition , Message Label: MET1D50)
- Key Requirement: False

#### TFDCX32348-17493: CANSignal - STOP_JG (System Interface)
CANSignal - STOP_JG (Stop judgment signal , Message Label: MET1D50)
- Key Requirement: False

#### TFDCX32348-17495: CANSignal - OIL_SUPJ (System Interface)
CANSignal - OIL_SUPJ (Lubrication judgment signal , Message Label: MET1D50)
- Key Requirement: False

#### TFDCX32348-17497: CANSignal - ACTV_TST (System Interface)
CANSignal - ACTV_TST (Active test signal , Message Label: MET1D50)
- Key Requirement: False

#### TFDCX32348-17098: CANSignal - IGON_SIG (System Interface)
CANSignal - IGON_SIG (IG-ON Source , Message Label: MET1D50)
- Key Requirement: False

#### TFDCX32348-17100: CANSignal - STON_SIG (System Interface)
CANSignal - STON_SIG (ST-ON Source , Message Label: MET1D50)
- Key Requirement: False

#### TFDCX32348-17102: CANSignal - MET_REST (System Interface)
CANSignal - MET_REST (Meter reset judgment signal , Message Label: MET1D50)
- Key Requirement: False

#### TFDCX32348-17105: CANSignal - FLWNG_ON (System Interface)
CANSignal - FLWNG_ON (Remaining WNG ON status , Message Label: MET1D50)
- Key Requirement: False

#### TFDCX32348-17106: CANSignal - FL_DISP (System Interface)
CANSignal - FL_DISP (Fuel display value signal , Message Label: MET1D50)
LSB = 0.5L
- Key Requirement: False

#### TFDCX32348-17108: CANSignal - FL_COMP (System Interface)
CANSignal - FL_COMP (Comparison data during lubrication , Message Label: MET1D50)
LSB = 0.5L
- Key Requirement: False

### TFDCX32348-57163: Output Requirements - Transmission signals other than FUEL system (Heading)

#### TFDCX32348-17112: CANSignal - DATA_NM2 (System Interface)
CANSignal - DATA_NM2 (Frame data number 2 , Message Label: MET1D51)
- Key Requirement: False

#### TFDCX32348-17114: CANSignal - D_N_INF (System Interface)
CANSignal - D_N_INF (Daytime and nighttime judgement , Message Label: MET1D51)
- Key Requirement: False

#### TFDCX32348-17116: CANSignal - RHEO_IN (System Interface)
CANSignal - RHEO_IN (Rheostat input value , Message Label: MET1D51)
LSB = 1%
- Key Requirement: False

#### TFDCX32348-17118: CANSignal - ILL_OUT (System Interface)
CANSignal - ILL_OUT (Meter Luminance Output Value , Message Label: MET1D51)
LSB = 1%
- Key Requirement: False

#### TFDCX32348-17121: CANSignal - SW_INF (System Interface)
CANSignal - SW_INF (SW operation information , Message Label: MET1D51)
- Key Requirement: False

#### TFDCX32348-17123: CANSignal - IG_VOL (System Interface)
CANSignal - IG_VOL (IGN Voltage , Message Label: MET1D51)
LSB = 0.1V
Record the data of IG-ON voltage [V]
- Key Requirement: False

#### TFDCX32348-17125: CANSignal - DISP_TMP (System Interface)
CANSignal - DISP_TMP (Indicator Ambient Temperature , Message Label: MET1D51)
LSB = 0.5℃
- Key Requirement: False

#### TFDCX32348-17127: CANSignal - LN_FC (System Interface)
CANSignal - LN_FC (Learning fuel efficiency , Message Label: MET1D51)
LSB = 0.2km/L
- Key Requirement: False

#### TFDCX32348-17129: CANSignal - RF_FC (System Interface)
CANSignal - RF_FC (Fuel efficiency between refueling , Message Label: MET1D51)
LSB = 0.2km/L
- Key Requirement: False

## TFDCX32348-12452: Function Entry (Heading)

### TFDCX32348-17131 (System Interface)
Function Entry - fn_drvrec_left_sw_short_press()
Description:This function is called when SW ON to OFF is detected before long press is determined on LEFT SW.

### TFDCX32348-17133 (System Interface)
Function Entry - fn_drvrec_right_sw_short_press()
Description: This function is called when SW ON to OFF is detected before long press is determined on RIGHT SW.

### TFDCX32348-17135 (System Interface)
Function Entry - fn_drvrec_up_sw_short_press()
Description: This function is called when SW ON to OFF is detected before long press is determined on UP SW.

### TFDCX32348-17137 (System Interface)
Function Entry - fn_drvrec_down_sw_short_press()
Description: This function is called when SW ON to OFF is detected before long press is determined on DOWN SW.

### TFDCX32348-17139 (System Interface)
Function Entry - fn_drvrec_left_sw_long_press()
Description: This function is called when SW long press is determined on LEFT SW.

### TFDCX32348-17141 (System Interface)
Function Entry - fn_drvrec_right_sw_long_press()
Description: This function is called when SW long press is determined on RIGHT SW.

### TFDCX32348-17143 (System Interface)
Function Entry - fn_drvrec_up_sw_long_press()
Description: This function is called when SW long press is determined on UP SW.

### TFDCX32348-17146 (System Interface)
Function Entry - fn_drvrec_down_sw_long_press()
Description: This function is called when SW long press is determined on DOWN SW.

### TFDCX32348-17148 (System Interface)
Function Entry - fn_drvrec_enter_sw_short_press()
Description: This function is called when SW ON to OFF is detected before long press is determined on ENTER SW.

### TFDCX32348-17149 (System Interface)
Function Entry - fn_drvrec_back_sw_short_press()
Description: This function is called when SW ON to OFF is detected before long press is determined on BACK SW.

### TFDCX32348-17151 (System Interface)
Function Entry - fn_drvrec_enter_sw_long_press()
Description: This function is called when SW long press is determined on ENTER SW.

### TFDCX32348-17152 (System Interface)
Function Entry - fn_drvrec_back_sw_long_press()
Description: This function is called when SW long press is determined on BACK SW.

### TFDCX32348-17154 (System Interface)
Function Entry - fn_drvrec_rheo_up_sw_short_press()
Description: This function is called when short press is determined on rheostat.

### TFDCX32348-17156 (System Interface)
Function Entry - fn_drvrec_rheo_up_sw_long_press()
Description: This function is called when long press is determined on rheostat.

### TFDCX32348-58245 (System Interface)
Function Entry - fn_drvrec_rheo_down_sw_short_press()
Description: This function is called when short press is determined on rheostat.

### TFDCX32348-58246 (System Interface)
Function Entry - fn_drvrec_rheo_down_sw_long_press()
Description: This function is called when long press is determined on rheostat.

### TFDCX32348-58247 (System Interface)
Function Entry - fn_drvrec_odo_sw_short_press()
Description: This function is called when short press is determined on odo.

### TFDCX32348-58248 (System Interface)
Function Entry - fn_drvrec_odo_sw_long_press()
Description: This function is called when long press is determined on odo.

## TFDCX32348-57305: Performance Requirements (Heading)

### TFDCX32348-10561: Performance Requirements - Transmission signals of FUEL system (Heading)

#### TFDCX32348-17110: Processing cycle (Heading)

##### TFDCX32348-20051: Processing cycle = 800msec Reason : T... (System Requirement)
Processing cycle = 800msec
Reason : Transmission cycle of CAN Message MET1D50 is 800ms
- Verification Criteria: Verify by executing test cases
- Verification Method: System Qualification Test, Unit Test
- Verification Owner: FV, SW
- System Requirement State: Approved
- Primary Discipline: SW
- ASIL Rating: QM

#### TFDCX32348-57306: Normal Control (Heading)

##### TFDCX32348-57323: CANSignal - DATA_NUM (Heading)

###### TFDCX32348-12397: Description (System Requirement)
Description - Cyclic output of 0(00b) ⇒ 1(01b) ⇒ 2(10b) ⇒ 3(11b) ⇒ 0(00b)... every frame data update.
DATA_NUM must be retained during +B-ON.
The Output value will be stored in backup RAM.
- Verification Criteria: Verify by executing test cases
- Verification Method: System Qualification Test, Unit Test
- Verification Owner: FV, SW
- System Requirement State: Approved
- Primary Discipline: SW
- Key Requirement: False
- ASIL Rating: QM

##### TFDCX32348-57324: CANSignal - RNW_COND (Heading)

###### TFDCX32348-12399: Description (System Requirement)
Description - Output display update condition.
The status shall be retained until the next display update.
RNW_COND size is 3 bits. Thus Considering lower 3 bits of Fuel_ST signal.
| # | Input |  | Output | Remarks |
| --- | --- | --- | --- | --- |
| # | InternalSignal - Fuel_ST | InternalSignal - Refuel_cause_comp_data | CANSignal - RNW_COND | Remarks |
| 1 | 0001b or 1001b | x | 001b | Meter Start up (Initial Value) |
| 2 | 0000b or 1000b | 2[Comp_Data_C]) | 010b | Refuel judging by Comp_Data_C when IG-OFF→ON |
| 3 | 0000b or 1000b | 1[Comp_Data_Clid] | 011b | Refuel judging by Comp_Data_Clid when IG-OFF→ON |
| 4 | 0010b or 1010b | 2[Comp_Data_C]) | 100b | Refuel judging by Comp_Data_C during IG-ON |
| 5 | 0010b or 1010b | 1[Comp_Data_Clid] | 101b | Refuel judging by Comp_Data_Clid during IG-ON |
| 6 | 0110b or 1110b | x | 110b | Forcible update |
| 7 | Other than above |  | 000b | No update |
- Verification Criteria: Verify by executing test cases
- Verification Method: System Qualification Test, Unit Test
- Verification Owner: FV, SW
- System Requirement State: Approved
- Primary Discipline: SW
- Key Requirement: False
- ASIL Rating: QM

##### TFDCX32348-57325: CANSignal - STOP_JG (Heading)

###### TFDCX32348-12401: Description (System Requirement)
Description - Outputs "1b" during vehicle stopping judgment.
Initial state : STOP_JG=1
| # | Input | Output |
| --- | --- | --- |
| # | InternalSignal - VehicleStopFlag | CANSignal - STOP_JG |
| 1 | ON | 1b |
| 2 | OFF | 0b |
- Verification Criteria: Verify by executing test cases
- Verification Method: System Qualification Test, Unit Test
- Verification Owner: FV, SW
- System Requirement State: Approved
- Primary Discipline: SW
- Key Requirement: False
- ASIL Rating: QM

##### TFDCX32348-57326: CANSignal - OIL_SUPJ (Heading)

###### TFDCX32348-12404: Description (System Requirement)
Description - Outputs "1b" during lubrication judgment.
| # | Input | Output |
| --- | --- | --- |
| # | InternalSignal - Refuel_Judge | CANSignal - OIL_SUPJ |
| 1 | ON | 1b |
| 2 | OFF | 0b |
- Verification Criteria: Verify by executing test cases
- Verification Method: System Qualification Test, Unit Test
- Verification Owner: FV, SW
- System Requirement State: Approved
- Primary Discipline: SW
- Key Requirement: False
- ASIL Rating: QM

##### TFDCX32348-57327: CANSignal - ACTV_TST (Heading)

###### TFDCX32348-12406: Description (System Requirement)
Description - Outputting "1b" during the active test (fuel gauge operation)
ACTV_TST signal indicates fuel gauge IO Control Operation. But active test (DID2803: fuel gauge operation) is Not Applicable for current program. Hence, ACTV_TEST will be always 0b.
- Verification Criteria: Verify by executing test cases
- Verification Method: System Qualification Test, Unit Test
- Verification Owner: FV, SW
- System Requirement State: Approved
- Primary Discipline: SW
- Key Requirement: False
- ASIL Rating: QM

##### TFDCX32348-57328: CANSignal - IGON_SIG (Heading)

###### TFDCX32348-12409: Description (System Requirement)
Description - Outputting "1b" during IG-ON
| # | Input | Output |
| --- | --- | --- |
| # | InternalSignal – IgnMode | CANSignal - IGON_SIG |
| 1 | ON | 1b |
| 2 | OFF | 0b |
- Verification Criteria: Verify by executing test cases
- Verification Method: System Qualification Test, Unit Test
- Verification Owner: FV, SW
- System Requirement State: Approved
- Primary Discipline: SW
- Key Requirement: False
- ASIL Rating: QM

##### TFDCX32348-57329: CANSignal - STON_SIG (Heading)

###### TFDCX32348-12411: Description (System Requirement)
Description - Outputting "1b" during ST-ON
| # | Input |  | Output |
| --- | --- | --- | --- |
| # | CAN communication States - B_ST | CANSignal - B_ST | CANSignal - STON_SIG |
| 1 | Communication starting Never Received: 1 Communication Failure: 0 | x | 0b |
| 2 | Communication abnormality Never Received: x Communication Failure: 1 | x | 0b |
| 3 | Communication establishment Never Received: 0 Communication Failure: 0 | 1b | 1b |
| 4 | Communication establishment Never Received: 0 Communication Failure: 0 | 0b | 0b |
- Verification Criteria: Verify by executing test cases
- Verification Method: System Qualification Test, Unit Test
- Verification Owner: FV, SW
- System Requirement State: Approved
- Primary Discipline: SW
- Key Requirement: False
- ASIL Rating: QM

##### TFDCX32348-57330: CANSignal - MET_REST (Heading)

###### TFDCX32348-12413: Description (System Requirement)
Description - Transmit "1b" for 5.6s when CPU reset happens, after 5.6s transmit "0b".
- Verification Criteria: Verify by executing test cases
- Verification Method: System Qualification Test, Unit Test
- Verification Owner: FV, SW
- System Requirement State: Approved
- Primary Discipline: SW
- Key Requirement: False
- ASIL Rating: QM

##### TFDCX32348-57331: CANSignal - FLWNG_ON (Heading)

###### TFDCX32348-12416: Description (System Requirement)
Description - Outputting "1b" while the fuel level WNG is lit.
| # | Input | Output |
| --- | --- | --- |
| # | InternalSignal - Fuel_Enpty_Warn | CANSignal - FLWNG_ON |
| 1 | ON | 1b |
| 2 | OFF | 0b |
- Verification Criteria: Verify by executing test cases
- Verification Method: System Qualification Test, Unit Test
- Verification Owner: FV, SW
- System Requirement State: Approved
- Primary Discipline: SW
- Key Requirement: False
- ASIL Rating: QM

##### TFDCX32348-57332: CANSignal - FL_DISP (Heading)

###### TFDCX32348-12418: Description (System Requirement)
Description - Output the latest value of display data H.
| # | Input |  | Output |
| --- | --- | --- | --- |
| # | InternalSignal – IgnMode | InternalSignal - Disp_Data_H | CANSignal - FL_DISP (*1) |
| 1 | OFF | None | 00h |
| 2 | ON | Other than None | Min(Round((2*Disp_Data_H),0), 255) |
(*1) FL_DISP is 0.5L resolution.
- Verification Criteria: Verify by executing test cases
- Verification Method: System Qualification Test, Unit Test
- Verification Owner: FV, SW
- System Requirement State: Approved
- Primary Discipline: SW
- Key Requirement: False
- ASIL Rating: QM

##### TFDCX32348-57333: CANSignal - FL_COMP (Heading)

###### TFDCX32348-12420: Description (System Requirement)
Description - Outputs the value of the comparison data at the time of lubrication ( data will be updated anytime on every 800msec).
| # | Input |  | Output |
| --- | --- | --- | --- |
| # | InternalSignal - Comp_Data_C | InternalSignal - Comp_Data_Clid | CANSignal - FL_COMP(*1) |
| 1 | None | None | 00h |
| 2 | None | Other than None | Min(Round((2*Comp_Data_Clid),0), 255) |
| 3 | Other than None | None | Min(Round((2*Comp_Data_C),0), 255) |
| 4 | Other than None | Comp_Data_Clid <= Comp_Data_C | Min(Round((2*Comp_Data_C),0), 255) |
| 5 | Other than None | Comp_Data_C < Comp_Data_Clid | Min(Round((2*Comp_Data_Clid),0), 255) |
| 6 | Other than above |  | 00h |
(*1) FL_COMP is 0.5L resolution.
- Verification Criteria: Verify by executing test cases
- Verification Method: System Qualification Test, Unit Test
- Verification Owner: FV, SW
- System Requirement State: Approved
- Primary Discipline: SW
- Key Requirement: False
- ASIL Rating: QM

### TFDCX32348-10563: Performance Requirements - Transmission signals other than FUEL system (Heading)

#### TFDCX32348-17158: Processing cycle (Heading)

##### TFDCX32348-20053: Processing cycle = 1200msec Reason : ... (System Requirement)
Processing cycle = 1200msec
Reason : Transmission cycle of CAN Message MET1D51 is 1200ms
- Verification Criteria: Verify by executing test cases
- Verification Method: System Qualification Test, Unit Test
- Verification Owner: FV, SW
- System Requirement State: Approved
- Primary Discipline: SW
- ASIL Rating: QM

#### TFDCX32348-57307: Normal Control (Heading)

##### TFDCX32348-57384: CANSignal - DATA_NM2 (Heading)

###### TFDCX32348-12456: Description (System Requirement)
Description - Cyclic output of 0(00b) ⇒ 1(01b) ⇒ 2(10b) ⇒ 3(11b) ⇒ 0(00b)... every frame data update
DATA_NUM2 must be retained during +B-ON.
The Output value will be stored in backup RAM.
- Verification Criteria: Verify by executing test cases
- Verification Method: System Qualification Test, Unit Test
- Verification Owner: FV, SW
- System Requirement State: Approved
- Primary Discipline: SW
- Key Requirement: False
- ASIL Rating: QM

##### TFDCX32348-57385: CANSignal - D_N_INF (Heading)

###### TFDCX32348-12459: Description (System Requirement)
Description - Outputs the judgment result of the brightness of the outside environment.
| # | Input | Output |
| --- | --- | --- |
| # | InternalSignal - IlumDayNightStatus | CANSignal - D_N_INF |
| 1 | UNKNOWN | 00b |
| 2 | UNDEFINED | 01b |
| 3 | DAY | 10b |
| 4 | NIGHT | 11b |
| # | Input |  |  |  | Output |
| --- | --- | --- | --- | --- | --- |
| # | InternalSignal - AppMode | CANSignal - ADIM Never Received Status | CAN Signal - ADIM Communication Failure Status | CANSignal - ADIM | CANSignal - D_N_INF |
| 1 | (Initialization at CPU reset or wakeup) |  |  |  | 00b |
| 2 | Normal Network Mode | 1 (Never Received) | 0 (Normal) | X | No change |
| 3 | Normal Network Mode | X | 1 (Failed) | X | 01b |
| 4 | Normal Network Mode | 0 (Received) | 0 (Normal) | 10b | 10b |
| 5 | Normal Network Mode | 0 (Received) | 0 (Normal) | 11b | 11b |
| 6 | Normal Network Mode | 0 (Received) | 0 (Normal) | (00b or 01b) continued for 3.6 seconds. | 01b |
| 7 | Other than above |  |  |  | No change |
- Verification Criteria: Verify by executing test cases
- Verification Method: System Qualification Test, Unit Test
- Verification Owner: FV, SW
- System Requirement State: Approved
- Primary Discipline: SW
- Key Requirement: False
- ASIL Rating: QM

##### TFDCX32348-57386: CANSignal - RHEO_IN (Heading)

###### TFDCX32348-12461: Description (System Requirement)
Description - Outputting dimming status (DUTY ratio data) based on the rheostat position.
00h=0%, 64h=100%, 65h～FEh = Undefined, FFh = Undetermined
CANSignal - RHEO_IN shall send dimming status received from InternalSignal - Rheostat_Status WheelVolRatioMon.
| # | Input | Output |
| --- | --- | --- |
| # | InternalSignal - Rheostat_Status WheelVolRatioMon | CANSignal - RHEO_IN(*1) |
| 1 | Unknown UNDECIDED (0xFF) | FFh |
| 2 | Undefined | 65h-FEh |
| 3 | 0% (0x00) | Round((WheelVolRatioMon*100)/254, 0)) (= 00h) |
| 4 | : | : |
| 5 | 30% (0x4C) | Round((WheelVolRatioMon*100)/254, 0)) (= 1Eh) |
| 6 | : | : |
| 7 | 100% (0xFE) | Round((WheelVolRatioMon*100)/254, 0)) (= 64h) |
(*1) WheelVolRatioMon is 100/254% resolution, RHEO_IN is 1% resolution. This formula is intended to convert the resolution. WheelVolRatioMon = 254 (100%) -> (254 * 100) / 254 -> RHEO_IN = 100 (100%)
- Verification Criteria: Verify by executing test cases
- Verification Method: System Qualification Test, Unit Test
- Verification Owner: FV, SW
- System Requirement State: Approved
- Primary Discipline: SW
- Key Requirement: False
- ASIL Rating: QM

##### TFDCX32348-57387: CANSignal - ILL_OUT (Heading)

###### TFDCX32348-12462: Description (System Requirement)
Description - Outputting TFT Display Lighting Status (DUTY Ratio).
00h=0%, 64h=100%, 65h～FEh = Undefined, FFh = Undetermined
CANSignal - ILL_OUT = InternalSignal - ILLDuty
ILLDuty = (Refer TFDCX32348-25676: TFT Duty Output )
ILLDuty resolution = 1% ILL_OUT resolution=1%
| # | Input | Output |
| --- | --- | --- |
| # | InternalSignal - ILLDuty | CANSignal - ILL_OUT |
| 1 | Unknown | FFh |
| 2 | Undefined | 65h-FEh |
| 3 | 0% | 00h |
| 4 | : | : |
| 5 | 100% | 64h |
- Verification Criteria: Verify by executing test cases
- Verification Method: System Qualification Test, Unit Test
- Verification Owner: FV, SW
- System Requirement State: Approved
- Primary Discipline: SW
- Key Requirement: False
- ASIL Rating: QM

##### TFDCX32348-57322: CANSignal - SW_INF (Heading)

###### TFDCX32348-17160: Switch Press Status (Heading)

###### TFDCX32348-21106: Initialization (System Requirement)
| # | Parameter Name | Initial value at CPU reset or wake up |
| --- | --- | --- |
| 1 | SWGrp1ShortPress_Status | 0 |
| 2 | SWGrp1LongPress_Status | 0 |
| 3 | SWGrp2ShortPress_Status | 0 |
| 4 | SWGrp2LongPress_Status | 0 |
| 5 | SWGrp3ShortPress_Status | 0 |
| 6 | SWGrp3LongPress_Status | 0 |
| 7 | SWGrp4ShortPress_Status | 0 |
| 8 | SWGrp4LongPress_Status | 0 |
- Verification Criteria: Verify by executing test cases
- Verification Method: System Qualification Test, Unit Test
- Verification Owner: FV, SW
- System Requirement State: Approved
- Primary Discipline: SW
- ASIL Rating: QM

###### TFDCX32348-21107: Group1 Short Press (System Requirement)
Execute this when the function is called
| # | Input | Output |
| --- | --- | --- |
| # | Function Entry | SWGrp1ShortPress_Status |
| 1 | fn_drvrec_left_sw_short_press() | 1 |
| 2 | fn_drvrec_right_sw_short_press() | 1 |
| 3 | fn_drvrec_up_sw_short_press() | 1 |
| 4 | fn_drvrec_down_sw_short_press() | 1 |
- Verification Criteria: Verify by executing test cases
- Verification Method: System Qualification Test, Unit Test
- Verification Owner: FV, SW
- System Requirement State: Approved
- Primary Discipline: SW
- ASIL Rating: QM

###### TFDCX32348-21109: Group1 Long Press (System Requirement)
Execute this when the function is called
| # | Input | Output |  |
| --- | --- | --- | --- |
| # | Function Entry | PressedSW_LRUD | SWGrp1LongPress_Status |
| 1 | fn_drvrec_left_sw_long_press() | LEFT | 1 |
| 2 | fn_drvrec_right_sw_long_press() | RIGHT | 1 |
| 3 | fn_drvrec_up_sw_long_press() | UP | 1 |
| 4 | fn_drvrec_down_sw_long_press() | DOWN | 1 |
- Verification Criteria: Verify by executing test cases
- Verification Method: System Qualification Test, Unit Test
- Verification Owner: FV, SW
- System Requirement State: Approved
- Primary Discipline: SW
- ASIL Rating: QM

###### TFDCX32348-21111: Group2 Short Press (System Requirement)
Execute this when the function is called
| # | Input | Output |
| --- | --- | --- |
| # | Function Entry | SWGrp2ShortPress_Status |
| 1 | fn_drvrec_enter_sw_short_press() | 1 |
| 2 | fn_drvrec_back_sw_short_press() | 1 |
- Verification Criteria: Verify by executing test cases
- Verification Method: System Qualification Test, Unit Test
- Verification Owner: FV, SW
- System Requirement State: Approved
- Primary Discipline: SW
- ASIL Rating: QM

###### TFDCX32348-21113: Group2 Long Press (System Requirement)
Execute this when the function is called
| # | Input | Output |  |
| --- | --- | --- | --- |
| # | Function Entry | PressedSW_EB | SWGrp2LongPress_Status |
| 1 | fn_drvrec_enter_sw_long_press() | ENTER | 1 |
| 2 | fn_drvrec_back_sw_long_press() | BACK | 1 |
- Verification Criteria: Verify by executing test cases
- Verification Method: System Qualification Test, Unit Test
- Verification Owner: FV, SW
- System Requirement State: Approved
- Primary Discipline: SW
- ASIL Rating: QM

###### TFDCX32348-21115: Group3 Short Press (System Requirement)
Execute this when the function is called
| # | Input | Output |
| --- | --- | --- |
| # | Function Entry | SWGrp3ShortPress_Status |
| 1 | fn_drvrec_rheo_up_sw_short_press() | 1 |
| 2 | fn_drvrec_rheo_down_sw_short_press() | 1 |
- Verification Criteria: Verify by executing test cases
- Verification Method: System Qualification Test, Unit Test
- Verification Owner: FV, SW
- System Requirement State: Approved
- Primary Discipline: SW
- ASIL Rating: QM

###### TFDCX32348-21117: Group3 Long Press (System Requirement)
Execute this when the function is called
| # | Input | Output |  |
| --- | --- | --- | --- |
| # | Function Entry | PressedSW_RHEO_UD | SWGrp3LongPress_Status |
| 1 | fn_drvrec_rheo_up_sw_long_press() | UP | 1 |
| 2 | fn_drvrec_rheo_down_sw_long_press() | DOWN | 1 |
- Verification Criteria: Verify by executing test cases
- Verification Method: System Qualification Test, Unit Test
- Verification Owner: FV, SW
- System Requirement State: Approved
- Primary Discipline: SW
- ASIL Rating: QM

###### TFDCX32348-58229: Group4 Short Press (System Requirement)
Execute this when the function is called
| # | Input | Output |
| --- | --- | --- |
| # | Function Entry | SWGrp4ShortPress_Status |
| 1 | fn_drvrec_odo_sw_short_press() | 1 |
- Verification Criteria: Verify by executing test cases
- Verification Method: System Qualification Test, Unit Test
- Verification Owner: FV, SW
- System Requirement State: Approved
- Primary Discipline: SW
- ASIL Rating: QM

###### TFDCX32348-58230: Group4 Long Press (System Requirement)
Execute this when the function is called
| # | Input | Output |
| --- | --- | --- |
| # | Function Entry | SWGrp4LongPress_Status |
| 1 | fn_drvrec_odo_sw_long_press() | 1 |
- Verification Criteria: Verify by executing test cases
- Verification Method: System Qualification Test, Unit Test
- Verification Owner: FV, SW
- System Requirement State: Approved
- Primary Discipline: SW
- ASIL Rating: QM

###### TFDCX32348-20069: SW_INF CAN output (Heading)

###### TFDCX32348-21119: SW_INF.Bit0 (System Requirement)
| # | Input | Output |  |
| --- | --- | --- | --- |
| # | SWGrp1ShortPress_Status | CANSignal - SW_INF.Bit0 | SWGrp1ShortPress_Status |
| 1 | 1 | 1 | 0 |
| 2 | 0 | 0 | No Change |
- Verification Criteria: Verify by executing test cases
- Verification Method: System Qualification Test, Unit Test
- Verification Owner: FV, SW
- System Requirement State: Approved
- Primary Discipline: SW
- ASIL Rating: QM

###### TFDCX32348-21121: SW_INF.Bit1 (System Requirement)
| # | Input |  |  |  | Output |  |
| --- | --- | --- | --- | --- | --- | --- |
| # | SWGrp1LongPress_Status | CAN Signal SW_INF.Bit1 | PressedSW_LRUD | InternalSignal - TargetSW | CANSignal - SW_INF.Bit1 | SWGrp1LongPress_Status |
| 1 | 1 | 0 | x | x | 1 | No Change |
| 2 | 1 | 1 | LEFT | TG_LEFT | 1 | No Change |
| 3 | 1 | 1 | RIGHT | TG_RIGHT | 1 | No Change |
| 4 | 1 | 1 | UP | TG_UP | 1 | No Change |
| 5 | 1 | 1 | DOWN | TG_DOWN | 1 | No Change |
| 6 | 1 | 1 | Other than above |  | 0 | 0 |
| 7 | 0 | x | x | x | 0 | 0 |
- Verification Criteria: Verify by executing test cases
- Verification Method: System Qualification Test, Unit Test
- Verification Owner: FV, SW
- System Requirement State: Approved
- Primary Discipline: SW
- ASIL Rating: QM

###### TFDCX32348-21123: SW_INF.Bit2 (System Requirement)
| # | Input | Output |  |
| --- | --- | --- | --- |
| # | SWGrp2ShortPress_Status | CANSignal - SW_INF.Bit2 | SWGrp2ShortPress_Status |
| 1 | 1 | 1 | 0 |
| 2 | 0 | 0 | No Change |
- Verification Criteria: Verify by executing test cases
- Verification Method: System Qualification Test, Unit Test
- Verification Owner: FV, SW
- System Requirement State: Approved
- Primary Discipline: SW
- ASIL Rating: QM

###### TFDCX32348-21125: SW_INF.Bit3 (System Requirement)
| # | Input |  |  |  | Output |  |
| --- | --- | --- | --- | --- | --- | --- |
| # | SWGrp2LongPress_Status | CANSignal - SW_INF.Bit3 | PressedSW_EB | InternalSignal - TargetSW | CANSignal - SW_INF.Bit3 | SWGrp2LongPress_Status |
| 1 | 1 | 0 | x | x | 1 | No Change |
| 2 | 1 | 1 | ENTER | TG_ENTER | 1 | No Change |
| 3 | 1 | 1 | BACK | TG_BACK | 1 | No Change |
| 4 | 1 | 1 | Other than above |  | 0 | 0 |
| 5 | 0 | x | x | x | 0 | 0 |
- Verification Criteria: Verify by executing test cases
- Verification Method: System Qualification Test, Unit Test
- Verification Owner: FV, SW
- System Requirement State: Approved
- Primary Discipline: SW
- ASIL Rating: QM

###### TFDCX32348-21126: SW_INF.Bit4 (System Requirement)
| # | Input | Output |  |
| --- | --- | --- | --- |
| # | SWGrp3ShortPress_Status | CANSignal - SW_INF.Bit4 | SWGrp3ShortPress_Status |
| 1 | 1 | 1 | 0 |
| 2 | 0 | 0 | No Change |
- Verification Criteria: Verify by executing test cases
- Verification Method: System Qualification Test, Unit Test
- Verification Owner: FV, SW
- System Requirement State: Approved
- Primary Discipline: SW
- ASIL Rating: QM

###### TFDCX32348-21128: SW_INF.Bit5 (System Requirement)
| # | Input |  |  |  |  | Output |  |
| --- | --- | --- | --- | --- | --- | --- | --- |
| # | SWGrp3LongPress_Status | CANSignal - SW_INF.Bit5 | PressedSW_RHEO_UD | InternalSignal - RHUP_Dbc RHEO_SW_Status | InternalSignal - RHDW_Dbc | CANSignal - SW_INF.Bit5 | SWGrp3LongPress_Status |
| 1 | 1 | 0 | x | x | x | 1 | No Change |
| 2 | 1 | 1 | UP | ON | OFF | 1 | No Change |
| 3 | 1 | 1 | DOWN | OFF | ON | 1 | No Change |
| 4 | 1 | 1 | Other than above |  |  | 0 | 0 |
| 5 | 0 | x | x | x | x | 0 | 0 |
- Verification Criteria: Verify by executing test cases
- Verification Method: System Qualification Test, Unit Test
- Verification Owner: FV, SW
- System Requirement State: Approved
- Primary Discipline: SW
- ASIL Rating: QM

###### TFDCX32348-58228: SW_INF.Bit6 (System Requirement)
| # | Input | Output |  |
| --- | --- | --- | --- |
| # | SWGrp4ShortPress_Status | CANSignal - SW_INF.Bit6 | SWGrp4ShortPress_Status |
| 1 | 1 | 1 | 0 |
| 2 | 0 | 0 | No Change |
- Verification Criteria: Verify by executing test cases
- Verification Method: System Qualification Test, Unit Test
- Verification Owner: FV, SW
- System Requirement State: Approved
- Primary Discipline: SW
- ASIL Rating: QM

###### TFDCX32348-58227: SW_INF.Bit7 (System Requirement)
| # | Input |  | Output |  |
| --- | --- | --- | --- | --- |
| # | SWGrp4LongPress_Status | InternalSignal - OdoSw_Dbc | CANSignal - SW_INF.Bit7 | SWGrp4LongPress_Status |
| 1 | 1 | ON | 1 | No Change |
| 2 | 1 | OFF | 0 | 0 |
| 3 | 0 | x | 0 | 0 |
- Verification Criteria: Verify by executing test cases
- Verification Method: System Qualification Test, Unit Test
- Verification Owner: FV, SW
- System Requirement State: Approved
- Primary Discipline: SW
- ASIL Rating: QM

##### TFDCX32348-57389: CANSignal - IG_VOL (Heading)

###### TFDCX32348-12464: Description (System Requirement)
Description - Outputting IG monitor voltages
00h=0.0V, FEh=25.4V, FFh = Undetermined
| # | Input | Output |
| --- | --- | --- |
| # | HW A/D - IGN_AD | CANSignal - IG_VOL (*1) |
| 1 | AD value = 0 (0V) | 00h |
| 2 | : | : |
| 3 | AD value = 634 (4V) | Round((AD value*63)/1000,0) (= F0h 28h) |
| 4 | : | : |
| 5 | AD value = 1586 (10V) | Round((AD value*63)/1000,0) (= 64h) |
| 6 | : | : |
| 7 | AD value = 3805 (24V) | Round((AD value*63)/1000,0) (= F0h) |
Please refer IGNITION_MON sheet of Toyota_725D_HSIS_ANALOG_INPUTS_R002_20240910.xlsx for IGN_AD signal information, AD value range and its corresponding voltage value.
(*1) IGN_AD resolution = (Ignition Voltage/ADC Count)=(24/3805) = 0.0063V, IG_VOL resolution is 0.1V. This formula is intended to convert the resolution.
IGN_AD = 3805 (24V) -> (3805 * 63) / 1000 -> IG_VOL = 240 (24V)
Note: The threshold is decimal value in 12bit AD.
- Verification Criteria: Verify by executing test cases
- Verification Method: System Qualification Test, Unit Test
- Verification Owner: FV, SW
- System Requirement State: Approved
- Primary Discipline: SW
- Key Requirement: False
- ASIL Rating: QM

##### TFDCX32348-57390: CANSignal - DISP_TMP (Heading)

###### TFDCX32348-12465: Description (System Requirement)
Description - Because it is not used, FFh is transmitted at a fixed level.
- Verification Criteria: Verify by executing test cases
- Verification Method: System Qualification Test, Unit Test
- Verification Owner: FV, SW
- System Requirement State: Approved
- Primary Discipline: SW
- Key Requirement: False
- ASIL Rating: QM

##### TFDCX32348-57391: CANSignal - LN_FC (Heading)

###### TFDCX32348-12468: Description (System Requirement)
Description - Outputs the most recent learning fuel efficiency data Cg.
00h=0.0km/L, FEh=50.8km/L, FFh = Undetermined
Outputs "FFh" when data communication interruption judgment for calculation is made.
| # | Input |  |  | Output |
| --- | --- | --- | --- | --- |
| # | CAN communication States - SP1P | CAN communication States - B_FC | InternalSignal - KAM_Range_Cg | CANSignal - LN_FC(*1) |
| 1 | Communication abnormality Never Received: x Communication Failure: 1 | x | x | FFh |
| 2 | Other than above | Communication abnormality Never Received: x Communication Failure: 1 | x | FFh |
| 3 | Other than above | Other than above | Any value | Min(Round(KAM_Range_Cg*5,0), 254) |
(*1) LN_FC resolution is 0.2km/L.
- Verification Criteria: Verify by executing test cases
- Verification Method: System Qualification Test, Unit Test
- Verification Owner: FV, SW
- System Requirement State: Approved
- Primary Discipline: SW
- Key Requirement: False
- ASIL Rating: QM

##### TFDCX32348-57392: CANSignal - RF_FC (Heading)

###### TFDCX32348-12469: Description (System Requirement)
Description - Outputs the latest value of the average fuel economy after refueling.
i.e. Average fuel efficiency to be renewed at the timing between refueling and refueling
00h=0.0km/L, FEh=50.8km/L, FFh = Undetermined
Outputs "FFh" when data communication interruption judgment for calculation is made.
| # | Input |  |  |  | Output |
| --- | --- | --- | --- | --- | --- |
| # | CAN communication States - SP1P | CAN communication States - B_FC | CANSignal - SP1 InternalSignal - SP1_in | InternalSignal - Range_Fuel_Economy | CANSignal - RF_FC(*1) |
| 1 | Communication abnormality Never Received: x Communication Failure: 1 | x | x | x | FFh |
| 2 | Other than above | Communication abnormality Never Received: x Communication Failure: 1 | x | x | FFh |
| 3 | Other than above | Other than above | SP1 <= 1.75km/h SP1_in<=175[1.75km/h] | x | FFh |
| 4 | Other than above | Other than above | SP1 > 1.75km/h SP1_in> 175[1.75km/h] | Any value | Min(Round(Range_Fuel_Economy*5,0),254) |
(*1) RF_FC resolution is 0.2km/L.
- Verification Criteria: Verify by executing test cases
- Verification Method: System Qualification Test, Unit Test
- Verification Owner: FV, SW
- System Requirement State: Approved
- Primary Discipline: SW
- Key Requirement: False
- ASIL Rating: QM

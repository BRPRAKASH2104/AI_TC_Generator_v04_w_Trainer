# Json2ReqIF Transformation

# Specification: DIAG _ETM_Generic
- JDA Snapshot Date: 2025-10-31 07:59:54

## TFDCX32348-10577: DIAG_ETM_Generic (Heading)
- System Requirement State: Draft
- Primary Discipline: TBD
- ASIL Rating: TBD

## TFDCX32348-10579: History (Heading)
- System Requirement State: Draft
- Primary Discipline: TBD
- ASIL Rating: TBD

### TFDCX32348-12270: Version Date... (Information)
| Version | Date | Name | Description of change | SRD Baseline |
| --- | --- | --- | --- | --- |
| 0.1 | 2024/04/09 | Takeshi Yamane | New created TFDCX32348-23231 [SYS][12.3FDC][APP] ETM | BL_20240521_01 |
| 0.2 | 2024/09/26 | Mathieu Lenoble | Update of the procedure to enter and navigate in ETM mode. TFDCX32348-41765: [SYS][12.3FDC][APP][ETM] Update of the steps to enter in ETM | BL_20241018_01 |
| 0.3 | 2025/03/13 | Mathieu Lenoble | TFDCX32348-74557: [SYS][12.3FDC][APP][ETM] Addition of SW version and DTC - TFDCX32348-20087: HMI_IN_ETMMode Display in TFT ETM Mod... - TFDCX32348-21130: Functional Reference SRD SW version I... - TFDCX32348-20076: ETM Flow - TFDCX32348-17166: To enter in ETM, the following steps shall... | BL_20250328 |
- System Requirement State: Draft
- Primary Discipline: TBD
- ASIL Rating: TBD

## TFDCX32348-10581: Overview (Heading)
- System Requirement State: Draft
- Primary Discipline: TBD
- ASIL Rating: TBD

### TFDCX32348-12272 (Information)
This SRD describes how to enter and navigate in ETM as well as which information will be shown in ETM mode.
- System Requirement State: Draft
- Primary Discipline: TBD
- ASIL Rating: TBD

### TFDCX32348-12274: Figure - ETM Block (Heading)
- System Requirement State: Draft
- Primary Discipline: TBD
- ASIL Rating: TBD

#### TFDCX32348-17177 (System Requirement)
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- Verification Criteria: Verify by design review
- Verification Method: TBD
- Verification Owner: SW
- System Requirement State: Approved
- Secondary Disciplines: TBD
- Primary Discipline: SW
- ASIL Rating: QM

## TFDCX32348-10583: Input Requirements (Heading)
- System Requirement State: Draft
- Primary Discipline: TBD
- ASIL Rating: TBD

### TFDCX32348-12276: Switch Input (Heading)
- System Requirement State: Draft
- Primary Discipline: TBD
- ASIL Rating: TBD

#### TFDCX32348-17179: H/W DI - DI_TURN_HAZ_SYNC_L (System Interface)
- Verification Criteria: Verify by design review
- Verification Method: TBD
- Verification Owner: SW
- System Requirement State: Approved
- Secondary Disciplines: TBD
- Primary Discipline: SW
- ASIL Rating: QM

#### TFDCX32348-20071: H/W DI - DI_TURN_HAZ_SYNC_R (System Interface)
- Verification Method: TBD
- Verification Owner: SW
- System Requirement State: Approved
- Secondary Disciplines: TBD
- Primary Discipline: SW
- ASIL Rating: QM

#### TFDCX32348-17181: H/W DI - ODO_TripKnobInput (System Interface)
- Verification Criteria: Verify by Design Review
- Verification Method: TBD
- Verification Owner: SW
- System Requirement State: Approved
- Secondary Disciplines: TBD
- Primary Discipline: SW
- ASIL Rating: QM

### TFDCX32348-12279: Internal I/F (Heading)
- System Requirement State: Draft
- Primary Discipline: TBD
- ASIL Rating: TBD

#### TFDCX32348-17184: InternalSignal - IgnMode (System Interface)
- Verification Criteria: Verify by design review
- Verification Method: TBD
- Verification Owner: SW
- System Requirement State: Approved
- Secondary Disciplines: TBD
- Primary Discipline: SW
- ASIL Rating: QM

#### TFDCX32348-17186: InternalSignal - Speed_in (System Interface)
- Verification Criteria: Verify by design review
- Verification Method: TBD
- Verification Owner: SW
- System Requirement State: Approved
- Secondary Disciplines: TBD
- Primary Discipline: SW
- ASIL Rating: QM

### TFDCX32348-76526: NVM (Heading)
- System Requirement State: Draft
- Primary Discipline: TBD
- ASIL Rating: TBD

#### TFDCX32348-76527: NVM - NVM_EngineeringTestModeEnable (System Interface)
- Verification Criteria: Verify by design review
- Verification Method: TBD
- Verification Owner: SW
- System Requirement State: Approved
- Secondary Disciplines: TBD
- Primary Discipline: SW
- ASIL Rating: QM

## TFDCX32348-10585: Output Requirements (Heading)
- System Requirement State: Draft
- Primary Discipline: TBD
- ASIL Rating: TBD

### TFDCX32348-12281: Buzzer (Heading)
- System Requirement State: Draft
- Primary Discipline: TBD
- ASIL Rating: TBD

#### TFDCX32348-17190: InternalSignal - BuzzerTest_SBR (System Interface)
- Verification Criteria: Verify by design review
- Verification Method: TBD
- Verification Owner: SW
- System Requirement State: Approved
- Secondary Disciplines: TBD
- Primary Discipline: SW
- ASIL Rating: QM

#### TFDCX32348-17192: InternalSignal - BuzzerTest_CLESON (System Interface)
- Verification Criteria: Verify by design review
- Verification Method: TBD
- Verification Owner: SW
- System Requirement State: Approved
- Secondary Disciplines: TBD
- Primary Discipline: SW
- ASIL Rating: QM

#### TFDCX32348-17194: InternalSignal - BuzzerTest_Door_Ajar (System Interface)
- Verification Criteria: Verify by design review
- Verification Method: TBD
- Verification Owner: SW
- System Requirement State: Approved
- Secondary Disciplines: TBD
- Primary Discipline: SW
- ASIL Rating: QM

### TFDCX32348-12287: DayNight_Mode_Select (Heading)
- System Requirement State: Draft
- Primary Discipline: TBD
- ASIL Rating: TBD

#### TFDCX32348-17164: Internal Signal - DayNight_Mode (System Requirement)
- Verification Criteria: Verify by design review
- Verification Method: TBD
- Verification Owner: SW
- System Requirement State: Approved
- Secondary Disciplines: TBD
- Primary Discipline: SW
- ASIL Rating: QM

## TFDCX32348-10587: Performance Requirements (Heading)
- System Requirement State: Draft
- Primary Discipline: TBD
- ASIL Rating: TBD

### TFDCX32348-43181: Buttons mapping (Heading)
- System Requirement State: Draft
- Primary Discipline: TBD
- ASIL Rating: TBD

#### TFDCX32348-43183: The front panel of the Switch box... (Information)
The front panel of the Switch box is as follow:
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The mapping between the box switches and the HW digital inputs is shown in the table below:
| Switch name on the switch box | Corresponding HW digital inputs |
| --- | --- |
| TURN L | DI_TURN_HAZ_SYNC_L |
| TURN R | DI_TURN_HAZ_SYNC_R |
| ODO SW | ODO_TripKnobInput |
Notes:
1. For the IG switch, use the internal signal IgnMode
2. The mapping between the switches and the HW digital inputs is also applicable for all the ETM related SRDs.
- System Requirement State: Draft
- Primary Discipline: TBD
- ASIL Rating: TBD

### TFDCX32348-12290: Transition to ETM Mode (Heading)
- System Requirement State: Draft
- Primary Discipline: TBD
- ASIL Rating: TBD

#### TFDCX32348-17166 (System Requirement)
To enter in ETM, the following steps shall be performed on the Switch box developed for this program
Pre-conditions:
1. The ETM mode shall be enable (i.e. NVM_EngineeringTestModeEnable must be equal to 0x01)
2. The switch TURN R and TURN L on the test box shall be in OFF position.
Steps:
1. Turn OFF the IGN.
2. Set to ON the input TURN R for more than 3 seconds and turn ON the IGN
3. Within 3 seconds, set to ON the input TURN L
4. After 3 seconds cycle (ON → OFF → ON → OFF) the inputs TURN R in less than 3 seconds.
5. ETM mode is triggered.
*If following either phenomenon occur while doing the entry procedures then ECU shall not enter in ETM.
- IGN is turned OFF.
- Vehicle speed is 1 km/h or more. (Speed_in)
Cluster can enter into ETM mode when CAN signal "missing" and "never received".
- Verification Criteria: Verify by executing test cases
- Verification Method: Functional Verification / Validation
- Verification Owner: FV
- System Requirement State: Draft
- Secondary Disciplines: FV, SW
- Primary Discipline: SW
- ASIL Rating: QM

#### TFDCX32348-17170: If the condition of transition to ETM... (System Requirement)
If the condition of transition to ETM mode is satisfied, Meter shall enter to ETM mode and Display the "ETM MODE" even if other function is displayed.
- Verification Criteria: Verify by executing test cases
- Verification Method: Functional Verification / Validation
- Verification Owner: FV
- System Requirement State: Draft
- Primary Discipline: SW
- ASIL Rating: TBD

#### TFDCX32348-17174: DayNight_ModeTest DayNight_Mode Funct... (Information)
DayNight_ModeTest
DayNight_Mode Functionality when ETM mode is ON
Range : 0 - No Request , 1 - Day Request , 2 - Night Request
If ODO SW is pushed, DayNight_Mode will change.
When ODO SW is pushed, DayNight_ModeTest will be updated as mentioned below.
"Other Mode->DayLight Brightness-> Night Brightness->Daylight Brightness-> Other Mode"
- Verification Criteria: Verify by executing test cases
- Verification Method: Software Qualification Test, System Qualification Test, Unit Test
- Verification Owner: FV, SW
- System Requirement State: Draft
- Secondary Disciplines: FV, SW
- Primary Discipline: SW
- ASIL Rating: TBD

#### TFDCX32348-17176: Timing Diagram to enter in ETM (Heading)
- System Requirement State: Draft
- Primary Discipline: TBD
- ASIL Rating: TBD

##### TFDCX32348-20074: Timing Diagram (System Requirement)
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- Verification Criteria: Verify by executing test cases
- Verification Method: Functional Verification / Validation
- Verification Owner: FV
- System Requirement State: Approved
- Primary Discipline: SW
- ASIL Rating: QM

### TFDCX32348-12292: Return to Normal Operation (Heading)
- System Requirement State: Draft
- Primary Discipline: TBD
- ASIL Rating: TBD

#### TFDCX32348-17178: How to return to normal operation (ex... (System Requirement)
How to return to normal operation (exit the ETM mode) is following.
- IGN is turned OFF.
- Vehicle speed is 1 km/h or more. (Speed_in)
One of the either condition is satisfied, METER shall exit the ETM mode.
- Verification Criteria: Verify by executing test cases
- Verification Method: Functional Verification / Validation
- Verification Owner: FV
- System Requirement State: Approved
- Primary Discipline: SW
- ASIL Rating: QM

### TFDCX32348-12294: General Process (Heading)
- System Requirement State: Draft
- Primary Discipline: TBD
- ASIL Rating: TBD

#### TFDCX32348-17180 (Information)
This section describes how are organized each of the ETM panel. Each panel has its own SRD.
- Verification Criteria: Verify by executing test cases
- Verification Method: Software Qualification Test, System Qualification Test, Unit Test
- Verification Owner: FV, SW
- System Requirement State: Approved
- Secondary Disciplines: FV, SW
- Primary Discipline: SW
- ASIL Rating: QM

#### TFDCX32348-17182: Figure - ETM General Process Flow (Heading)
- System Requirement State: Draft
- Primary Discipline: TBD
- ASIL Rating: TBD

##### TFDCX32348-20076: ETM Flow (System Requirement)
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- Verification Criteria: Verify by executing test cases
- Verification Method: Functional Verification / Validation
- Verification Owner: FV
- System Requirement State: Approved
- Primary Discipline: SW
- ASIL Rating: QM

##### TFDCX32348-20078: Push ODO SW means "Short Push"... (System Requirement)
Push ODO SW means "Short Push", more detail information, refer to "Switch Input (Link : TFDCX32348-7311 )".
- Verification Criteria: Verify by executing test cases
- Verification Method: Functional Verification / Validation
- Verification Owner: FV
- System Requirement State: Approved
- Primary Discipline: SW
- ASIL Rating: QM

##### TFDCX32348-20080: Note:When performing step 2. following parameter shall be... (System Requirement)
Note:
When performing step 2. following parameter shall be changed to "OFF".
- BuzzerTest_CLESON
- BuzzerTest_SBR
- BuzzerTest_Door_Ajar
- Verification Criteria: Verify by executing test cases
- Verification Method: Functional Verification / Validation
- Verification Owner: FV
- System Requirement State: Approved
- Primary Discipline: SW
- ASIL Rating: QM

##### TFDCX32348-20082: Meter shall change to next panel... (System Requirement)
Meter shall change to next panel when ODO SW is pushed even if current test is on going.
- Verification Criteria: Verify by executing test cases
- Verification Method: Functional Verification / Validation
- Verification Owner: FV
- System Requirement State: Approved
- Primary Discipline: SW
- ASIL Rating: QM

##### TFDCX32348-20085: Table - Reference Destination of Each... (Heading)
Table - Reference Destination of Each Function
- System Requirement State: Draft
- Primary Discipline: TBD
- ASIL Rating: TBD

###### TFDCX32348-21130: Functional Reference SRD SW version I... (System Requirement)
| Functional | Reference SRD |
| --- | --- |
| SW version | ID: TFDCX32348-7815: DIAG_ETM_SW version |
| TFT Color Check | ID: TFDCX32348-841: DIAG_ETM_TFT color check |
| Buzzer Test | ID: TFDCX32348-7576: DIAG_ETM_Buzzer beep |
| DayNight_ModeTest | ID: TFDCX32348-17174 DayNight_ModeTest |
| DTC | ID: TFDCX32348-74132: DIAG_ETM_DTC |
- Verification Criteria: Verify by executing test cases
- Verification Method: Functional Verification / Validation
- Verification Owner: FV
- System Requirement State: Approved
- Primary Discipline: SW
- ASIL Rating: QM

#### TFDCX32348-17183: Table - Display for TFT by ETM Mode (Heading)
- System Requirement State: Draft
- Primary Discipline: TBD
- ASIL Rating: TBD

##### TFDCX32348-20087: HMI_IN_ETMMode Display in TFT ETM Mod... (System Requirement)
| HMI_IN_ETMMode | Display in TFT |
| --- | --- |
| ETM Mode OFF (0x00) | Display the current normal operation |
| ETM Mode ON (0x01) | Display the "ETM Mode" |
| SW Ver. | Display the "APL SW Ver.", "BOOT SW Ver." and customer SW version for each logical blocks. |
| TFT Test | Display the "TFT test pattern" |
| Buzzer Test | Display the "Buzzer Test" |
| DayNight_ModeTest | Display the "DayNight_Mode" |
| DTC | Display the DTC recorded |
- Verification Criteria: Verify by executing test cases
- Verification Method: Functional Verification / Validation
- Verification Owner: FV
- System Requirement State: Approved
- Primary Discipline: SW
- ASIL Rating: QM

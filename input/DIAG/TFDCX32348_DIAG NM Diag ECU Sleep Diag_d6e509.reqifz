# Json2ReqIF Transformation

# Specification: DIAG NM Diag, ECU Sleep Diag
- JDA Snapshot Date: 2025-10-31 07:59:36

## TFDCX32348-7817: NM Diag / ECU Sleep Diag (Heading)
NM Diag
- System Requirement State: Approved

## TFDCX32348-7819: History (Heading)
- System Requirement State: Approved

### TFDCX32348-10601: History (Information)
| Version | Date | Name | Description of change | SRD Baseline |
| --- | --- | --- | --- | --- |
| 1.0 | 28/Oct/2022 | ttakaba | [SYS][38xD][DIAG] NM Diagnostic (1777286) First release. | BL_20221116_02 |
| 1.1 | 30/Nov/2022 | ttakaba | Changed ODO value memory into snapshot from displayed value to CAN transmission value according to impediment1838164. (2798911, 2798912, 2815116, 2815120, 2788806, 2795919, 2795936, 2795948, 2795965) | BL_20221130_01 |
| 1.1a | 5/Jan/2023 | ttakaba | Added 5 seconds delay before memorizing data of TRIP_CNT/TIME_CNT to (G1)(L1)(G3) based on impediment 1870370. (2788806, 2795936, 2795948) | BL_20230113_01 |
| 1.1b | 22/May/2023 | ttakaba | T38XD29284-38320, T38XD29284-49293, T38XD29284-49297, T38XD29284-49302, T38XD29284-49306 Added a note "CAN activation due to the fuel tank warning has been removed. Bit 7 (0x0080) of CANWorkingReason and CANWakeupCause are never set in ope-mode processing." according to Cluster Operating mode and NM diag requirements are mismatched (2022765). | BL_20230522_01 (JIRA migration) |
| 1.1c (38xD) | 9/Jan/2024 | ttakaba | T38XD29284-49293, T38XD29284-49302, T38XD29284-49312, T38XD29284-49321, T38XD29284-49330, Not require software change but added a comment of voltage tolerance for validation according to T38XD29284-59501: Tips for validation | BL_20240109_01 |
| 2.0 (12.3FDC) | 22/Apr/2025 | ttakaba | TFDCX32348-76368: [SYS][12.3FDC][APP] NM Diagnostic TFDCX32348-76371: [SYS][12.3FDC][APP] ECU sleep diagnostics 79943, 17357, 17367, 17387, 17397 Added diag mask condition processing. 80133, 17357, 17360, 17367, 17371, 17385, 17391, 17400 Added UTC time information memory processing. 17355, 17357, 17360 CAN excessive wakeup fator is determined based on the recent 10 wakeup cause. 17357, 17367 Invoke CPU reset to recover failure. 79996, 17360, 80154, 17371, 80200, 17391, 80207, 17400 Snapshot storages are expanded to 3 sets. 12492 Removed CXPI excessive wakeup detection function 17385 Diag CAN frame ID is changed to extended ID. 80289, 80291, 80293, 80295, 80296 Implemented ECU sleep diag - (E1) cluster excessive wakeup detection. 80301, 80303, 80305, 80307, 80308 Implemented ECU sleep diag - (E2) cluster sleep NG continued detection. | BL_20250422_01 |
| 2.1 | 9/Jun/2025 | ttakaba | TFDCX32348-90521 [SYS][12.3FDC][IMP][APP][Diagnostic] update the target event frame for (G4)CAN Sleep NG detection This is SRD error fix in the previous release. Therefore, retains red highlight indicating the previous update and changes in this update are highlighted in orange. 79943 Corrected CAN communication failure condition from “Yes” to “No” in DiagMaskCondition processing table row#5,6. 17391 Fixed typo. (G2LastNM → G3LastNM) 17397 Updated event frame CAN IDs described in (*4) comment. | BL_20250611_01 |
| 2.2 | 27/Aug/2025 | ttakaba | TFDCX32348-97740 [SYS][12.3FDC][R5.2][STDQA3204][STDQA3230][STDQA3246][STDQA3247][APP][Diagnostic] Update Phase 6 Diag System for NM Diag - Updated diag mask PTSYS condition. 79943 Updated Diag Mask applicable PTSYS condition. - Reflect latest HSIS analog input (Toyota_725D_HSIS_ANALOG_INPUTS_R009_20250805.xlsx) 17357, 17367, 17387, 17397, 80291, 80303 Updated ADC count for 10.0V. | BL_20250828_01 |
- System Requirement State: Approved

## TFDCX32348-7821: Overview (Heading)
- System Requirement State: Approved

### TFDCX32348-10604: Overview (Information)
This feature monitors communiction status to detect unexpected behavior that repeats sleep wakeup or state that does not enter to sleep for long time after IG OFF.
If an incident is detected then cluster stores the occurrence and the cause information into NVM.
This information will be used to analyze the root cause when battery drain malfunction is occurred.
- System Requirement State: Approved

## TFDCX32348-7823: Input Requirements (Heading)
- System Requirement State: Approved

### TFDCX32348-10606: Date and Time Data - CurrentTime (System Interface)
Date and Time Data - CurrentTime.
Elapsed time must be measured in NM Diag. This elapsed time must be measured continuously even during CPU sleep.
Elapsed time is assumed to be measured based on the calender and time information obtained from RTC module in the micro.
Since this is elaped time, the date/time data obtained form the RTC module does not need to be the real time.
This SRD refers to the date/time data obtainded from the RTC module as CurrentTime.
- Verification Criteria: Verify by design/code review
- Verification Method: Code/Design Review
- Verification Owner: SW
- System Requirement State: Approved
- Primary Discipline: SW
- ASIL Rating: QM

### TFDCX32348-10608: Internal Signal - IgnMode (System Interface)
- Verification Criteria: Verify by design/code review
- Verification Method: Code/Design Review
- Verification Owner: SW
- System Requirement State: Approved
- Primary Discipline: SW
- ASIL Rating: QM

### TFDCX32348-10610: Internal Signal - ACCStatus (System Interface)
- Verification Criteria: Verify by design/code review
- Verification Method: Code/Design Review
- Verification Owner: SW
- System Requirement State: Approved
- Primary Discipline: SW
- ASIL Rating: QM

### TFDCX32348-10612: Internal Signal - CANWakeupCause (System Interface)
- Verification Criteria: Verify by design/code review
- Verification Method: Code/Design Review
- Verification Owner: SW
- System Requirement State: Approved
- Primary Discipline: SW
- ASIL Rating: QM

### TFDCX32348-10614: Internal Signal - CANWorkingReason (System Interface)
- Verification Criteria: Verify by design/code review
- Verification Method: Code/Design Review
- Verification Owner: SW
- System Requirement State: Approved
- Primary Discipline: SW
- ASIL Rating: QM

### TFDCX32348-10616: Internal Signal - CAN-NM_Mode (System Interface)
- Verification Criteria: Verify by design/code review
- Verification Method: Code/Design Review
- Verification Owner: SW
- System Requirement State: Approved
- Primary Discipline: SW
- ASIL Rating: QM

### TFDCX32348-10618: Internal Signal - LastReceivedNM (System Interface)
- Verification Criteria: Verify by design/code review
- Verification Method: Code/Design Review
- Verification Owner: SW
- System Requirement State: Approved
- Primary Discipline: SW
- ASIL Rating: QM

### TFDCX32348-10620: CAN messages (Received frame ID data) (System Interface)
- Verification Criteria: Verify by design/code review
- Verification Method: Code/Design Review
- Verification Owner: SW
- System Requirement State: Approved
- Primary Discipline: SW
- ASIL Rating: QM

### TFDCX32348-10622: CXPI messages (Received frame PID data) (Dropped) (System Interface)
- Verification Criteria: Verify by design/code review
- Verification Method: Code/Design Review
- Verification Owner: SW
- System Requirement State: Rejected
- Primary Discipline: SW
- ASIL Rating: QM

### TFDCX32348-10624: CAN Signal - TRIP_CNT (Message Label: BDB1F03) (Dropped) (System Interface)
- Verification Criteria: Verify by design/code review
- Verification Method: Code/Design Review
- Verification Owner: SW
- System Requirement State: Rejected
- Primary Discipline: SW
- ASIL Rating: QM

### TFDCX32348-10627: CAN Signal - TIME_CNT (Message Label: BDB1F03) (Dropped) (System Interface)
- Verification Criteria: Verify by design/code review
- Verification Method: Code/Design Review
- Verification Owner: SW
- System Requirement State: Rejected
- Primary Discipline: SW
- ASIL Rating: QM

### TFDCX32348-10633 (System Interface)
CAN Signal - ODO (Message Label: MET1S02) (Dropped)
Note: This CAN signal is cluster TX. This feature refers the output value.
- Verification Criteria: Verify by design/code review
- Verification Method: Code/Design Review
- Verification Owner: SW
- System Requirement State: Rejected
- Primary Discipline: SW
- ASIL Rating: QM

### TFDCX32348-10278 (System Interface)
CAN Signal - ODO_UINT (Message Label: MET1S02) (Dropped)
Note: This CAN signal is cluster TX. This feature refers the output value.
- Verification Criteria: Verify by design/code review
- Verification Method: Code/Design Review
- Verification Owner: SW
- System Requirement State: Rejected
- Primary Discipline: SW
- ASIL Rating: QM

### TFDCX32348-81555: CAN Signal - IGB_EIG (Message Label: PMN1G03) (System Interface)
- Verification Criteria: Verify by design/code review
- Verification Method: Code/Design Review
- Verification Owner: SW
- System Requirement State: Approved
- Primary Discipline: SW
- ASIL Rating: QM

### TFDCX32348-81676: CAN Signal D_SEC (Message Label: RSE1G20) (System Interface)
- Verification Criteria: Verify by design/code review
- Verification Method: Code/Design Review
- Verification Owner: SW
- System Requirement State: Approved
- Primary Discipline: SW
- ASIL Rating: QM

### TFDCX32348-81675: CAN Signal - D_MIN (Message Label: RSE1G20) (System Interface)
- Verification Criteria: Verify by design/code review
- Verification Method: Code/Design Review
- Verification Owner: SW
- System Requirement State: Approved
- Primary Discipline: SW
- ASIL Rating: QM

### TFDCX32348-81674: CAN Signal - D_HOUR (Message Label: RSE1G20) (System Interface)
- Verification Criteria: Verify by design/code review
- Verification Method: Code/Design Review
- Verification Owner: SW
- System Requirement State: Approved
- Primary Discipline: SW
- ASIL Rating: QM

### TFDCX32348-81673: CAN Signal - D_DAY (Message Label: RSE1G20) (System Interface)
- Verification Criteria: Verify by design/code review
- Verification Method: Code/Design Review
- Verification Owner: SW
- System Requirement State: Approved
- Primary Discipline: SW
- ASIL Rating: QM

### TFDCX32348-81672: CAN Signal - D_MONT (Message Label: RSE1G20) (System Interface)
- Verification Criteria: Verify by design/code review
- Verification Method: Code/Design Review
- Verification Owner: SW
- System Requirement State: Approved
- Primary Discipline: SW
- ASIL Rating: QM

### TFDCX32348-81671: CAN Signal - D_YEAR (Message Label: RSE1G20) (System Interface)
- Verification Criteria: Verify by design/code review
- Verification Method: Code/Design Review
- Verification Owner: SW
- System Requirement State: Approved
- Primary Discipline: SW
- ASIL Rating: QM

### TFDCX32348-81556: InternalSignal - AppMode (System Interface)
- Verification Criteria: Verify by design/code review
- Verification Method: Code/Design Review
- Verification Owner: SW
- System Requirement State: Approved
- Primary Discipline: SW
- ASIL Rating: QM

### TFDCX32348-81557: Internal Signal - ClusterWakeupCause (System Interface)
Internal Signal - ClusterWakeupCause
Meaning:This parameter provides the trigger factor that caused the cluster to wakeup.
- Verification Criteria: Verify by design/code review
- Verification Method: Code/Design Review
- Verification Owner: SW
- System Requirement State: Approved
- Primary Discipline: SW
- ASIL Rating: QM

### TFDCX32348-81558: Internal Signal - AppWorkingReason (System Interface)
Internal Signal - AppWorkingReason
Meaning:This parameter provides the reason why the cluster cannot sleep.
- Verification Criteria: Verify by design/code review
- Verification Method: Code/Design Review
- Verification Owner: SW
- System Requirement State: Approved
- Primary Discipline: SW
- ASIL Rating: QM

### TFDCX32348-81559: Internal Signal - ShutdownHoldReason (System Interface)
Internal Signal - ShutdownHoldReason
Meaning:This parameter provides the reason why the cluster cannot start shutdown.
- Verification Criteria: Verify by design/code review
- Verification Method: Code/Design Review
- Verification Owner: SW
- System Requirement State: Approved
- Primary Discipline: SW
- ASIL Rating: QM

### TFDCX32348-81561 (System Interface)
Internal Signal - BatteryDrainLogicStatus
Meaning: This parameter provides the status of the battery drain prevention logic.
Range: DISABLE, ENABLE
- Verification Criteria: Verify by design/code review
- Verification Method: Code/Design Review
- Verification Owner: SW
- System Requirement State: Approved
- Primary Discipline: SW
- ASIL Rating: QM

### TFDCX32348-81562: Internal Signal - PTSysTypeFlag (System Interface)
Internal Signal - PTSysTypeFlag
Meaning: This parameter indicates the powertrain system type.
- Verification Criteria: Verify by design/code review
- Verification Method: Code/Design Review
- Verification Owner: SW
- System Requirement State: Approved
- Primary Discipline: SW
- ASIL Rating: QM

### TFDCX32348-81563: Internal Signal - VehicleOdoInfo (System Interface)
- Verification Criteria: Verify by design/code review
- Verification Method: Code/Design Review
- Verification Owner: SW
- System Requirement State: Approved
- Primary Discipline: SW
- ASIL Rating: QM

### TFDCX32348-81664: H/W ADC - AI_BATTERY (System Interface)
- Verification Criteria: Verify by design/code review
- Verification Method: Code/Design Review
- Verification Owner: SW
- System Requirement State: Approved
- Primary Discipline: SW
- ASIL Rating: QM

## TFDCX32348-7825: Output Requirements (Heading)
- System Requirement State: Approved

### TFDCX32348-10280: N/A (System Interface)
- Verification Criteria: Verify by design/code review
- Verification Method: Code/Design Review
- Verification Owner: SW
- System Requirement State: Approved
- Primary Discipline: SW
- ASIL Rating: QM

## TFDCX32348-7827: Function Entry (Heading)
- System Requirement State: Approved

### TFDCX32348-10282 (System Interface)
Function Entry - fn_NM_Sleep_diag_RoB_clear()
Description: Diag feature shall call this function to clear RoB NVM data.
- Verification Criteria: Verify by design/code review
- Verification Method: Code/Design Review
- Verification Owner: SW
- System Requirement State: Approved
- Primary Discipline: SW
- ASIL Rating: QM

## TFDCX32348-81654: Function Calls (Heading)
- System Requirement State: Approved

### TFDCX32348-81655 (System Interface)
Function Call - fn_diag_U2A1600_Detected()
Description : Calls this function when U2A1600 (Excessive CAN wakeup by internal cause) DTC is detected.
- Verification Criteria: Verify by design/code review
- Verification Method: Code/Design Review
- Verification Owner: SW
- System Requirement State: Approved
- Primary Discipline: SW
- ASIL Rating: QM

### TFDCX32348-81656 (System Interface)
Function Call - fn_diag_U2A1700_Detected()
Description : Calls this function when U2A1700 (CAN sleep NG continued by internal cause) DTC is detected.
- Verification Criteria: Verify by design/code review
- Verification Method: Code/Design Review
- Verification Owner: SW
- System Requirement State: Approved
- Primary Discipline: SW
- ASIL Rating: QM

### TFDCX32348-81657 (System Interface)
Function Call - fn_diag_U2A1200_Detected()
Description : Calls this function when U2A1200 (Excessive CAN wakeup by global cause) DTC is detected.
- Verification Criteria: Verify by design/code review
- Verification Method: Code/Design Review
- Verification Owner: SW
- System Requirement State: Approved
- Primary Discipline: SW
- ASIL Rating: QM

### TFDCX32348-81658 (System Interface)
Function Call - fn_diag_U2A1300_Detected()
Description : Calls this function when U2A1300 (CAN sleep NG continued by global cause) DTC is detected.
- Verification Criteria: Verify by design/code review
- Verification Method: Code/Design Review
- Verification Owner: SW
- System Requirement State: Approved
- Primary Discipline: SW
- ASIL Rating: QM

### TFDCX32348-81659 (System Interface)
Function Call - fn_diag_U2A0000_Detected()
Description : Calls this function when U2A0000 (Excessive cluster wakeup) DTC is detected.
- Verification Criteria: Verify by design/code review
- Verification Method: Code/Design Review
- Verification Owner: SW
- System Requirement State: Approved
- Primary Discipline: SW
- ASIL Rating: QM

### TFDCX32348-81660 (System Interface)
Function Call - fn_diag_U2A0100_Detected()
Description : Calls this function when U2A0100 (Cluster sleep NG continued) DTC is detected.
- Verification Criteria: Verify by design/code review
- Verification Method: Code/Design Review
- Verification Owner: SW
- System Requirement State: Approved
- Primary Discipline: SW
- ASIL Rating: QM

## TFDCX32348-7829: NVM Requirements (Heading)
- System Requirement State: Approved

### TFDCX32348-10284: NVM UserDefDTC U2A1600 - (G1) CAN Excessive wake up (Cluster Internal Cause) (Heading)
- System Requirement State: Approved

#### TFDCX32348-80639: NVM - NVM_U2A1600_Snapshot (System Interface)
- Verification Criteria: Verify by design/code review
- Verification Method: Code/Design Review
- Verification Owner: SW
- System Requirement State: Approved
- Primary Discipline: SW
- ASIL Rating: QM

#### TFDCX32348-80640: NVM - NVM_U2A1600_TripCnt_1 (System Interface)
- Verification Criteria: Verify by design/code review
- Verification Method: Code/Design Review
- Verification Owner: SW
- System Requirement State: Approved
- Primary Discipline: SW
- ASIL Rating: QM

#### TFDCX32348-80641: NVM - NVM_U2A1600_TimeCnt_1 (System Interface)
- Verification Criteria: Verify by design/code review
- Verification Method: Code/Design Review
- Verification Owner: SW
- System Requirement State: Approved
- Primary Discipline: SW
- ASIL Rating: QM

#### TFDCX32348-80642: NVM - NVM_U2A1600_Odo_1 (System Interface)
- Verification Criteria: Verify by design/code review
- Verification Method: Code/Design Review
- Verification Owner: SW
- System Requirement State: Approved
- Primary Discipline: SW
- ASIL Rating: QM

#### TFDCX32348-80643: NVM - NVM_U2A1600_Year_1 (System Interface)
- Verification Criteria: Verify by design/code review
- Verification Method: Code/Design Review
- Verification Owner: SW
- System Requirement State: Approved
- Primary Discipline: SW
- ASIL Rating: QM

#### TFDCX32348-80644: NVM - NVM_U2A1600_Mont_1 (System Interface)
- Verification Criteria: Verify by design/code review
- Verification Method: Code/Design Review
- Verification Owner: SW
- System Requirement State: Approved
- Primary Discipline: SW
- ASIL Rating: QM

#### TFDCX32348-80645: NVM - NVM_U2A1600_Date_1 (System Interface)
- Verification Criteria: Verify by design/code review
- Verification Method: Code/Design Review
- Verification Owner: SW
- System Requirement State: Approved
- Primary Discipline: SW
- ASIL Rating: QM

#### TFDCX32348-80646: NVM - NVM_U2A1600_Hour_1 (System Interface)
- Verification Criteria: Verify by design/code review
- Verification Method: Code/Design Review
- Verification Owner: SW
- System Requirement State: Approved
- Primary Discipline: SW
- ASIL Rating: QM

#### TFDCX32348-80647: NVM - NVM_U2A1600_Min_1 (System Interface)
- Verification Criteria: Verify by design/code review
- Verification Method: Code/Design Review
- Verification Owner: SW
- System Requirement State: Approved
- Primary Discipline: SW
- ASIL Rating: QM

#### TFDCX32348-80648: NVM - NVM_U2A1600_Sec_1 (System Interface)
- Verification Criteria: Verify by design/code review
- Verification Method: Code/Design Review
- Verification Owner: SW
- System Requirement State: Approved
- Primary Discipline: SW
- ASIL Rating: QM

#### TFDCX32348-80649: NVM - NVM_U2A1600_Factor00_1 (System Interface)
- Verification Criteria: Verify by design/code review
- Verification Method: Code/Design Review
- Verification Owner: SW
- System Requirement State: Approved
- Primary Discipline: SW
- ASIL Rating: QM

#### TFDCX32348-80650: NVM - NVM_U2A1600_Factor01_1 (System Interface)
- Verification Criteria: Verify by design/code review
- Verification Method: Code/Design Review
- Verification Owner: SW
- System Requirement State: Approved
- Primary Discipline: SW
- ASIL Rating: QM

#### TFDCX32348-80651: NVM - NVM_U2A1600_Factor02_1 (System Interface)
- Verification Criteria: Verify by design/code review
- Verification Method: Code/Design Review
- Verification Owner: SW
- System Requirement State: Approved
- Primary Discipline: SW
- ASIL Rating: QM

#### TFDCX32348-80652: NVM - NVM_U2A1600_Factor04_1 (System Interface)
- Verification Criteria: Verify by design/code review
- Verification Method: Code/Design Review
- Verification Owner: SW
- System Requirement State: Approved
- Primary Discipline: SW
- ASIL Rating: QM

#### TFDCX32348-80653: NVM - NVM_U2A1600_TripCnt_2 (System Interface)
- Verification Criteria: Verify by design/code review
- Verification Method: Code/Design Review
- Verification Owner: SW
- System Requirement State: Approved
- Primary Discipline: SW
- ASIL Rating: QM

#### TFDCX32348-80654: NVM - NVM_U2A1600_TimeCnt_2 (System Interface)
- Verification Criteria: Verify by design/code review
- Verification Method: Code/Design Review
- Verification Owner: SW
- System Requirement State: Approved
- Primary Discipline: SW
- ASIL Rating: QM

#### TFDCX32348-80655: NVM - NVM_U2A1600_Odo_2 (System Interface)
- Verification Criteria: Verify by design/code review
- Verification Method: Code/Design Review
- Verification Owner: SW
- System Requirement State: Approved
- Primary Discipline: SW
- ASIL Rating: QM

#### TFDCX32348-80656: NVM - NVM_U2A1600_Year_2 (System Interface)
- Verification Criteria: Verify by design/code review
- Verification Method: Code/Design Review
- Verification Owner: SW
- System Requirement State: Approved
- Primary Discipline: SW
- ASIL Rating: QM

#### TFDCX32348-80657: NVM - NVM_U2A1600_Mont_2 (System Interface)
- Verification Criteria: Verify by design/code review
- Verification Method: Code/Design Review
- Verification Owner: SW
- System Requirement State: Approved
- Primary Discipline: SW
- ASIL Rating: QM

#### TFDCX32348-80658: NVM - NVM_U2A1600_Date_2 (System Interface)
- Verification Criteria: Verify by design/code review
- Verification Method: Code/Design Review
- Verification Owner: SW
- System Requirement State: Approved
- Primary Discipline: SW
- ASIL Rating: QM

#### TFDCX32348-80659: NVM - NVM_U2A1600_Hour_2 (System Interface)
- Verification Criteria: Verify by design/code review
- Verification Method: Code/Design Review
- Verification Owner: SW
- System Requirement State: Approved
- Primary Discipline: SW
- ASIL Rating: QM

#### TFDCX32348-80660: NVM - NVM_U2A1600_Min_2 (System Interface)
- Verification Criteria: Verify by design/code review
- Verification Method: Code/Design Review
- Verification Owner: SW
- System Requirement State: Approved
- Primary Discipline: SW
- ASIL Rating: QM

#### TFDCX32348-80661: NVM - NVM_U2A1600_Sec_2 (System Interface)
- Verification Criteria: Verify by design/code review
- Verification Method: Code/Design Review
- Verification Owner: SW
- System Requirement State: Approved
- Primary Discipline: SW
- ASIL Rating: QM

#### TFDCX32348-80662: NVM - NVM_U2A1600_Factor00_2 (System Interface)
- Verification Criteria: Verify by design/code review
- Verification Method: Code/Design Review
- Verification Owner: SW
- System Requirement State: Approved
- Primary Discipline: SW
- ASIL Rating: QM

#### TFDCX32348-80663: NVM - NVM_U2A1600_Factor01_2 (System Interface)
- Verification Criteria: Verify by design/code review
- Verification Method: Code/Design Review
- Verification Owner: SW
- System Requirement State: Approved
- Primary Discipline: SW
- ASIL Rating: QM

#### TFDCX32348-80664: NVM - NVM_U2A1600_Factor02_2 (System Interface)
- Verification Criteria: Verify by design/code review
- Verification Method: Code/Design Review
- Verification Owner: SW
- System Requirement State: Approved
- Primary Discipline: SW
- ASIL Rating: QM

#### TFDCX32348-80665: NVM - NVM_U2A1600_Factor04_2 (System Interface)
- Verification Criteria: Verify by design/code review
- Verification Method: Code/Design Review
- Verification Owner: SW
- System Requirement State: Approved
- Primary Discipline: SW
- ASIL Rating: QM

#### TFDCX32348-80666: NVM - NVM_U2A1600_TripCnt_3 (System Interface)
- Verification Criteria: Verify by design/code review
- Verification Method: Code/Design Review
- Verification Owner: SW
- System Requirement State: Approved
- Primary Discipline: SW
- ASIL Rating: QM

#### TFDCX32348-80667: NVM - NVM_U2A1600_TimeCnt_3 (System Interface)
- Verification Criteria: Verify by design/code review
- Verification Method: Code/Design Review
- Verification Owner: SW
- System Requirement State: Approved
- Primary Discipline: SW
- ASIL Rating: QM

#### TFDCX32348-80668: NVM - NVM_U2A1600_Odo_3 (System Interface)
- Verification Criteria: Verify by design/code review
- Verification Method: Code/Design Review
- Verification Owner: SW
- System Requirement State: Approved
- Primary Discipline: SW
- ASIL Rating: QM

#### TFDCX32348-80669: NVM - NVM_U2A1600_Year_3 (System Interface)
- Verification Criteria: Verify by design/code review
- Verification Method: Code/Design Review
- Verification Owner: SW
- System Requirement State: Approved
- Primary Discipline: SW
- ASIL Rating: QM

#### TFDCX32348-80670: NVM - NVM_U2A1600_Mont_3 (System Interface)
- Verification Criteria: Verify by design/code review
- Verification Method: Code/Design Review
- Verification Owner: SW
- System Requirement State: Approved
- Primary Discipline: SW
- ASIL Rating: QM

#### TFDCX32348-80671: NVM - NVM_U2A1600_Date_3 (System Interface)
- Verification Criteria: Verify by design/code review
- Verification Method: Code/Design Review
- Verification Owner: SW
- System Requirement State: Approved
- Primary Discipline: SW
- ASIL Rating: QM

#### TFDCX32348-80672: NVM - NVM_U2A1600_Hour_3 (System Interface)
- Verification Criteria: Verify by design/code review
- Verification Method: Code/Design Review
- Verification Owner: SW
- System Requirement State: Approved
- Primary Discipline: SW
- ASIL Rating: QM

#### TFDCX32348-80673: NVM - NVM_U2A1600_Min_3 (System Interface)
- Verification Criteria: Verify by design/code review
- Verification Method: Code/Design Review
- Verification Owner: SW
- System Requirement State: Approved
- Primary Discipline: SW
- ASIL Rating: QM

#### TFDCX32348-80674: NVM - NVM_U2A1600_Sec_3 (System Interface)
- Verification Criteria: Verify by design/code review
- Verification Method: Code/Design Review
- Verification Owner: SW
- System Requirement State: Approved
- Primary Discipline: SW
- ASIL Rating: QM

#### TFDCX32348-80675: NVM - NVM_U2A1600_Factor00_3 (System Interface)
- Verification Criteria: Verify by design/code review
- Verification Method: Code/Design Review
- Verification Owner: SW
- System Requirement State: Approved
- Primary Discipline: SW
- ASIL Rating: QM

#### TFDCX32348-80676: NVM - NVM_U2A1600_Factor01_3 (System Interface)
- Verification Criteria: Verify by design/code review
- Verification Method: Code/Design Review
- Verification Owner: SW
- System Requirement State: Approved
- Primary Discipline: SW
- ASIL Rating: QM

#### TFDCX32348-80677: NVM - NVM_U2A1600_Factor02_3 (System Interface)
- Verification Criteria: Verify by design/code review
- Verification Method: Code/Design Review
- Verification Owner: SW
- System Requirement State: Approved
- Primary Discipline: SW
- ASIL Rating: QM

#### TFDCX32348-80678: NVM - NVM_U2A1600_Factor04_3 (System Interface)
- Verification Criteria: Verify by design/code review
- Verification Method: Code/Design Review
- Verification Owner: SW
- System Requirement State: Approved
- Primary Discipline: SW
- ASIL Rating: QM

### TFDCX32348-10286: NVM UserDefDTC U2A1700 - (G2) CAN Sleep NG Continued (Cluster Internal Cause) (Heading)
- System Requirement State: Approved

#### TFDCX32348-80879: NVM - NVM_U2A1700_Snapshot (System Interface)
- Verification Criteria: Verify by design/code review
- Verification Method: Code/Design Review
- Verification Owner: SW
- System Requirement State: Approved
- Primary Discipline: SW
- ASIL Rating: QM

#### TFDCX32348-80880: NVM - NVM_U2A1700_TripCnt_1 (System Interface)
- Verification Criteria: Verify by design/code review
- Verification Method: Code/Design Review
- Verification Owner: SW
- System Requirement State: Approved
- Primary Discipline: SW
- ASIL Rating: QM

#### TFDCX32348-80881: NVM - NVM_U2A1700_TimeCnt_1 (System Interface)
- Verification Criteria: Verify by design/code review
- Verification Method: Code/Design Review
- Verification Owner: SW
- System Requirement State: Approved
- Primary Discipline: SW
- ASIL Rating: QM

#### TFDCX32348-80882: NVM - NVM_U2A1700_Odo_1 (System Interface)
- Verification Criteria: Verify by design/code review
- Verification Method: Code/Design Review
- Verification Owner: SW
- System Requirement State: Approved
- Primary Discipline: SW
- ASIL Rating: QM

#### TFDCX32348-80883: NVM - NVM_U2A1700_Year_1 (System Interface)
- Verification Criteria: Verify by design/code review
- Verification Method: Code/Design Review
- Verification Owner: SW
- System Requirement State: Approved
- Primary Discipline: SW
- ASIL Rating: QM

#### TFDCX32348-80884: NVM - NVM_U2A1700_Mont_1 (System Interface)
- Verification Criteria: Verify by design/code review
- Verification Method: Code/Design Review
- Verification Owner: SW
- System Requirement State: Approved
- Primary Discipline: SW
- ASIL Rating: QM

#### TFDCX32348-80885: NVM - NVM_U2A1700_Date_1 (System Interface)
- Verification Criteria: Verify by design/code review
- Verification Method: Code/Design Review
- Verification Owner: SW
- System Requirement State: Approved
- Primary Discipline: SW
- ASIL Rating: QM

#### TFDCX32348-80886: NVM - NVM_U2A1700_Hour_1 (System Interface)
- Verification Criteria: Verify by design/code review
- Verification Method: Code/Design Review
- Verification Owner: SW
- System Requirement State: Approved
- Primary Discipline: SW
- ASIL Rating: QM

#### TFDCX32348-80887: NVM - NVM_U2A1700_Min_1 (System Interface)
- Verification Criteria: Verify by design/code review
- Verification Method: Code/Design Review
- Verification Owner: SW
- System Requirement State: Approved
- Primary Discipline: SW
- ASIL Rating: QM

#### TFDCX32348-80888: NVM - NVM_U2A1700_Sec_1 (System Interface)
- Verification Criteria: Verify by design/code review
- Verification Method: Code/Design Review
- Verification Owner: SW
- System Requirement State: Approved
- Primary Discipline: SW
- ASIL Rating: QM

#### TFDCX32348-80889: NVM - NVM_U2A1700_Factor00_1 (System Interface)
- Verification Criteria: Verify by design/code review
- Verification Method: Code/Design Review
- Verification Owner: SW
- System Requirement State: Approved
- Primary Discipline: SW
- ASIL Rating: QM

#### TFDCX32348-80890: NVM - NVM_U2A1700_Factor01_1 (System Interface)
- Verification Criteria: Verify by design/code review
- Verification Method: Code/Design Review
- Verification Owner: SW
- System Requirement State: Approved
- Primary Discipline: SW
- ASIL Rating: QM

#### TFDCX32348-80891: NVM - NVM_U2A1700_Factor02_1 (System Interface)
- Verification Criteria: Verify by design/code review
- Verification Method: Code/Design Review
- Verification Owner: SW
- System Requirement State: Approved
- Primary Discipline: SW
- ASIL Rating: QM

#### TFDCX32348-80892: NVM - NVM_U2A1700_Factor04_1 (System Interface)
- Verification Criteria: Verify by design/code review
- Verification Method: Code/Design Review
- Verification Owner: SW
- System Requirement State: Approved
- Primary Discipline: SW
- ASIL Rating: QM

#### TFDCX32348-80893: NVM - NVM_U2A1700_TripCnt_2 (System Interface)
- Verification Criteria: Verify by design/code review
- Verification Method: Code/Design Review
- Verification Owner: SW
- System Requirement State: Approved
- Primary Discipline: SW
- ASIL Rating: QM

#### TFDCX32348-80894: NVM - NVM_U2A1700_TimeCnt_2 (System Interface)
- Verification Criteria: Verify by design/code review
- Verification Method: Code/Design Review
- Verification Owner: SW
- System Requirement State: Approved
- Primary Discipline: SW
- ASIL Rating: QM

#### TFDCX32348-80895: NVM - NVM_U2A1700_Odo_2 (System Interface)
- Verification Criteria: Verify by design/code review
- Verification Method: Code/Design Review
- Verification Owner: SW
- System Requirement State: Approved
- Primary Discipline: SW
- ASIL Rating: QM

#### TFDCX32348-80896: NVM - NVM_U2A1700_Year_2 (System Interface)
- Verification Criteria: Verify by design/code review
- Verification Method: Code/Design Review
- Verification Owner: SW
- System Requirement State: Approved
- Primary Discipline: SW
- ASIL Rating: QM

#### TFDCX32348-80897: NVM - NVM_U2A1700_Mont_2 (System Interface)
- Verification Criteria: Verify by design/code review
- Verification Method: Code/Design Review
- Verification Owner: SW
- System Requirement State: Approved
- Primary Discipline: SW
- ASIL Rating: QM

#### TFDCX32348-80898: NVM - NVM_U2A1700_Date_2 (System Interface)
- Verification Criteria: Verify by design/code review
- Verification Method: Code/Design Review
- Verification Owner: SW
- System Requirement State: Approved
- Primary Discipline: SW
- ASIL Rating: QM

#### TFDCX32348-80899: NVM - NVM_U2A1700_Hour_2 (System Interface)
- Verification Criteria: Verify by design/code review
- Verification Method: Code/Design Review
- Verification Owner: SW
- System Requirement State: Approved
- Primary Discipline: SW
- ASIL Rating: QM

#### TFDCX32348-80900: NVM - NVM_U2A1700_Min_2 (System Interface)
- Verification Criteria: Verify by design/code review
- Verification Method: Code/Design Review
- Verification Owner: SW
- System Requirement State: Approved
- Primary Discipline: SW
- ASIL Rating: QM

#### TFDCX32348-80901: NVM - NVM_U2A1700_Sec_2 (System Interface)
- Verification Criteria: Verify by design/code review
- Verification Method: Code/Design Review
- Verification Owner: SW
- System Requirement State: Approved
- Primary Discipline: SW
- ASIL Rating: QM

#### TFDCX32348-80902: NVM - NVM_U2A1700_Factor00_2 (System Interface)
- Verification Criteria: Verify by design/code review
- Verification Method: Code/Design Review
- Verification Owner: SW
- System Requirement State: Approved
- Primary Discipline: SW
- ASIL Rating: QM

#### TFDCX32348-80903: NVM - NVM_U2A1700_Factor01_2 (System Interface)
- Verification Criteria: Verify by design/code review
- Verification Method: Code/Design Review
- Verification Owner: SW
- System Requirement State: Approved
- Primary Discipline: SW
- ASIL Rating: QM

#### TFDCX32348-80904: NVM - NVM_U2A1700_Factor02_2 (System Interface)
- Verification Criteria: Verify by design/code review
- Verification Method: Code/Design Review
- Verification Owner: SW
- System Requirement State: Approved
- Primary Discipline: SW
- ASIL Rating: QM

#### TFDCX32348-80905: NVM - NVM_U2A1700_Factor04_2 (System Interface)
- Verification Criteria: Verify by design/code review
- Verification Method: Code/Design Review
- Verification Owner: SW
- System Requirement State: Approved
- Primary Discipline: SW
- ASIL Rating: QM

#### TFDCX32348-80906: NVM - NVM_U2A1700_TripCnt_3 (System Interface)
- Verification Criteria: Verify by design/code review
- Verification Method: Code/Design Review
- Verification Owner: SW
- System Requirement State: Approved
- Primary Discipline: SW
- ASIL Rating: QM

#### TFDCX32348-80907: NVM - NVM_U2A1700_TimeCnt_3 (System Interface)
- Verification Criteria: Verify by design/code review
- Verification Method: Code/Design Review
- Verification Owner: SW
- System Requirement State: Approved
- Primary Discipline: SW
- ASIL Rating: QM

#### TFDCX32348-80908: NVM - NVM_U2A1700_Odo_3 (System Interface)
- Verification Criteria: Verify by design/code review
- Verification Method: Code/Design Review
- Verification Owner: SW
- System Requirement State: Approved
- Primary Discipline: SW
- ASIL Rating: QM

#### TFDCX32348-80909: NVM - NVM_U2A1700_Year_3 (System Interface)
- Verification Criteria: Verify by design/code review
- Verification Method: Code/Design Review
- Verification Owner: SW
- System Requirement State: Approved
- Primary Discipline: SW
- ASIL Rating: QM

#### TFDCX32348-80910: NVM - NVM_U2A1700_Mont_3 (System Interface)
- Verification Criteria: Verify by design/code review
- Verification Method: Code/Design Review
- Verification Owner: SW
- System Requirement State: Approved
- Primary Discipline: SW
- ASIL Rating: QM

#### TFDCX32348-80911: NVM - NVM_U2A1700_Date_3 (System Interface)
- Verification Criteria: Verify by design/code review
- Verification Method: Code/Design Review
- Verification Owner: SW
- System Requirement State: Approved
- Primary Discipline: SW
- ASIL Rating: QM

#### TFDCX32348-80912: NVM - NVM_U2A1700_Hour_3 (System Interface)
- Verification Criteria: Verify by design/code review
- Verification Method: Code/Design Review
- Verification Owner: SW
- System Requirement State: Approved
- Primary Discipline: SW
- ASIL Rating: QM

#### TFDCX32348-80913: NVM - NVM_U2A1700_Min_3 (System Interface)
- Verification Criteria: Verify by design/code review
- Verification Method: Code/Design Review
- Verification Owner: SW
- System Requirement State: Approved
- Primary Discipline: SW
- ASIL Rating: QM

#### TFDCX32348-80914: NVM - NVM_U2A1700_Sec_3 (System Interface)
- Verification Criteria: Verify by design/code review
- Verification Method: Code/Design Review
- Verification Owner: SW
- System Requirement State: Approved
- Primary Discipline: SW
- ASIL Rating: QM

#### TFDCX32348-80915: NVM - NVM_U2A1700_Factor00_3 (System Interface)
- Verification Criteria: Verify by design/code review
- Verification Method: Code/Design Review
- Verification Owner: SW
- System Requirement State: Approved
- Primary Discipline: SW
- ASIL Rating: QM

#### TFDCX32348-80916: NVM - NVM_U2A1700_Factor01_3 (System Interface)
- Verification Criteria: Verify by design/code review
- Verification Method: Code/Design Review
- Verification Owner: SW
- System Requirement State: Approved
- Primary Discipline: SW
- ASIL Rating: QM

#### TFDCX32348-80917: NVM - NVM_U2A1700_Factor02_3 (System Interface)
- Verification Criteria: Verify by design/code review
- Verification Method: Code/Design Review
- Verification Owner: SW
- System Requirement State: Approved
- Primary Discipline: SW
- ASIL Rating: QM

#### TFDCX32348-80918: NVM - NVM_U2A1700_Factor04_3 (System Interface)
- Verification Criteria: Verify by design/code review
- Verification Method: Code/Design Review
- Verification Owner: SW
- System Requirement State: Approved
- Primary Discipline: SW
- ASIL Rating: QM

### TFDCX32348-10290: NVM UserDefDTC U2A1200 - (G3) CAN Excessive Wake up (Global Cause) (Heading)
- System Requirement State: Approved

#### TFDCX32348-81167: NVM - NVM_U2A1200_Snapshot (System Interface)
- Verification Criteria: Verify by design/code review
- Verification Method: Code/Design Review
- Verification Owner: SW
- System Requirement State: Approved
- Primary Discipline: SW
- ASIL Rating: QM

#### TFDCX32348-81168: NVM - NVM_U2A1200_TripCnt_1 (System Interface)
- Verification Criteria: Verify by design/code review
- Verification Method: Code/Design Review
- Verification Owner: SW
- System Requirement State: Approved
- Primary Discipline: SW
- ASIL Rating: QM

#### TFDCX32348-81169: NVM - NVM_U2A1200_TimeCnt_1 (System Interface)
- Verification Criteria: Verify by design/code review
- Verification Method: Code/Design Review
- Verification Owner: SW
- System Requirement State: Approved
- Primary Discipline: SW
- ASIL Rating: QM

#### TFDCX32348-81170: NVM - NVM_U2A1200_Odo_1 (System Interface)
- Verification Criteria: Verify by design/code review
- Verification Method: Code/Design Review
- Verification Owner: SW
- System Requirement State: Approved
- Primary Discipline: SW
- ASIL Rating: QM

#### TFDCX32348-81171: NVM - NVM_U2A1200_Year_1 (System Interface)
- Verification Criteria: Verify by design/code review
- Verification Method: Code/Design Review
- Verification Owner: SW
- System Requirement State: Approved
- Primary Discipline: SW
- ASIL Rating: QM

#### TFDCX32348-81172: NVM - NVM_U2A1200_Mont_1 (System Interface)
- Verification Criteria: Verify by design/code review
- Verification Method: Code/Design Review
- Verification Owner: SW
- System Requirement State: Approved
- Primary Discipline: SW
- ASIL Rating: QM

#### TFDCX32348-81173: NVM - NVM_U2A1200_Date_1 (System Interface)
- Verification Criteria: Verify by design/code review
- Verification Method: Code/Design Review
- Verification Owner: SW
- System Requirement State: Approved
- Primary Discipline: SW
- ASIL Rating: QM

#### TFDCX32348-81174: NVM - NVM_U2A1200_Hour_1 (System Interface)
- Verification Criteria: Verify by design/code review
- Verification Method: Code/Design Review
- Verification Owner: SW
- System Requirement State: Approved
- Primary Discipline: SW
- ASIL Rating: QM

#### TFDCX32348-81175: NVM - NVM_U2A1200_Min_1 (System Interface)
- Verification Criteria: Verify by design/code review
- Verification Method: Code/Design Review
- Verification Owner: SW
- System Requirement State: Approved
- Primary Discipline: SW
- ASIL Rating: QM

#### TFDCX32348-81176: NVM - NVM_U2A1200_Sec_1 (System Interface)
- Verification Criteria: Verify by design/code review
- Verification Method: Code/Design Review
- Verification Owner: SW
- System Requirement State: Approved
- Primary Discipline: SW
- ASIL Rating: QM

#### TFDCX32348-81177: NVM - NVM_U2A1200_LastNM_1[10] (System Interface)
- Verification Criteria: Verify by design/code review
- Verification Method: Code/Design Review
- Verification Owner: SW
- System Requirement State: Approved
- Primary Discipline: SW
- ASIL Rating: QM

#### TFDCX32348-81178: NVM - NVM_U2A1200_Frame_1[10][3] (System Interface)
- Verification Criteria: Verify by design/code review
- Verification Method: Code/Design Review
- Verification Owner: SW
- System Requirement State: Approved
- Primary Discipline: SW
- ASIL Rating: QM

#### TFDCX32348-81179: NVM - NVM_U2A1200_TripCnt_2 (System Interface)
- Verification Criteria: Verify by design/code review
- Verification Method: Code/Design Review
- Verification Owner: SW
- System Requirement State: Approved
- Primary Discipline: SW
- ASIL Rating: QM

#### TFDCX32348-81180: NVM - NVM_U2A1200_TimeCnt_2 (System Interface)
- Verification Criteria: Verify by design/code review
- Verification Method: Code/Design Review
- Verification Owner: SW
- System Requirement State: Approved
- Primary Discipline: SW
- ASIL Rating: QM

#### TFDCX32348-81181: NVM - NVM_U2A1200_Odo_2 (System Interface)
- Verification Criteria: Verify by design/code review
- Verification Method: Code/Design Review
- Verification Owner: SW
- System Requirement State: Approved
- Primary Discipline: SW
- ASIL Rating: QM

#### TFDCX32348-81182: NVM - NVM_U2A1200_Year_2 (System Interface)
- Verification Criteria: Verify by design/code review
- Verification Method: Code/Design Review
- Verification Owner: SW
- System Requirement State: Approved
- Primary Discipline: SW
- ASIL Rating: QM

#### TFDCX32348-81183: NVM - NVM_U2A1200_Mont_2 (System Interface)
- Verification Criteria: Verify by design/code review
- Verification Method: Code/Design Review
- Verification Owner: SW
- System Requirement State: Approved
- Primary Discipline: SW
- ASIL Rating: QM

#### TFDCX32348-81184: NVM - NVM_U2A1200_Date_2 (System Interface)
- Verification Criteria: Verify by design/code review
- Verification Method: Code/Design Review
- Verification Owner: SW
- System Requirement State: Approved
- Primary Discipline: SW
- ASIL Rating: QM

#### TFDCX32348-81185: NVM - NVM_U2A1200_Hour_2 (System Interface)
- Verification Criteria: Verify by design/code review
- Verification Method: Code/Design Review
- Verification Owner: SW
- System Requirement State: Approved
- Primary Discipline: SW
- ASIL Rating: QM

#### TFDCX32348-81186: NVM - NVM_U2A1200_Min_2 (System Interface)
- Verification Criteria: Verify by design/code review
- Verification Method: Code/Design Review
- Verification Owner: SW
- System Requirement State: Approved
- Primary Discipline: SW
- ASIL Rating: QM

#### TFDCX32348-81187: NVM - NVM_U2A1200_Sec_2 (System Interface)
- Verification Criteria: Verify by design/code review
- Verification Method: Code/Design Review
- Verification Owner: SW
- System Requirement State: Approved
- Primary Discipline: SW
- ASIL Rating: QM

#### TFDCX32348-81188: NVM - NVM_U2A1200_LastNM_2[10] (System Interface)
- Verification Criteria: Verify by design/code review
- Verification Method: Code/Design Review
- Verification Owner: SW
- System Requirement State: Approved
- Primary Discipline: SW
- ASIL Rating: QM

#### TFDCX32348-81189: NVM - NVM_U2A1200_Frame_2[10][3] (System Interface)
- Verification Criteria: Verify by design/code review
- Verification Method: Code/Design Review
- Verification Owner: SW
- System Requirement State: Approved
- Primary Discipline: SW
- ASIL Rating: QM

#### TFDCX32348-81190: NVM - NVM_U2A1200_TripCnt_3 (System Interface)
- Verification Criteria: Verify by design/code review
- Verification Method: Code/Design Review
- Verification Owner: SW
- System Requirement State: Approved
- Primary Discipline: SW
- ASIL Rating: QM

#### TFDCX32348-81191: NVM - NVM_U2A1200_TimeCnt_3 (System Interface)
- Verification Criteria: Verify by design/code review
- Verification Method: Code/Design Review
- Verification Owner: SW
- System Requirement State: Approved
- Primary Discipline: SW
- ASIL Rating: QM

#### TFDCX32348-81192: NVM - NVM_U2A1200_Odo_3 (System Interface)
- Verification Criteria: Verify by design/code review
- Verification Method: Code/Design Review
- Verification Owner: SW
- System Requirement State: Approved
- Primary Discipline: SW
- ASIL Rating: QM

#### TFDCX32348-81193: NVM - NVM_U2A1200_Year_3 (System Interface)
- Verification Criteria: Verify by design/code review
- Verification Method: Code/Design Review
- Verification Owner: SW
- System Requirement State: Approved
- Primary Discipline: SW
- ASIL Rating: QM

#### TFDCX32348-81194: NVM - NVM_U2A1200_Mont_3 (System Interface)
- Verification Criteria: Verify by design/code review
- Verification Method: Code/Design Review
- Verification Owner: SW
- System Requirement State: Approved
- Primary Discipline: SW
- ASIL Rating: QM

#### TFDCX32348-81195: NVM - NVM_U2A1200_Date_3 (System Interface)
- Verification Criteria: Verify by design/code review
- Verification Method: Code/Design Review
- Verification Owner: SW
- System Requirement State: Approved
- Primary Discipline: SW
- ASIL Rating: QM

#### TFDCX32348-81196: NVM - NVM_U2A1200_Hour_3 (System Interface)
- Verification Criteria: Verify by design/code review
- Verification Method: Code/Design Review
- Verification Owner: SW
- System Requirement State: Approved
- Primary Discipline: SW
- ASIL Rating: QM

#### TFDCX32348-81197: NVM - NVM_U2A1200_Min_3 (System Interface)
- Verification Criteria: Verify by design/code review
- Verification Method: Code/Design Review
- Verification Owner: SW
- System Requirement State: Approved
- Primary Discipline: SW
- ASIL Rating: QM

#### TFDCX32348-81198: NVM - NVM_U2A1200_Sec_3 (System Interface)
- Verification Criteria: Verify by design/code review
- Verification Method: Code/Design Review
- Verification Owner: SW
- System Requirement State: Approved
- Primary Discipline: SW
- ASIL Rating: QM

#### TFDCX32348-81199: NVM - NVM_U2A1200_LastNM_3[10] (System Interface)
- Verification Criteria: Verify by design/code review
- Verification Method: Code/Design Review
- Verification Owner: SW
- System Requirement State: Approved
- Primary Discipline: SW
- ASIL Rating: QM

#### TFDCX32348-81200: NVM - NVM_U2A1200_Frame_3[10][3] (System Interface)
- Verification Criteria: Verify by design/code review
- Verification Method: Code/Design Review
- Verification Owner: SW
- System Requirement State: Approved
- Primary Discipline: SW
- ASIL Rating: QM

### TFDCX32348-10291: NVM UserDefDTC U2A1300 - (G3) CAN Sleep NG Continued (Global Cause) (Heading)
- System Requirement State: Approved

#### TFDCX32348-81202: NVM - NVM_U2A1300_Snapshot (System Interface)
- Verification Criteria: Verify by design/code review
- Verification Method: Code/Design Review
- Verification Owner: SW
- System Requirement State: Approved
- Primary Discipline: SW
- ASIL Rating: QM

#### TFDCX32348-81203: NVM - NVM_U2A1300_TripCnt_1 (System Interface)
- Verification Criteria: Verify by design/code review
- Verification Method: Code/Design Review
- Verification Owner: SW
- System Requirement State: Approved
- Primary Discipline: SW
- ASIL Rating: QM

#### TFDCX32348-81204: NVM - NVM_U2A1300_TimeCnt_1 (System Interface)
- Verification Criteria: Verify by design/code review
- Verification Method: Code/Design Review
- Verification Owner: SW
- System Requirement State: Approved
- Primary Discipline: SW
- ASIL Rating: QM

#### TFDCX32348-81205: NVM - NVM_U2A1300_Odo_1 (System Interface)
- Verification Criteria: Verify by design/code review
- Verification Method: Code/Design Review
- Verification Owner: SW
- System Requirement State: Approved
- Primary Discipline: SW
- ASIL Rating: QM

#### TFDCX32348-81206: NVM - NVM_U2A1300_Year_1 (System Interface)
- Verification Criteria: Verify by design/code review
- Verification Method: Code/Design Review
- Verification Owner: SW
- System Requirement State: Approved
- Primary Discipline: SW
- ASIL Rating: QM

#### TFDCX32348-81207: NVM - NVM_U2A1300_Mont_1 (System Interface)
- Verification Criteria: Verify by design/code review
- Verification Method: Code/Design Review
- Verification Owner: SW
- System Requirement State: Approved
- Primary Discipline: SW
- ASIL Rating: QM

#### TFDCX32348-81208: NVM - NVM_U2A1300_Date_1 (System Interface)
- Verification Criteria: Verify by design/code review
- Verification Method: Code/Design Review
- Verification Owner: SW
- System Requirement State: Approved
- Primary Discipline: SW
- ASIL Rating: QM

#### TFDCX32348-81209: NVM - NVM_U2A1300_Hour_1 (System Interface)
- Verification Criteria: Verify by design/code review
- Verification Method: Code/Design Review
- Verification Owner: SW
- System Requirement State: Approved
- Primary Discipline: SW
- ASIL Rating: QM

#### TFDCX32348-81210: NVM - NVM_U2A1300_Min_1 (System Interface)
- Verification Criteria: Verify by design/code review
- Verification Method: Code/Design Review
- Verification Owner: SW
- System Requirement State: Approved
- Primary Discipline: SW
- ASIL Rating: QM

#### TFDCX32348-81211: NVM - NVM_U2A1300_Sec_1 (System Interface)
- Verification Criteria: Verify by design/code review
- Verification Method: Code/Design Review
- Verification Owner: SW
- System Requirement State: Approved
- Primary Discipline: SW
- ASIL Rating: QM

#### TFDCX32348-81212: NVM - NVM_U2A1300_NMFrame_1[5] (System Interface)
- Verification Criteria: Verify by design/code review
- Verification Method: Code/Design Review
- Verification Owner: SW
- System Requirement State: Approved
- Primary Discipline: SW
- ASIL Rating: QM

#### TFDCX32348-81213: NVM - NVM_U2A1300_DiagFrame_1[5] (System Interface)
- Verification Criteria: Verify by design/code review
- Verification Method: Code/Design Review
- Verification Owner: SW
- System Requirement State: Approved
- Primary Discipline: SW
- ASIL Rating: QM

#### TFDCX32348-81214: NVM - NVM_U2A1300_EventFrame_1[5] (System Interface)
- Verification Criteria: Verify by design/code review
- Verification Method: Code/Design Review
- Verification Owner: SW
- System Requirement State: Approved
- Primary Discipline: SW
- ASIL Rating: QM

#### TFDCX32348-81215: NVM - NVM_U2A1300_TripCnt_2 (System Interface)
- Verification Criteria: Verify by design/code review
- Verification Method: Code/Design Review
- Verification Owner: SW
- System Requirement State: Approved
- Primary Discipline: SW
- ASIL Rating: QM

#### TFDCX32348-81216: NVM - NVM_U2A1300_TimeCnt_2 (System Interface)
- Verification Criteria: Verify by design/code review
- Verification Method: Code/Design Review
- Verification Owner: SW
- System Requirement State: Approved
- Primary Discipline: SW
- ASIL Rating: QM

#### TFDCX32348-81217: NVM - NVM_U2A1300_Odo_2 (System Interface)
- Verification Criteria: Verify by design/code review
- Verification Method: Code/Design Review
- Verification Owner: SW
- System Requirement State: Approved
- Primary Discipline: SW
- ASIL Rating: QM

#### TFDCX32348-81218: NVM - NVM_U2A1300_Year_2 (System Interface)
- Verification Criteria: Verify by design/code review
- Verification Method: Code/Design Review
- Verification Owner: SW
- System Requirement State: Approved
- Primary Discipline: SW
- ASIL Rating: QM

#### TFDCX32348-81219: NVM - NVM_U2A1300_Mont_2 (System Interface)
- Verification Criteria: Verify by design/code review
- Verification Method: Code/Design Review
- Verification Owner: SW
- System Requirement State: Approved
- Primary Discipline: SW
- ASIL Rating: QM

#### TFDCX32348-81220: NVM - NVM_U2A1300_Date_2 (System Interface)
- Verification Criteria: Verify by design/code review
- Verification Method: Code/Design Review
- Verification Owner: SW
- System Requirement State: Approved
- Primary Discipline: SW
- ASIL Rating: QM

#### TFDCX32348-81221: NVM - NVM_U2A1300_Hour_2 (System Interface)
- Verification Criteria: Verify by design/code review
- Verification Method: Code/Design Review
- Verification Owner: SW
- System Requirement State: Approved
- Primary Discipline: SW
- ASIL Rating: QM

#### TFDCX32348-81222: NVM - NVM_U2A1300_Min_2 (System Interface)
- Verification Criteria: Verify by design/code review
- Verification Method: Code/Design Review
- Verification Owner: SW
- System Requirement State: Approved
- Primary Discipline: SW
- ASIL Rating: QM

#### TFDCX32348-81223: NVM - NVM_U2A1300_Sec_2 (System Interface)
- Verification Criteria: Verify by design/code review
- Verification Method: Code/Design Review
- Verification Owner: SW
- System Requirement State: Approved
- Primary Discipline: SW
- ASIL Rating: QM

#### TFDCX32348-81224: NVM - NVM_U2A1300_NMFrame_2[5] (System Interface)
- Verification Criteria: Verify by design/code review
- Verification Method: Code/Design Review
- Verification Owner: SW
- System Requirement State: Approved
- Primary Discipline: SW
- ASIL Rating: QM

#### TFDCX32348-81225: NVM - NVM_U2A1300_DiagFrame_2[5] (System Interface)
- Verification Criteria: Verify by design/code review
- Verification Method: Code/Design Review
- Verification Owner: SW
- System Requirement State: Approved
- Primary Discipline: SW
- ASIL Rating: QM

#### TFDCX32348-81226: NVM - NVM_U2A1300_EventFrame_2[5] (System Interface)
- Verification Criteria: Verify by design/code review
- Verification Method: Code/Design Review
- Verification Owner: SW
- System Requirement State: Approved
- Primary Discipline: SW
- ASIL Rating: QM

#### TFDCX32348-81227: NVM - NVM_U2A1300_TripCnt_3 (System Interface)
- Verification Criteria: Verify by design/code review
- Verification Method: Code/Design Review
- Verification Owner: SW
- System Requirement State: Approved
- Primary Discipline: SW
- ASIL Rating: QM

#### TFDCX32348-81228: NVM - NVM_U2A1300_TimeCnt_3 (System Interface)
- Verification Criteria: Verify by design/code review
- Verification Method: Code/Design Review
- Verification Owner: SW
- System Requirement State: Approved
- Primary Discipline: SW
- ASIL Rating: QM

#### TFDCX32348-81229: NVM - NVM_U2A1300_Odo_3 (System Interface)
- Verification Criteria: Verify by design/code review
- Verification Method: Code/Design Review
- Verification Owner: SW
- System Requirement State: Approved
- Primary Discipline: SW
- ASIL Rating: QM

#### TFDCX32348-81230: NVM - NVM_U2A1300_Year_3 (System Interface)
- Verification Criteria: Verify by design/code review
- Verification Method: Code/Design Review
- Verification Owner: SW
- System Requirement State: Approved
- Primary Discipline: SW
- ASIL Rating: QM

#### TFDCX32348-81231: NVM - NVM_U2A1300_Mont_3 (System Interface)
- Verification Criteria: Verify by design/code review
- Verification Method: Code/Design Review
- Verification Owner: SW
- System Requirement State: Approved
- Primary Discipline: SW
- ASIL Rating: QM

#### TFDCX32348-81232: NVM - NVM_U2A1300_Date_3 (System Interface)
- Verification Criteria: Verify by design/code review
- Verification Method: Code/Design Review
- Verification Owner: SW
- System Requirement State: Approved
- Primary Discipline: SW
- ASIL Rating: QM

#### TFDCX32348-81233: NVM - NVM_U2A1300_Hour_3 (System Interface)
- Verification Criteria: Verify by design/code review
- Verification Method: Code/Design Review
- Verification Owner: SW
- System Requirement State: Approved
- Primary Discipline: SW
- ASIL Rating: QM

#### TFDCX32348-81234: NVM - NVM_U2A1300_Min_3 (System Interface)
- Verification Criteria: Verify by design/code review
- Verification Method: Code/Design Review
- Verification Owner: SW
- System Requirement State: Approved
- Primary Discipline: SW
- ASIL Rating: QM

#### TFDCX32348-81235: NVM - NVM_U2A1300_Sec_3 (System Interface)
- Verification Criteria: Verify by design/code review
- Verification Method: Code/Design Review
- Verification Owner: SW
- System Requirement State: Approved
- Primary Discipline: SW
- ASIL Rating: QM

#### TFDCX32348-81236: NVM - NVM_U2A1300_NMFrame_3[5] (System Interface)
- Verification Criteria: Verify by design/code review
- Verification Method: Code/Design Review
- Verification Owner: SW
- System Requirement State: Approved
- Primary Discipline: SW
- ASIL Rating: QM

#### TFDCX32348-81237: NVM - NVM_U2A1300_DiagFrame_3[5] (System Interface)
- Verification Criteria: Verify by design/code review
- Verification Method: Code/Design Review
- Verification Owner: SW
- System Requirement State: Approved
- Primary Discipline: SW
- ASIL Rating: QM

#### TFDCX32348-81238: NVM - NVM_U2A1300_EventFrame_3[5] (System Interface)
- Verification Criteria: Verify by design/code review
- Verification Method: Code/Design Review
- Verification Owner: SW
- System Requirement State: Approved
- Primary Discipline: SW
- ASIL Rating: QM

### TFDCX32348-81257: NVM UserDefDTC U2A0000 - (E1) Cluster Excessive Wakeup (Heading)
- System Requirement State: Approved

#### TFDCX32348-81331: NVM - NVM_U2A0000_Snapshot (System Interface)
- Verification Criteria: Verify by design/code review
- Verification Method: Code/Design Review
- Verification Owner: SW
- System Requirement State: Approved
- Primary Discipline: SW
- ASIL Rating: QM

#### TFDCX32348-81332: NVM - NVM_U2A0000_TripCnt_1 (System Interface)
- Verification Criteria: Verify by design/code review
- Verification Method: Code/Design Review
- Verification Owner: SW
- System Requirement State: Approved
- Primary Discipline: SW
- ASIL Rating: QM

#### TFDCX32348-81333: NVM - NVM_U2A0000_TimeCnt_1 (System Interface)
- Verification Criteria: Verify by design/code review
- Verification Method: Code/Design Review
- Verification Owner: SW
- System Requirement State: Approved
- Primary Discipline: SW
- ASIL Rating: QM

#### TFDCX32348-81334: NVM - NVM_U2A0000_Odo_1 (System Interface)
- Verification Criteria: Verify by design/code review
- Verification Method: Code/Design Review
- Verification Owner: SW
- System Requirement State: Approved
- Primary Discipline: SW
- ASIL Rating: QM

#### TFDCX32348-81335: NVM - NVM_U2A0000_Year_1 (System Interface)
- Verification Criteria: Verify by design/code review
- Verification Method: Code/Design Review
- Verification Owner: SW
- System Requirement State: Approved
- Primary Discipline: SW
- ASIL Rating: QM

#### TFDCX32348-81336: NVM - NVM_U2A0000_Mont_1 (System Interface)
- Verification Criteria: Verify by design/code review
- Verification Method: Code/Design Review
- Verification Owner: SW
- System Requirement State: Approved
- Primary Discipline: SW
- ASIL Rating: QM

#### TFDCX32348-81337: NVM - NVM_U2A0000_Date_1 (System Interface)
- Verification Criteria: Verify by design/code review
- Verification Method: Code/Design Review
- Verification Owner: SW
- System Requirement State: Approved
- Primary Discipline: SW
- ASIL Rating: QM

#### TFDCX32348-81338: NVM - NVM_U2A0000_Hour_1 (System Interface)
- Verification Criteria: Verify by design/code review
- Verification Method: Code/Design Review
- Verification Owner: SW
- System Requirement State: Approved
- Primary Discipline: SW
- ASIL Rating: QM

#### TFDCX32348-81339: NVM - NVM_U2A0000_Min_1 (System Interface)
- Verification Criteria: Verify by design/code review
- Verification Method: Code/Design Review
- Verification Owner: SW
- System Requirement State: Approved
- Primary Discipline: SW
- ASIL Rating: QM

#### TFDCX32348-81340: NVM - NVM_U2A0000_Sec_1 (System Interface)
- Verification Criteria: Verify by design/code review
- Verification Method: Code/Design Review
- Verification Owner: SW
- System Requirement State: Approved
- Primary Discipline: SW
- ASIL Rating: QM

#### TFDCX32348-81341: NVM - NVM_U2A0000_Factor01_1 (System Interface)
- Verification Criteria: Verify by design/code review
- Verification Method: Code/Design Review
- Verification Owner: SW
- System Requirement State: Approved
- Primary Discipline: SW
- ASIL Rating: QM

#### TFDCX32348-81342: NVM - NVM_U2A0000_Factor02_1 (System Interface)
- Verification Criteria: Verify by design/code review
- Verification Method: Code/Design Review
- Verification Owner: SW
- System Requirement State: Approved
- Primary Discipline: SW
- ASIL Rating: QM

#### TFDCX32348-81343: NVM - NVM_U2A0000_Factor04_1 (System Interface)
- Verification Criteria: Verify by design/code review
- Verification Method: Code/Design Review
- Verification Owner: SW
- System Requirement State: Approved
- Primary Discipline: SW
- ASIL Rating: QM

#### TFDCX32348-81344: NVM - NVM_U2A0000_Factor05_1 (System Interface)
- Verification Criteria: Verify by design/code review
- Verification Method: Code/Design Review
- Verification Owner: SW
- System Requirement State: Approved
- Primary Discipline: SW
- ASIL Rating: QM

#### TFDCX32348-81345: NVM - NVM_U2A0000_Factor0E_1 (System Interface)
- Verification Criteria: Verify by design/code review
- Verification Method: Code/Design Review
- Verification Owner: SW
- System Requirement State: Approved
- Primary Discipline: SW
- ASIL Rating: QM

#### TFDCX32348-81346: NVM - NVM_U2A0000_TripCnt_2 (System Interface)
- Verification Criteria: Verify by design/code review
- Verification Method: Code/Design Review
- Verification Owner: SW
- System Requirement State: Approved
- Primary Discipline: SW
- ASIL Rating: QM

#### TFDCX32348-81347: NVM - NVM_U2A0000_TimeCnt_2 (System Interface)
- Verification Criteria: Verify by design/code review
- Verification Method: Code/Design Review
- Verification Owner: SW
- System Requirement State: Approved
- Primary Discipline: SW
- ASIL Rating: QM

#### TFDCX32348-81348: NVM - NVM_U2A0000_Odo_2 (System Interface)
- Verification Criteria: Verify by design/code review
- Verification Method: Code/Design Review
- Verification Owner: SW
- System Requirement State: Approved
- Primary Discipline: SW
- ASIL Rating: QM

#### TFDCX32348-81349: NVM - NVM_U2A0000_Year_2 (System Interface)
- Verification Criteria: Verify by design/code review
- Verification Method: Code/Design Review
- Verification Owner: SW
- System Requirement State: Approved
- Primary Discipline: SW
- ASIL Rating: QM

#### TFDCX32348-81350: NVM - NVM_U2A0000_Mont_2 (System Interface)
- Verification Criteria: Verify by design/code review
- Verification Method: Code/Design Review
- Verification Owner: SW
- System Requirement State: Approved
- Primary Discipline: SW
- ASIL Rating: QM

#### TFDCX32348-81351: NVM - NVM_U2A0000_Date_2 (System Interface)
- Verification Criteria: Verify by design/code review
- Verification Method: Code/Design Review
- Verification Owner: SW
- System Requirement State: Approved
- Primary Discipline: SW
- ASIL Rating: QM

#### TFDCX32348-81352: NVM - NVM_U2A0000_Hour_2 (System Interface)
- Verification Criteria: Verify by design/code review
- Verification Method: Code/Design Review
- Verification Owner: SW
- System Requirement State: Approved
- Primary Discipline: SW
- ASIL Rating: QM

#### TFDCX32348-81353: NVM - NVM_U2A0000_Min_2 (System Interface)
- Verification Criteria: Verify by design/code review
- Verification Method: Code/Design Review
- Verification Owner: SW
- System Requirement State: Approved
- Primary Discipline: SW
- ASIL Rating: QM

#### TFDCX32348-81354: NVM - NVM_U2A0000_Sec_2 (System Interface)
- Verification Criteria: Verify by design/code review
- Verification Method: Code/Design Review
- Verification Owner: SW
- System Requirement State: Approved
- Primary Discipline: SW
- ASIL Rating: QM

#### TFDCX32348-81355: NVM - NVM_U2A0000_Factor01_2 (System Interface)
- Verification Criteria: Verify by design/code review
- Verification Method: Code/Design Review
- Verification Owner: SW
- System Requirement State: Approved
- Primary Discipline: SW
- ASIL Rating: QM

#### TFDCX32348-81356: NVM - NVM_U2A0000_Factor02_2 (System Interface)
- Verification Criteria: Verify by design/code review
- Verification Method: Code/Design Review
- Verification Owner: SW
- System Requirement State: Approved
- Primary Discipline: SW
- ASIL Rating: QM

#### TFDCX32348-81357: NVM - NVM_U2A0000_Factor04_2 (System Interface)
- Verification Criteria: Verify by design/code review
- Verification Method: Code/Design Review
- Verification Owner: SW
- System Requirement State: Approved
- Primary Discipline: SW
- ASIL Rating: QM

#### TFDCX32348-81358: NVM - NVM_U2A0000_Factor05_2 (System Interface)
- Verification Criteria: Verify by design/code review
- Verification Method: Code/Design Review
- Verification Owner: SW
- System Requirement State: Approved
- Primary Discipline: SW
- ASIL Rating: QM

#### TFDCX32348-81359: NVM - NVM_U2A0000_Factor0E_2 (System Interface)
- Verification Criteria: Verify by design/code review
- Verification Method: Code/Design Review
- Verification Owner: SW
- System Requirement State: Approved
- Primary Discipline: SW
- ASIL Rating: QM

#### TFDCX32348-81360: NVM - NVM_U2A0000_TripCnt_3 (System Interface)
- Verification Criteria: Verify by design/code review
- Verification Method: Code/Design Review
- Verification Owner: SW
- System Requirement State: Approved
- Primary Discipline: SW
- ASIL Rating: QM

#### TFDCX32348-81361: NVM - NVM_U2A0000_TimeCnt_3 (System Interface)
- Verification Criteria: Verify by design/code review
- Verification Method: Code/Design Review
- Verification Owner: SW
- System Requirement State: Approved
- Primary Discipline: SW
- ASIL Rating: QM

#### TFDCX32348-81362: NVM - NVM_U2A0000_Odo_3 (System Interface)
- Verification Criteria: Verify by design/code review
- Verification Method: Code/Design Review
- Verification Owner: SW
- System Requirement State: Approved
- Primary Discipline: SW
- ASIL Rating: QM

#### TFDCX32348-81363: NVM - NVM_U2A0000_Year_3 (System Interface)
- Verification Criteria: Verify by design/code review
- Verification Method: Code/Design Review
- Verification Owner: SW
- System Requirement State: Approved
- Primary Discipline: SW
- ASIL Rating: QM

#### TFDCX32348-81364: NVM - NVM_U2A0000_Mont_3 (System Interface)
- Verification Criteria: Verify by design/code review
- Verification Method: Code/Design Review
- Verification Owner: SW
- System Requirement State: Approved
- Primary Discipline: SW
- ASIL Rating: QM

#### TFDCX32348-81365: NVM - NVM_U2A0000_Date_3 (System Interface)
- Verification Criteria: Verify by design/code review
- Verification Method: Code/Design Review
- Verification Owner: SW
- System Requirement State: Approved
- Primary Discipline: SW
- ASIL Rating: QM

#### TFDCX32348-81366: NVM - NVM_U2A0000_Hour_3 (System Interface)
- Verification Criteria: Verify by design/code review
- Verification Method: Code/Design Review
- Verification Owner: SW
- System Requirement State: Approved
- Primary Discipline: SW
- ASIL Rating: QM

#### TFDCX32348-81367: NVM - NVM_U2A0000_Min_3 (System Interface)
- Verification Criteria: Verify by design/code review
- Verification Method: Code/Design Review
- Verification Owner: SW
- System Requirement State: Approved
- Primary Discipline: SW
- ASIL Rating: QM

#### TFDCX32348-81368: NVM - NVM_U2A0000_Sec_3 (System Interface)
- Verification Criteria: Verify by design/code review
- Verification Method: Code/Design Review
- Verification Owner: SW
- System Requirement State: Approved
- Primary Discipline: SW
- ASIL Rating: QM

#### TFDCX32348-81369: NVM - NVM_U2A0000_Factor01_3 (System Interface)
- Verification Criteria: Verify by design/code review
- Verification Method: Code/Design Review
- Verification Owner: SW
- System Requirement State: Approved
- Primary Discipline: SW
- ASIL Rating: QM

#### TFDCX32348-81370: NVM - NVM_U2A0000_Factor02_3 (System Interface)
- Verification Criteria: Verify by design/code review
- Verification Method: Code/Design Review
- Verification Owner: SW
- System Requirement State: Approved
- Primary Discipline: SW
- ASIL Rating: QM

#### TFDCX32348-81371: NVM - NVM_U2A0000_Factor04_3 (System Interface)
- Verification Criteria: Verify by design/code review
- Verification Method: Code/Design Review
- Verification Owner: SW
- System Requirement State: Approved
- Primary Discipline: SW
- ASIL Rating: QM

#### TFDCX32348-81372: NVM - NVM_U2A0000_Factor05_3 (System Interface)
- Verification Criteria: Verify by design/code review
- Verification Method: Code/Design Review
- Verification Owner: SW
- System Requirement State: Approved
- Primary Discipline: SW
- ASIL Rating: QM

#### TFDCX32348-81373: NVM - NVM_U2A0000_Factor0E_3 (System Interface)
- Verification Criteria: Verify by design/code review
- Verification Method: Code/Design Review
- Verification Owner: SW
- System Requirement State: Approved
- Primary Discipline: SW
- ASIL Rating: QM

### TFDCX32348-81258: NVM UserDefDTC U2A0100 - (E2) Cluster Sleep NG Continued (Heading)
- System Requirement State: Approved

#### TFDCX32348-81374: NVM - NVM_U2A0100_Snapshot (System Interface)
- Verification Criteria: Verify by design/code review
- Verification Method: Code/Design Review
- Verification Owner: SW
- System Requirement State: Approved
- Primary Discipline: SW
- ASIL Rating: QM

#### TFDCX32348-81375: NVM - NVM_U2A0100_TripCnt_1 (System Interface)
- Verification Criteria: Verify by design/code review
- Verification Method: Code/Design Review
- Verification Owner: SW
- System Requirement State: Approved
- Primary Discipline: SW
- ASIL Rating: QM

#### TFDCX32348-81376: NVM - NVM_U2A0100_TimeCnt_1 (System Interface)
- Verification Criteria: Verify by design/code review
- Verification Method: Code/Design Review
- Verification Owner: SW
- System Requirement State: Approved
- Primary Discipline: SW
- ASIL Rating: QM

#### TFDCX32348-81377: NVM - NVM_U2A0100_Odo_1 (System Interface)
- Verification Criteria: Verify by design/code review
- Verification Method: Code/Design Review
- Verification Owner: SW
- System Requirement State: Approved
- Primary Discipline: SW
- ASIL Rating: QM

#### TFDCX32348-81378: NVM - NVM_U2A0100_Year_1 (System Interface)
- Verification Criteria: Verify by design/code review
- Verification Method: Code/Design Review
- Verification Owner: SW
- System Requirement State: Approved
- Primary Discipline: SW
- ASIL Rating: QM

#### TFDCX32348-81379: NVM - NVM_U2A0100_Mont_1 (System Interface)
- Verification Criteria: Verify by design/code review
- Verification Method: Code/Design Review
- Verification Owner: SW
- System Requirement State: Approved
- Primary Discipline: SW
- ASIL Rating: QM

#### TFDCX32348-81380: NVM - NVM_U2A0100_Date_1 (System Interface)
- Verification Criteria: Verify by design/code review
- Verification Method: Code/Design Review
- Verification Owner: SW
- System Requirement State: Approved
- Primary Discipline: SW
- ASIL Rating: QM

#### TFDCX32348-81381: NVM - NVM_U2A0100_Hour_1 (System Interface)
- Verification Criteria: Verify by design/code review
- Verification Method: Code/Design Review
- Verification Owner: SW
- System Requirement State: Approved
- Primary Discipline: SW
- ASIL Rating: QM

#### TFDCX32348-81382: NVM - NVM_U2A0100_Min_1 (System Interface)
- Verification Criteria: Verify by design/code review
- Verification Method: Code/Design Review
- Verification Owner: SW
- System Requirement State: Approved
- Primary Discipline: SW
- ASIL Rating: QM

#### TFDCX32348-81383: NVM - NVM_U2A0100_Sec_1 (System Interface)
- Verification Criteria: Verify by design/code review
- Verification Method: Code/Design Review
- Verification Owner: SW
- System Requirement State: Approved
- Primary Discipline: SW
- ASIL Rating: QM

#### TFDCX32348-81384: NVM - NVM_U2A0100_Factor09_1 (System Interface)
- Verification Criteria: Verify by design/code review
- Verification Method: Code/Design Review
- Verification Owner: SW
- System Requirement State: Approved
- Primary Discipline: SW
- ASIL Rating: QM

#### TFDCX32348-81385: NVM - NVM_U2A0100_Factor0A_1 (System Interface)
- Verification Criteria: Verify by design/code review
- Verification Method: Code/Design Review
- Verification Owner: SW
- System Requirement State: Approved
- Primary Discipline: SW
- ASIL Rating: QM

#### TFDCX32348-81386: NVM - NVM_U2A0100_Factor0C_1 (System Interface)
- Verification Criteria: Verify by design/code review
- Verification Method: Code/Design Review
- Verification Owner: SW
- System Requirement State: Approved
- Primary Discipline: SW
- ASIL Rating: QM

#### TFDCX32348-81387: NVM - NVM_U2A0100_Factor0E_1 (System Interface)
- Verification Criteria: Verify by design/code review
- Verification Method: Code/Design Review
- Verification Owner: SW
- System Requirement State: Approved
- Primary Discipline: SW
- ASIL Rating: QM

#### TFDCX32348-81388: NVM - NVM_U2A0100_TripCnt_2 (System Interface)
- Verification Criteria: Verify by design/code review
- Verification Method: Code/Design Review
- Verification Owner: SW
- System Requirement State: Approved
- Primary Discipline: SW
- ASIL Rating: QM

#### TFDCX32348-81389: NVM - NVM_U2A0100_TimeCnt_2 (System Interface)
- Verification Criteria: Verify by design/code review
- Verification Method: Code/Design Review
- Verification Owner: SW
- System Requirement State: Approved
- Primary Discipline: SW
- ASIL Rating: QM

#### TFDCX32348-81390: NVM - NVM_U2A0100_Odo_2 (System Interface)
- Verification Criteria: Verify by design/code review
- Verification Method: Code/Design Review
- Verification Owner: SW
- System Requirement State: Approved
- Primary Discipline: SW
- ASIL Rating: QM

#### TFDCX32348-81391: NVM - NVM_U2A0100_Year_2 (System Interface)
- Verification Criteria: Verify by design/code review
- Verification Method: Code/Design Review
- Verification Owner: SW
- System Requirement State: Approved
- Primary Discipline: SW
- ASIL Rating: QM

#### TFDCX32348-81392: NVM - NVM_U2A0100_Mont_2 (System Interface)
- Verification Criteria: Verify by design/code review
- Verification Method: Code/Design Review
- Verification Owner: SW
- System Requirement State: Approved
- Primary Discipline: SW
- ASIL Rating: QM

#### TFDCX32348-81393: NVM - NVM_U2A0100_Date_2 (System Interface)
- Verification Criteria: Verify by design/code review
- Verification Method: Code/Design Review
- Verification Owner: SW
- System Requirement State: Approved
- Primary Discipline: SW
- ASIL Rating: QM

#### TFDCX32348-81394: NVM - NVM_U2A0100_Hour_2 (System Interface)
- Verification Criteria: Verify by design/code review
- Verification Method: Code/Design Review
- Verification Owner: SW
- System Requirement State: Approved
- Primary Discipline: SW
- ASIL Rating: QM

#### TFDCX32348-81395: NVM - NVM_U2A0100_Min_2 (System Interface)
- Verification Criteria: Verify by design/code review
- Verification Method: Code/Design Review
- Verification Owner: SW
- System Requirement State: Approved
- Primary Discipline: SW
- ASIL Rating: QM

#### TFDCX32348-81396: NVM - NVM_U2A0100_Sec_2 (System Interface)
- Verification Criteria: Verify by design/code review
- Verification Method: Code/Design Review
- Verification Owner: SW
- System Requirement State: Approved
- Primary Discipline: SW
- ASIL Rating: QM

#### TFDCX32348-81397: NVM - NVM_U2A0100_Factor09_2 (System Interface)
- Verification Criteria: Verify by design/code review
- Verification Method: Code/Design Review
- Verification Owner: SW
- System Requirement State: Approved
- Primary Discipline: SW
- ASIL Rating: QM

#### TFDCX32348-81398: NVM - NVM_U2A0100_Factor0A_2 (System Interface)
- Verification Criteria: Verify by design/code review
- Verification Method: Code/Design Review
- Verification Owner: SW
- System Requirement State: Approved
- Primary Discipline: SW
- ASIL Rating: QM

#### TFDCX32348-81399: NVM - NVM_U2A0100_Factor0C_2 (System Interface)
- Verification Criteria: Verify by design/code review
- Verification Method: Code/Design Review
- Verification Owner: SW
- System Requirement State: Approved
- Primary Discipline: SW
- ASIL Rating: QM

#### TFDCX32348-81400: NVM - NVM_U2A0100_Factor0E_2 (System Interface)
- Verification Criteria: Verify by design/code review
- Verification Method: Code/Design Review
- Verification Owner: SW
- System Requirement State: Approved
- Primary Discipline: SW
- ASIL Rating: QM

#### TFDCX32348-81401: NVM - NVM_U2A0100_TripCnt_3 (System Interface)
- Verification Criteria: Verify by design/code review
- Verification Method: Code/Design Review
- Verification Owner: SW
- System Requirement State: Approved
- Primary Discipline: SW
- ASIL Rating: QM

#### TFDCX32348-81402: NVM - NVM_U2A0100_TimeCnt_3 (System Interface)
- Verification Criteria: Verify by design/code review
- Verification Method: Code/Design Review
- Verification Owner: SW
- System Requirement State: Approved
- Primary Discipline: SW
- ASIL Rating: QM

#### TFDCX32348-81403: NVM - NVM_U2A0100_Odo_3 (System Interface)
- Verification Criteria: Verify by design/code review
- Verification Method: Code/Design Review
- Verification Owner: SW
- System Requirement State: Approved
- Primary Discipline: SW
- ASIL Rating: QM

#### TFDCX32348-81404: NVM - NVM_U2A0100_Year_3 (System Interface)
- Verification Criteria: Verify by design/code review
- Verification Method: Code/Design Review
- Verification Owner: SW
- System Requirement State: Approved
- Primary Discipline: SW
- ASIL Rating: QM

#### TFDCX32348-81405: NVM - NVM_U2A0100_Mont_3 (System Interface)
- Verification Criteria: Verify by design/code review
- Verification Method: Code/Design Review
- Verification Owner: SW
- System Requirement State: Approved
- Primary Discipline: SW
- ASIL Rating: QM

#### TFDCX32348-81406: NVM - NVM_U2A0100_Date_3 (System Interface)
- Verification Criteria: Verify by design/code review
- Verification Method: Code/Design Review
- Verification Owner: SW
- System Requirement State: Approved
- Primary Discipline: SW
- ASIL Rating: QM

#### TFDCX32348-81407: NVM - NVM_U2A0100_Hour_3 (System Interface)
- Verification Criteria: Verify by design/code review
- Verification Method: Code/Design Review
- Verification Owner: SW
- System Requirement State: Approved
- Primary Discipline: SW
- ASIL Rating: QM

#### TFDCX32348-81408: NVM - NVM_U2A0100_Min_3 (System Interface)
- Verification Criteria: Verify by design/code review
- Verification Method: Code/Design Review
- Verification Owner: SW
- System Requirement State: Approved
- Primary Discipline: SW
- ASIL Rating: QM

#### TFDCX32348-81409: NVM - NVM_U2A0100_Sec_3 (System Interface)
- Verification Criteria: Verify by design/code review
- Verification Method: Code/Design Review
- Verification Owner: SW
- System Requirement State: Approved
- Primary Discipline: SW
- ASIL Rating: QM

#### TFDCX32348-81410: NVM - NVM_U2A0100_Factor09_3 (System Interface)
- Verification Criteria: Verify by design/code review
- Verification Method: Code/Design Review
- Verification Owner: SW
- System Requirement State: Approved
- Primary Discipline: SW
- ASIL Rating: QM

#### TFDCX32348-81411: NVM - NVM_U2A0100_Factor0A_3 (System Interface)
- Verification Criteria: Verify by design/code review
- Verification Method: Code/Design Review
- Verification Owner: SW
- System Requirement State: Approved
- Primary Discipline: SW
- ASIL Rating: QM

#### TFDCX32348-81412: NVM - NVM_U2A0100_Factor0C_3 (System Interface)
- Verification Criteria: Verify by design/code review
- Verification Method: Code/Design Review
- Verification Owner: SW
- System Requirement State: Approved
- Primary Discipline: SW
- ASIL Rating: QM

#### TFDCX32348-81413: NVM - NVM_U2A0100_Factor0E_3 (System Interface)
- Verification Criteria: Verify by design/code review
- Verification Method: Code/Design Review
- Verification Owner: SW
- System Requirement State: Approved
- Primary Discipline: SW
- ASIL Rating: QM

### TFDCX32348-81566: NVM - NVM_TimeCounter (System Interface)
- Verification Criteria: Verify by design/code review
- Verification Method: Code/Design Review
- Verification Owner: SW
- System Requirement State: Approved
- Primary Discipline: SW
- ASIL Rating: QM

### TFDCX32348-81567: NVM - NVM_TripCounter (System Interface)
- Verification Criteria: Verify by design/code review
- Verification Method: Code/Design Review
- Verification Owner: SW
- System Requirement State: Approved
- Primary Discipline: SW
- ASIL Rating: QM

## TFDCX32348-80575: MCUCONST Requirements (Heading)
- System Requirement State: Approved

### TFDCX32348-80579: MCUCONST - MCUID0432 (System Interface)
MCUCONST - MCUID0432
Meaning : Fuel Lid type
- Verification Criteria: Verify by design/code review
- Verification Method: Code/Design Review
- Verification Owner: SW
- System Requirement State: Approved
- Primary Discipline: SW
- ASIL Rating: QM

## TFDCX32348-7831: Performance Requirements (Heading)
- System Requirement State: Approved

### TFDCX32348-79942: Diag Mask Condition Processing (Heading)
- System Requirement State: Approved

#### TFDCX32348-79943: Table - Diag Mask Condition Processing (System Requirement)
Table - Diag Mask Condition Processing
[8.通信NMダイアグ仕様_ECUスリープダイアグ仕様_03.xlsx] [STD_Q&A#3246,#3247]
| # | Input |  |  |  | Output | Remarks |
| --- | --- | --- | --- | --- | --- | --- |
| # | Internal Signal - AppMode | Internal Signal - PTSysTypeFlag | CAN Signal - IGB_EIG signal status | CAN Signal - IGB_EIG | Internal Parameter - DiagMaskCondition | Remarks |
| 1 | (Initialization at wakeup or CPU reset) |  |  |  | 0 |  |
| 2 | "Normal Network Mode" | Other than { 0011b (HV) or 0100b (PHV) or 0101b (EV) or 0110b (1 motor HV) or 0111b (FCV) } | X | X | 0 | CONV |
| 3 | "Normal Network Mode" | 0011b (HV) or 0100b (PHV) or 0101b (EV) or 0110b (1 motor HV) or 0111b (FCV) | Never Received = Yes Communication Failure = No | X | 0 | HV and before 1st reception of IGB_EIG |
| 4 | "Normal Network Mode" | 0011b (HV) or 0100b (PHV) or 0101b (EV) or 0110b (1 motor HV) or 0111b (FCV) | Never Received = X Communication Failure = Yes | X | 1 | HV and communication failure of IGB_EIG |
| 5 | "Normal Network Mode" | 0011b (HV) or 0100b (PHV) or 0101b (EV) or 0110b (1 motor HV) or 0111b (FCV) | Never Received = No Communication Failure = No | 0 | 0 | HV and normal condition of IGB_EIG |
| 6 | "Normal Network Mode" | 0011b (HV) or 0100b (PHV) or 0101b (EV) or 0110b (1 motor HV) or 0111b (FCV) | Never Received = No Communication Failure = No | 1 | 1 | HV and normal condition of IGB_EIG |
| 7 | Other than "Normal Network Mode" | X | X | X | No change | CAN communication is stopped. |
(*1) (ver.2.1) SRD error fix. “Yes” → “No”
- Verification Criteria: Verify by executing test cases
- Verification Method: System Qualification Test
- Verification Owner: FV
- System Requirement State: Approved
- Primary Discipline: SW
- ASIL Rating: QM

### TFDCX32348-80132: UTC Time Information Latching (Heading)
- System Requirement State: Approved

#### TFDCX32348-80133: Table - UTC Time Information Latching (System Requirement)
Table - UTC Time Information Latching
UTC information is broadcast during IG ON. The purpose of this table is to memory the latest UTC information into backup RAM and use it during IG OFF.
| # | Input |  | Output |  |  |  |  |  |
| --- | --- | --- | --- | --- | --- | --- | --- | --- |
| # | Internal Signal - IgnMode | CAN Signal - D_YEAR signal status (*2) | Internal Parameter - UTC_Year (*1) | Internal Parameter - UTC_Mont (*1) | Internal Parameter - UTC_Date (*1) | Internal Parameter - UTC_Hour (*1) | Internal Parameter - UTC_Min (*1) | Internal Parameter - UTC_Sec (*1) |
| 1 | (Initialization at Battery connect) |  | 0xFF | 0xFF | 0xFF | 0xFF | 0xFF | 0xFF |
| 2 | (Initialization at Wakeup) |  | No change | No change | No change | No change | No change | No change |
| 3 | ON | Received and Normal | CAN Signal - D_YEAR | CAN Signal - D_MONT | CAN Signal - D_DAY | CAN Signal - D_HOUR | CAN Signal - D_MIN | CAN Signal - D_SEC |
| 4 | Other than above |  | No change | No change | No change | No change | No change | No change |
(*1) UINT8 type, and store them to backup RAM.
(*2) All the UTC CAN signals are assigned to one CAN frame. It is enough to check the signal state for just one CAN signal.
- Verification Criteria: Verify by executing test cases
- Verification Method: System Qualification Test
- Verification Owner: FV
- System Requirement State: Approved
- Primary Discipline: SW
- ASIL Rating: QM

### TFDCX32348-79963: NM Diag (Heading)
- System Requirement State: Approved

#### TFDCX32348-10293: Parameter Bit Meaning of CANWorkingReason and CANWakeupCause (Heading)
- System Requirement State: Approved

##### TFDCX32348-12467: CANWakeupReason/CANWakeupCause (Information)
CANWakeupReason/CANWakeupCause
This feature refers following parameters output from ope-mode processing to determine the factor of CAN active condition.
CANWakeupReason and CANWakeupCause have bitwise meaning as described in below table.
| # | Bit | Meaning of bit |  |
| --- | --- | --- | --- |
| # | Bit | CANWorkingReason | CANWakeupCause |
| 1 | bit 0 (0x0001) | IG ON or IG OFF delay | IG ON |
| 2 | bit 1 (0x0002) | ACC ON | CAN dominant detected |
| 3 | bit 2 (0x0004) | Required Day/Night Status | Required Day/Night Status |
| 4 | bit 3 (0x0008) | DTC logging (Required time stamp) | DTC logging (Required time stamp) |
| 5 | bit 4 (0x0010) | Rheostat changed | Rheostat changed |
| 6 | bit 5 (0x0020) | - | CXPI wake up pulse |
| 7 | bit 6 (0x0040) | Changed hazard control status | Changed hazard control status |
| 8 | bit 7 (0x0080) | Closed fuel tank warning status changed | Closed fuel tank warning status changed |
| 9 | bit 8 (0x0100) | CXPI signal change | CXPI signal change |
| 10 | bit 9 (0x0200) | - | Received CAN NM |
| 11 | bit 10 (0x0400) | TC input status change | TC input status change |
| 12 | bit 11 (0x0800) | - | - |
| 13 | bit 12 (0x1000) | - | - |
| 14 | bit 13 (0x2000) | - | - |
| 15 | bit 14 (0x4000) | - | - |
| 16 | bit 15 (0x8000) | - | - |
Note: CAN activation due to the fuel tank warning has been removed. Bit 7 (0x0080) of CANWorkingReason and CANWakeupCause are never set in ope-mode processing.
- System Requirement State: Approved

#### TFDCX32348-10295: (G1) CAN Excessive Wake up Detection (Cluster Internal Cause) (Heading)
- System Requirement State: Approved

##### TFDCX32348-12470: (G1) Summary of the Detection Logic (Heading)
- System Requirement State: Approved

###### TFDCX32348-17353: (G1) Summary of the Detection Logic (Information)
This function detects an incident that CAN communication frequently repeats sleep and wake up due to the factors of cluster internal conditions.
If the incident is detected, stores gathered information into NVM.
- System Requirement State: Approved

##### TFDCX32348-12471: (G1) Internal Parameters (Heading)
- System Requirement State: Approved

###### TFDCX32348-17355: (G1) Internal Parameters (System Requirement)
(G1) Internal Parameters
| # | Parameter Name | Type | Resolution & Unit | Storage | Usage |
| --- | --- | --- | --- | --- | --- |
| 1 | G1StartTime | Depends on implementation | - | Backup RAM | Used to hold the monitoring start date & time |
| 2 | G1CANWakeupCount | UINT8 | - | Backup RAM | Used to count the number of wake up within the monitoring period |
| 3 | G1CANWakeupCause[10] | UINT16 array | - | Backup RAM | Used to memorize the wake up trigger conditions |
| 4 | G1ElapsedTime | UINT16 | 1 sec | RAM | Elapsed time since monitoring start. Need to clip at 65535 when the calculated elapsed time exceeds 65535 sec. |
- Verification Criteria: Verify by design/code review
- Verification Method: Code/Design Review
- Verification Owner: SW
- System Requirement State: Approved
- Primary Discipline: SW
- ASIL Rating: QM

##### TFDCX32348-12473: (G1) CAN Excessive Wakeup Detection Flow (Heading)
- System Requirement State: Approved

###### TFDCX32348-17357: (G1) Detection flow (System Requirement)
(G1) Detection flow
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(T0) CPU reset start.
(T1)(T2) If cluster sleep/wake up is occurred, return to previous state and continue the processing.
(T3) Monitoring start after IG and ACC are OFF and DiagMaskCondition == 0 and battery voltage is normal.
Considering input circuit variation, error of +/-0.5V is allowed during validation.
(T4) Memorize the monitoring start time and clear the gathering information.
(T5) When CAN wake up event is detected, calculate elapsed time from last event, and transition to state (D).
(T6) If elapsed time exceeds specified time (G1_WKP_JUDGE_TIME), restart CAN excessive wake up duration.
(T7) If the wake up was not due to cluster internal cause, back to (C) for checking next CAN wake up event.
(T8) If wake up was due to cluster internal cause, increment wake up counter and memorize the wake up cause.
The wake up factor is determined based on the last 10 wake up causes. (Last 10 wake up causes are saved to G1CANWakeupCause[10] array.)
(T9) If count did not reach to the excessive wake up count (G1_WKP_BORDER_NUM), back to (C) for checking next CAN wake up event.
(T10) If count reached to the threshold of CAN excessive wake up, memorize the information into NVM, and call fn_diag_U2A1600_Detected() to memory the DTC.
(T11) Back to monitoring inactive state when IG or ACC is ON or DiagMaskCondition == 1.
(T12) After the NVM writing is completed, if (T11) condition is not satisfied and regulation related processing is not working (BatteryDrainLogicStatus == ENABLE), then force a CPU reset to recover.
(*1) Refer to TFDCX32348-10606 for CurrentTime.
(*2) Refer to TFDCX32348-12467 for bit meaning of CANWakeupCause.
(*3) Refer to TFDCX32348-79996 .
(*4) Clear all array elements.
- Verification Criteria: Verify by executing test cases
- Verification Method: System Qualification Test
- Verification Owner: FV
- System Requirement State: Approved
- Primary Discipline: SW
- ASIL Rating: QM

##### TFDCX32348-12475: (G1) Constant Parameters (Heading)
- System Requirement State: Approved

###### TFDCX32348-17359: (G1) Constants (System Requirement)
(G1) Constants
| # | Parameter Name | Resolution & Unit | Value | Description |
| --- | --- | --- | --- | --- |
| 1 | G1_WKP_JUDGE_TIME | 1 sec | 3600 sec | Monitoring duration |
| 2 | G1_WKP_BORDER_NUM | 1 time | 25 times | Number of wake up to determine excessive wake up |
- Verification Criteria: Verify by executing test cases
- Verification Method: System Qualification Test
- Verification Owner: FV
- System Requirement State: Approved
- Primary Discipline: SW
- ASIL Rating: QM

##### TFDCX32348-12477: (G1) Save Information into NVM (Heading)
- System Requirement State: Approved

###### TFDCX32348-79996: (G1) Save Information Flow (System Requirement)
(G1) Save Information Flow
This processing corresponds to the action of (T10) transition in (G1) detection flow . Refer to TFDCX32348-17357 .
When an excessive CAN wakeup is detected, the detection information is saved to NVM as snapshot data.
Three sets of the snapshot data are maintained, and the most recent three data sets are saved.
Follow the flowchart below to save the snapshot data to NVM.
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(1) Select snapshot storage set according to NVM_U2A1600_Snapshot. Refer to (*2) of the below Table-1.
(2) Write the detection information to selected data set in NVM. Refer to TFDCX32348-17360.
(3) Refer to (*3) of the below Table-1.
(4) Wait until NVM writing is completed.
Table-1
| # | Input | Output |  | Remarks |
| --- | --- | --- | --- | --- |
| # | NVM - NVM_U2A1600_Snapshot current value (*1) | Snapshot storage set selection (*2) | NVM - NVM_U2A1600_Snapshot update value (*3) | Remarks |
| 1 | 0x00 | Set 1 | 0x01 | No data set is available. Save data to set 1. |
| 2 | 0x01 | Set 2 | 0x02 | 1 data set is available. Save data to set 2. |
| 3 | 0x02 | Set 3 | 0x83 | 2 data sets are available. Save data to set 3. |
| 4 | 0x83 | Set 1 | 0x81 | 3 data sets are available. Overwrite data to set 1. |
| 5 | 0x81 | Set 2 | 0x82 | 3 data sets are available. Overwrite data to set 2. |
| 6 | 0x82 | Set 3 | 0x83 | 3 data sets are available. Overwrite data to set 3. |
(*1) This parameter is used to manage the data set to store the snapshot data. Bit7 (0x80) is used to flag that all data sets are used.
Change the value every snapshot writing : 0x00 → 0x01 → 0x02 → 0x83 → 0x81 → 0x82 → 0x83 → 0x81 → 0x82 → 0x83 …
(*2) This corresponds to box (1) of the above flowchart. Select the data set according to the NVM_U2A1600_Snapshot value.
(*3) This corresponds to box (3) of the above flowchart.
- Verification Criteria: Verify by executing test cases
- Verification Method: System Qualification Test
- Verification Owner: FV
- System Requirement State: Approved
- Primary Discipline: SW
- ASIL Rating: QM

###### TFDCX32348-17360: (G1) Save information into NVM. (System Requirement)
(G1) Save information into NVM.
This corresponds to box (2) of the flowchart (TFDCX32348-79996 )
There are 3 sets of the NVM storages to save the information. See box (1) of the flowchart (TFDCX32348-79996 ) for the destination data set.
Calculate the arithmetic OR of the values in array G1CANWakeupCause[0] through G1CANWakeupCause[9] and store the result in G1Cause before processing below table.
( G1Cause = G1CANWakeupCause[0] | G1CANWakeupCause[1] | G1CANWakeupCause[2] | … | G1CANWakeupCause[9] )
| # | Parameter | NVM Parameter (Set 1) | NVM Parameter (Set 2) | NVM Parameter (Set 3) | Type | Set Value | Remarks |
| --- | --- | --- | --- | --- | --- | --- | --- |
| 1 | Snapshot destination | NVM_U2A1600_Snapshot (Common for all sets) | NVM_U2A1600_Snapshot (Common for all sets) | NVM_U2A1600_Snapshot (Common for all sets) | UINT8 | Refer to (*3) in Table-1 of TFDCX32348-79996 | Where to store the latest snapshot |
| 2 | Trip Count | NVM_U2A1600_TripCnt_1 | NVM_U2A1600_TripCnt_2 | NVM_U2A1600_TripCnt_3 | UINT16 | NVM - NVM_TripCounter | Trip counter |
| 3 | Time Stamp | NVM_U2A1600_TimeCnt_1 | NVM_U2A1600_TimeCnt_2 | NVM_U2A1600_TimeCnt_3 | UINT32 | NVM - NVM_TimeCounter | Time counter |
| 4 | ODO | NVM_U2A1600_Odo_1 | NVM_U2A1600_Odo_2 | NVM_U2A1600_Odo_3 | UINT32 | Internal Signal - VehicleOdoInfo | ODO value |
| 5 | UTC Year | NVM_U2A1600_Year_1 | NVM_U2A1600_Year_2 | NVM_U2A1600_Year_3 | UINT8 | UTC_Year | Refer to TFDCX32348-80133. |
| 6 | UTC Month | NVM_U2A1600_Mont_1 | NVM_U2A1600_Mont_2 | NVM_U2A1600_Mont_3 | UINT8 | UTC_Mont | Refer to TFDCX32348-80133. |
| 7 | UTC Date | NVM_U2A1600_Date_1 | NVM_U2A1600_Date_2 | NVM_U2A1600_Date_3 | UINT8 | UTC_Date | Refer to TFDCX32348-80133. |
| 8 | UTC Hour | NVM_U2A1600_Hour_1 | NVM_U2A1600_Hour_2 | NVM_U2A1600_Hour_3 | UINT8 | UTC_Hour | Refer to TFDCX32348-80133. |
| 9 | UTC Minute | NVM_U2A1600_Min_1 | NVM_U2A1600_Min_2 | NVM_U2A1600_Min_3 | UINT8 | UTC_Min | Refer to TFDCX32348-80133. |
| 10 | UTC Second | NVM_U2A1600_Sec_1 | NVM_U2A1600_Sec_2 | NVM_U2A1600_Sec_3 | UINT8 | UTC_Sec | Refer to TFDCX32348-80133. |
| 11 | Factor 0x00 | NVM_U2A1600_Factor00_1 | NVM_U2A1600_Factor00_2 | NVM_U2A1600_Factor00_3 | BOOLEAN (UINT8) | If "(G1Cause & 0x0008) != 0" then 1 else 0 | DTC memory |
| 12 | Factor 0x01 | NVM_U2A1600_Factor01_1 | NVM_U2A1600_Factor01_2 | NVM_U2A1600_Factor01_3 | BOOLEAN (UINT8) | If "(G1Cause & 0x0400) != 0" then 1 else 0 | TC input status change |
| 13 | Factor 0x02 | NVM_U2A1600_Factor02_1 | NVM_U2A1600_Factor02_2 | NVM_U2A1600_Factor02_3 | BOOLEAN (UINT8) | If "(G1Cause & 0x0010) != 0" then 1 else 0 | Rheostat change |
| 14 | Factor 0x04 | NVM_U2A1600_Factor04_1 | NVM_U2A1600_Factor04_2 | NVM_U2A1600_Factor04_3 | BOOLEAN (UINT8) | If "(G1Cause & 0x0004) != 0" then 1 else 0 | Other factor (Day/Night required) |
- Verification Criteria: Verify by executing test cases
- Verification Method: System Qualification Test
- Verification Owner: FV
- System Requirement State: Approved
- Primary Discipline: SW
- ASIL Rating: QM

#### TFDCX32348-10297: (G2) CAN Sleep NG Continued Detection (Cluster Internal Cause) (Heading)
- System Requirement State: Approved

##### TFDCX32348-12479: (G2) Summary of the Detection Logic (Heading)
- System Requirement State: Approved

###### TFDCX32348-17362: (G2) Summary of the detection logic (Information)
This function detects an incident that CAN communication keeps awake after IG OFF due to factors of cluster internal conditions.
If the incident is detected, stores gathered information into NVM.
- System Requirement State: Approved

##### TFDCX32348-12481: (G2) Internal Parameters (Heading)
- System Requirement State: Approved

###### TFDCX32348-17365: (G2) Internal parameters (System Requirement)
(G2) Internal parameters
| # | Parameter Name | Type | Resolution & Unit | Storage | Usage |
| --- | --- | --- | --- | --- | --- |
| 1 | G2StartTime | Depends on implementation | - | RAM | Used to hold the monitoring start date & time |
| 2 | G2CANWorkingReason | UINT16 | - | RAM | Used to memorize the CAN working conditions |
- Verification Criteria: Verify by design/code review
- Verification Method: Code/Design Review
- Verification Owner: SW
- System Requirement State: Approved
- Primary Discipline: SW
- ASIL Rating: QM

##### TFDCX32348-12483: (G2) CAN Sleep NG Continued Detection Flow (Heading)
- System Requirement State: Approved

###### TFDCX32348-17367: (G2) Detection flow (System Requirement)
(G2) Detection flow
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(T0) CPU reset start.
(T1)(T2) If cluster sleep/wake up is occurred, return to previous state and continue the processing.
(T3) Monitoring start after IG and ACC are OFF and DiagMaskCondition == 0 and battery voltage is normal.
Considering input circuit variation, error of +/-0.5V is allowed during validation.
(T4) If CAN network is active due to cluster internal cause, start monitoring of CAN sleep NG continuation.
(T5) If CAN communication exits network mode or cluster internal CAN working condition is withdrawn, back to monitoring start state (B).
(T6) If CAN network is active due to cluster internal cause, memorize the factor to G2CANWorkingReason.
(T7) if CAN active condition due to cluster internal cause continued for G2_SLP_JUDGE_TIME, it is determined as an incident of CAN sleep NG continued then save information into NVM, and call fn_diag_U2A1700_Detected() to memory the DTC.
(T8) Back to monitoring inactive state when IG or ACC is ON or DiagMaskCondition == 1.
(T9) After the NVM writing is completed, if (T8) condition is not satisfied and regulation related processing is not working (BatteryDrainLogicState == ENABLE), then force a CPU reset to recover.
(*1) Refer to TFDCX32348-10606 for CurrentTime.
(*2) Refer to TFDCX32348-12467 for the bit meaning of CANWorkingReason.
(*3) Refer to TFDCX32348-80154 .
- Verification Criteria: Verify by executing test cases
- Verification Method: System Qualification Test
- Verification Owner: FV
- System Requirement State: Approved
- Primary Discipline: SW
- ASIL Rating: QM

##### TFDCX32348-12485: (G2) Constant Parameters (Heading)
- System Requirement State: Approved

###### TFDCX32348-17369: (G2) Constant (System Requirement)
(G2) Constant
| # | Parameter Name | Resolution & Unit | Value | Description |
| --- | --- | --- | --- | --- |
| 1 | G2_SLP_JUDGE_TIME | 1 sec | 3600 sec | Monitoring duration |
- Verification Criteria: Verify by executing test cases
- Verification Method: System Qualification Test
- Verification Owner: FV
- System Requirement State: Approved
- Primary Discipline: SW
- ASIL Rating: QM

##### TFDCX32348-12487: (G2) Save Information into NVM (Heading)
- System Requirement State: Approved

###### TFDCX32348-80154: (G2) Save Information Flow (System Requirement)
(G2) Save Information Flow
This processing corresponds to the action of (T7) transition in (G2) detection flow . Refer to TFDCX32348-17367 .
When CAN communication keeps awake long time due to the cluster internal cause, the detection information is saved to NVM as snapshot data.
Three sets of the snapshot data are maintained, and the most recent three data sets are saved.
Follow the flowchart below to save the snapshot data to NVM.
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(1) Select snapshot storage set according to NVM_U2A1700_SnapShot. Refer to (*2) of the below Table-1.
(2) Write the detection information to selected data set in NVM. Refer to TFDCX32348-17371 .
(3) Refer to (*3) of the below Table-1.
(4) Wait until NVM writing is completed.
Table-1
| # | Input | Output |  | Remarks |
| --- | --- | --- | --- | --- |
| # | NVM - NVM_U2A1700_Snapshot current value (*1) | Snapshot storage set selection (*2) | NVM - NVM_U2A1700_Snapshot update value (*3) | Remarks |
| 1 | 0x00 | Set 1 | 0x01 | No data set is available. Save data to set 1. |
| 2 | 0x01 | Set 2 | 0x02 | 1 data set is available. Save data to set 2. |
| 3 | 0x02 | Set 3 | 0x83 | 2 data sets are available. Save data to set 3. |
| 4 | 0x83 | Set 1 | 0x81 | 3 data sets are available. Overwrite data to set 1. |
| 5 | 0x81 | Set 2 | 0x82 | 3 data sets are available. Overwrite data to set 2. |
| 6 | 0x82 | Set 3 | 0x83 | 3 data sets are available. Overwrite data to set 3. |
(*1) This parameter is used to manage the data set to store the snapshot data. Bit7 (0x80) is used to flag that all data sets are used.
Change the value every snapshot writing : 0x00 → 0x01 → 0x02 → 0x83 → 0x81 → 0x82 → 0x83 → 0x81 → 0x82 → 0x83 …
(*2) This corresponds to box( 1) of the above flowchart. Select the data set according to the NVM_U2A1700_Snapshot value.
(*3) This corresponds to box (3) of the above flowchart.
- Verification Criteria: Verify by executing test cases
- Verification Method: System Qualification Test
- Verification Owner: FV
- System Requirement State: Approved
- Primary Discipline: SW
- ASIL Rating: QM

###### TFDCX32348-17371: (G2) Save information into NVM (System Requirement)
(G2) Save information into NVM
This corresponds to box (2) of the flowchart (TFDCX32348-80154 ).
There are 3 sets of the NVM storages to save the information. See box (1) of the flowchart (TFDCX32348-80154 ) for the destination data set.
| # | Parameter | NVM Parameter (Set 1) | NVM Parameter (Set 2) | NVM Parameter (Set 3) | Type | Set Value | Remarks |
| --- | --- | --- | --- | --- | --- | --- | --- |
| 1 | Snapshot destination | NVM_U2A1700_Snapshot (Common for all sets) | NVM_U2A1700_Snapshot (Common for all sets) | NVM_U2A1700_Snapshot (Common for all sets) | UINT8 | Refer to (*3) in Table-1 of TFDCX32348-80154 | Where to store the latest snapshot |
| 2 | Trip Count | NVM_U2A1700_TripCnt_1 | NVM_U2A1700_TripCnt_2 | NVM_U2A1700_TripCnt_3 | UINT16 | NVM - NVM_TripCounter | Trip counter |
| 3 | Time Stamp | NVM_U2A1700_TimeCnt_1 | NVM_U2A1700_TimeCnt_2 | NVM_U2A1700_TimeCnt_3 | UINT32 | NVM - NVM_TimeCounter | Time counter |
| 4 | ODO | NVM_U2A1700_Odo_1 | NVM_U2A1700_Odo_2 | NVM_U2A1700_Odo_3 | UINT32 | Internal Signal - VehicleOdoInfo | ODO value |
| 5 | UTC Year | NVM_U2A1700_Year_1 | NVM_U2A1700_Year_2 | NVM_U2A1700_Year_3 | UINT8 | UTC_Year | Refer to TFDCX32348-80133 . |
| 6 | UTC Month | NVM_U2A1700_Mont_1 | NVM_U2A1700_Mont_2 | NVM_U2A1700_Mont_3 | UINT8 | UTC_Mont | Refer to TFDCX32348-80133 . |
| 7 | UTC Date | NVM_U2A1700_Date_1 | NVM_U2A1700_Date_2 | NVM_U2A1700_Date_3 | UINT8 | UTC_Date | Refer to TFDCX32348-80133 . |
| 8 | UTC Hour | NVM_U2A1700_Hour_1 | NVM_U2A1700_Hour_2 | NVM_U2A1700_Hour_3 | UINT8 | UTC_Hour | Refer to TFDCX32348-80133 . |
| 9 | UTC Minute | NVM_U2A1700_Min_1 | NVM_U2A1700_Min_2 | NVM_U2A1700_Min_3 | UINT8 | UTC_Min | Refer to TFDCX32348-80133 . |
| 10 | UTC Second | NVM_U2A1700_Sec_1 | NVM_U2A1700_Sec_2 | NVM_U2A1700_Sec_3 | UINT8 | UTC_Sec | Refer to TFDCX32348-80133 . |
| 11 | Factor 0x00 | NVM_U2A1700_Factor00_1 | NVM_U2A1700_Factor00_2 | NVM_U2A1700_Factor00_3 | BOOLEAN (UINT8) | If "(G2CANWorkingReason & 0x0008) != 0" then 1 else 0 | DTC memory |
| 12 | Factor 0x01 | NVM_U2A1700_Factor01_1 | NVM_U2A1700_Factor01_2 | NVM_U2A1700_Factor01_3 | BOOLEAN (UINT8) | If "(G2CANWorkingReason & 0x0400) != 0" then 1 else 0 | TC input status change |
| 13 | Factor 0x02 | NVM_U2A1700_Factor02_1 | NVM_U2A1700_Factor02_2 | NVM_U2A1700_Factor02_3 | BOOLEAN (UINT8) | If "(G2CANWorkingReason & 0x0010) != 0" then 1 else 0 | Rheostat change |
| 14 | Factor 0x04 | NVM_U2A1700_Factor04_1 | NVM_U2A1700_Factor04_2 | NVM_U2A1700_Factor04_3 | BOOLEAN (UINT8) | If "(G2CANWorkingReason & 0x0004) != 0" then 1 else 0 | Other factor (Day/Night required) |
- Verification Criteria: Verify by executing test cases
- Verification Method: System Qualification Test
- Verification Owner: FV
- System Requirement State: Approved
- Primary Discipline: SW
- ASIL Rating: QM

#### TFDCX32348-10299: (L1) CXPI Excessive Wake up Detection (Dropped) (Heading)
- System Requirement State: Rejected

##### TFDCX32348-12488: (L1) Summary of the Detection Logic (Dropped) (Heading)
- System Requirement State: Rejected

###### TFDCX32348-17373: (L1) Summary of the detection logic (Dropped) (Information)
This function detects an incident that CAN communication frequently repeats sleep and wake up triggered by CXPI.
If the incident is detected, stores gathered information into NVM.
- System Requirement State: Rejected

##### TFDCX32348-12490: (L1) Internal Parameters (Dropped) (Heading)
- System Requirement State: Rejected

###### TFDCX32348-17375: (L1) Internal parameters (Dropped) (System Requirement)
(L1) Internal parameters (Dropped)
| # | Parameter Name | Type | Resolution & Unit | Storage | Usage |
| --- | --- | --- | --- | --- | --- |
| 1 | L1StartTime | Depends on implementation | - | Backup RAM | Used to hold the monitoring start date & time |
| 2 | L1WakeupCntSWS | UINT8 | 1 time | Backup RAM | Used to count wake up times requested from SWS ECU. |
| 3 | L1WakeupCntCMB | UINT8 | 1 time | Backup RAM | Used to count wake up times requested from CMB ECU. |
| 4 | L1WakeupCntUNKNOWN | UINT8 | 1 time | Backup RAM | Used to count wake up times potential due to noise. |
| 5 | L1ElaspedTime | UINT16 | 1 sec | RAM | Elapsed time ssince monitoring start. Need to clip at 65535 when the calculated elapsed time exceeds 65535 sec. |
- Verification Criteria: Verify by design/code review
- Verification Method: Code/Design Review
- Verification Owner: SW
- System Requirement State: Rejected
- Primary Discipline: SW
- ASIL Rating: QM

##### TFDCX32348-12492: (L1) CXPI Excessive Wake up Detection Flow (Dropped) (Heading)
- System Requirement State: Rejected

###### TFDCX32348-17377: (L1) Detection flow (Dropped) (System Requirement)
(L1) Detection flow (Dropped)
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(T0) CPU reset start.
(T1)(T2) If cluster sleep/wake up is occurred, return to previous state and continue the processing.
(T3) Monitoring start after IG and ACC are OFF if battery voltage is normal.
(ver. 1.1c) Considering input circuit variation, error of +/-0.5V is allowed during validation.
(T4) Start CXPI excessive wake up detection immediately.
(T5) When CAN communication status changed to network mode, calculate elapsed time from monitoring start and transition to next state (D).
(T6) If elapsed time exceeds monitoring duration, back to state (B) to restart monitoring duration.
(T7) If CAN wake up cause was not due to CXPI, transition to state (C) to continue monitoring.
(T8) If CAN wake up cause was due to CXPI, transition to state (E) to check the CXPI wake up requester.
(T9) If CXPI wake up was triggered by CMB ECU, increment L1WakeupCntCMB.
(T10) If CXPI wake up was triggered by SWS ECU, increment L1WakeupCntSWS.
(T11) If CXPI wake up trigger was not found, increment L1WakeupCntUNKNOWN. It is considered as wake up by noise.
(T12) If all wake up counters have not reached to L1_WKP_BORDER_NUM, transition to state (C) to continue monitoring.
(T13) If any of the wake up counter has reached to L1_WKP_BORDER_NUM, it is judged as CXPI excessive wake up then save information into NVM.
(*1) Refer to for CurrentTime.
(*2) Refer to for the bit meaning of CANWakeupCause.
(*3) Refer to CXPI Summary Sheet (Embedded object) for CXPI frame PID and refer to Frame information byte input for Wakeup.ind.
(*4) Refer to .
- Verification Criteria: Verify by executing test cases
- Verification Method: System Qualification Test
- Verification Owner: FV
- System Requirement State: Rejected
- Primary Discipline: SW
- ASIL Rating: QM

##### TFDCX32348-12494: (L1) Constant Parameters (Dropped) (Heading)
- System Requirement State: Rejected

###### TFDCX32348-17379: (L1) Constants (Dropped) (System Requirement)
(L1) Constants (Dropped)
| # | Parameter Name | Resolution & Unit | Value | Description |
| --- | --- | --- | --- | --- |
| 1 | L1_WKP_JUDGE_TIME | 1 sec | 3600 sec | Monitoring duration |
| 2 | L1_WKP_BORDER_NUM | 1 time | 30 times | Number of wake up to determine excessive wake up |
- Verification Criteria: Verify by executing test cases
- Verification Method: System Qualification Test
- Verification Owner: FV
- System Requirement State: Rejected
- Primary Discipline: SW
- ASIL Rating: QM

##### TFDCX32348-12497: (L1) Save Information into NVM (Dropped) (Heading)
- System Requirement State: Rejected

###### TFDCX32348-17381: (L1) Save information into NVM (Dropped) (System Requirement)
(L1) Save information into NVM (Dropped)
When the incident is detected (refer to T13 of ), save the information into NVM.
There are 2 sets of NVM storages to save the information. If set 1 is empty (all data == 0), store the information into NVM set 1.
If NVM set 1 is not emply, save the information into NVM set 2 even if NVM set 2 is not empty. (i.e. save the information into set 1 -> set 2 -> set 2 -> set 2 .....)
Wait 5seconds before storing data into NVM to wait CAN reception of TRIP_CNT/TIME_CNT. After 5 seconds waiting, no need to check CAN reception status of TRIP_CNT/TIME_CNT. If it is not received, store default value of TRP_CNT/TIME_CNT.
(Added this comment based on impediment 1870370)
| # | Parameter | NVM Parameter |  | Type | Set Value | Remarks |
| --- | --- | --- | --- | --- | --- | --- |
| # | Parameter | Set 1 | Set 2 | Type | Set Value | Remarks |
| 1 | RoB Code | NVM_Rob_F003 |  | BOOLEAN (UINT8) | 1 | Common for set1/2 |
| 2 | Trip Count | NVM_F003_TripCnt_1 | NVM_F003_TripCnt_2 | UINT16 | CAN Signal - TRIP_CNT |  |
| 3 | Time Stamp | NVM_F003_TimeCnt_1 | NVM_F003_TimeCnt_2 | UINT32 | CAN Signal - TIME_CNT |  |
| 4 | ODO Unit | NVM_F003_OdoUint_1 | NVM_F003_OdoUint_2 | UINT8 | Internal Signal - CL_ODO_UNIT CAN Signal - ODO_UNIT | km/mile Memorize the value cluster is sending. |
| 5 | ODO | NVM_F003_Odo_1 | NVM_F003_Odo_2 | UINT32 | HMI - HMI_TOTAL_ODO_VALUE CAN Signal - ODO | ODO value Memorize the value cluster is sending. |
| 6 | Factor 0x00 | NVM_F003_Factor00_1 | NVM_F003_Factor00_2 | BOOLEAN (UINT8) | If "L1WakeupCntUNKNOWN >= L_WKP_BORDER_NUM" then 1 else 0 | Potential noise. |
| 7 | Factor 0x20 | NVM_F003_Factor20_1 | NVM_F003_Factor20_2 | BOOLEAN (UINT8) | If "L1WakeupCntSWS >= L_WKP_BORDER_NUM" then 1 else 0 | Wake up requested by SWS ECU. |
| 8 | Factor 0x21 | NVM_F003_Factor21_1 | NVM_F003_Factor21_2 | BOOLEAN (UINT8) | If "L1WakeupCntCMB >= L_WKP_BORDER_NUM" then 1 else 0 | Wake up requested by CMB ECU. |
- Verification Criteria: Verify by executing test cases
- Verification Method: System Qualification Test
- Verification Owner: FV
- System Requirement State: Rejected
- Primary Discipline: SW
- ASIL Rating: QM

#### TFDCX32348-10300: (G3) CAN Excessive Wakeup Detection (Global Cause) (Heading)
- System Requirement State: Approved

##### TFDCX32348-12499: (G3) Summary of the Detection Logic (Heading)
- System Requirement State: Approved

###### TFDCX32348-17383: (G3) Summary of the detection logic (Information)
This function detects an incident that CAN communication frequently repeats sleep and wake up after IG OFF.
If the incident is detected, stores gathered information into NVM.
- System Requirement State: Approved

##### TFDCX32348-12501: (G3) Internal Parameters (Heading)
- System Requirement State: Approved

###### TFDCX32348-17385: (G3) Internal parameters (System Requirement)
(G3) Internal parameters
| # | Parameter Name | Type | Resolution & Unit | Storage | Usage |
| --- | --- | --- | --- | --- | --- |
| 1 | G3StartTime | Depends on implementation | - | Backup RAM | Used to hold the monitoring start date & time |
| 2 | G3TermStartTime | Depends on implementation | - | Backup RAM | Used to hold data & time of last CAN wake up |
| 3 | G3CANWakeupCnt | UINT8 | 1 | Backup RAM | Used to count the number of wake up within the monitoring period |
| 4 | G3ElapsedTime | UINT16 | 1 sec | RAM | Elapsed time ssince monitoring start. Clip at 65535 when the calculated elapsed time exceeds 65535 sec. |
| 5 | G3TermTime | UINT16 | 1 sec | RAM | Interval time between CAN wake up and last CAN wake up timing. Clip at 65535 when the calculated elapsed time exceeds 65535 sec. |
| 6 | G3InfoIndex | UINT8 | 1 | Backup RAM | Index for G3LastNM[] and G3FrameInfo[][] first dimension. |
| 7 | G3FrameIndex | UINT8 | 1 | RAM | Index for G3FrameInfo[][] second dimension. |
| 8 | G3LastNM[10] | UINT8 array | - | Backup RAM | Used to save last raceived NM ID (lower 8bit) for 10 CAN wake up after excessive CAN wake up is determined. |
| 9 | G3FrameInfo[10][3] | UINT32 array | - | Backup RAM | Used to save first raceived message IDs for 10 CAN wake up after excessive CAN wake up is determined. |
| 10 | G3NMReceived | BOOLEAN (UINT8) | - | RAM | Used to flag whether NM has already received. |
| 11 | G3DiagReceived | BOOLEAN (UINT8) | - | RAM | Used to flag whether Diag frame has already received. |
| 12 | G3ContReceived | BOOLEAN (UINT8) | - | RAM | Used to flag whether Control frame has already received. |
| 13 | G3Trip_Cnt | UINT16 | - | Backup RAM | Used to hold TripCnt when the incident is determined. |
| 14 | G3Time_Cnt | UINT32 | - | Backup RAM | Used to hold TimeCnt when the incident is determined. |
| 15 | G3OdoUnit | UINT8 | - | Backup RAM | Used to hold OdoUnit when the incident is determined. |
| 16 | G3Odo | UINT32 | - | Backup RAM | Used to hold Odo when the incident is determined. |
| 17 | G3Year | UINT8 | - | Backup RAM | Used to hold UTC information when the incident is determined. |
| 18 | G3Mont | UINT8 | - | Backup RAM | Used to hold UTC information when the incident is determined. |
| 19 | G3Day | UINT8 | - | Backup RAM | Used to hold UTC information when the incident is determined. |
| 20 | G3Hour | UINT8 | - | Backup RAM | Used to hold UTC information when the incident is determined. |
| 21 | G3Min | UINT8 | - | Backup RAM | Used to hold UTC information when the incident is determined. |
| 22 | G3Sec | UINT8 | - | Backup RAM | Used to hold UTC information when the incident is determined. |
- Verification Criteria: Verify by design/code review
- Verification Method: Code/Design Review
- Verification Owner: SW
- System Requirement State: Approved
- Primary Discipline: SW
- ASIL Rating: QM

##### TFDCX32348-12503: (G3) CAN Excessive Wake up Detection Flow (Heading)
- System Requirement State: Approved

###### TFDCX32348-17387: (G3) Detection flow (System Requirement)
(G3) Detection flow
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(T0) CPU reset start.
(T1)(T2)(T3) If cluster sleep/wake up is occurred, return to previous state and continue the processing.
(T4) Monitoring start after IG and ACC are OFF and DiagMaskCondition == 0 and battery voltage is normal.
Considering input circuit variation, error of +/-0.5V is allowed during validation.
(T5) Start CAN excessive wake up detection immediately.
(T6) When CAN communication status changed to network mode, calculate elapsed time (G3ElapsedTime) from monitoring start and elapsed time from last CAN wake up (G3TermTime), and increment CAN wake up count.
(T7) If monitoring duration and CAN wake up interval time have not reached to the limit and wake up count has not reached to threshold, transition to state (C) to check next CAN wake up event.
(T8) If monitoring duration or CAN wake up interval time exceeded specified duration, transition to state (B) to re-start monitoring duration.
(T9) If CAN wake up count reached to excessive wake up threshold within monitoring duration, it is determined an incident of CAN excessive wake up then save time information, and start information gathering.
Wait 5 seconds before capturing TRIP_CNT/TIME_CNT into internal RAM to wait CAN reception of TRIP_CNT/TIME_CNT. After 5 seconds waiting, no need to check CAN reception status of TRIP_CNT/TIME_CNT. If it is not received, store default of TRIP_CNT/TIME_CNT.
(Added a comment based on impediment 1870370)
(T10) Cancel monitoring if IG or ACC is ON or DiagMaskCondition == 1.
(T11) After CAN excessive wake up is determined, gather CAN frame information for 10 sleep/wake up cycles.
(T12) When CAN communication status left network mode, memorize the NM frame ID (lower 8 bit only) into G3LastNM[].
(T13) When CAN communication status is switched to network mode, memorize the first ID that is received on NM frame, Diag frame, and Control frame.
(T14) Memorize first received NM frame CAN ID.
(T15) Memorize first received Diag frame CAN ID.
(T16) Memorize first received Control frame CAN ID.
(T17) If all CAN IDs of first NM frame, first Diag frame, and first Control frame are memorized or CAN status left network mode or elapsed G3_WKP_TERM_JUDGE time in state (H), transition to state (E).
(T18) If 10 cycle CAN sleep/wake up information gathering has completed, save information into NVM, and call fn_diag_U2A1200_Detected() to memory the DTC.
(T19) Transition to state (A) when IG or ACC is ON.
(*1) Refer to TFDCX32348-10606 for CurrentTime.
(*2) Refer to TFDCX32348-13088 for NM CAN IDs.
(*3) Refer to TFDCX32348-12132 for Diag CAN IDs. (For frames from servise tool to meter)
(*4) Targeting all CAN frame IDs except for NM frame and Diag frame.
(*5) Refer to T38XD29284-49315.
- Verification Criteria: Verify by executing test cases
- Verification Method: System Qualification Test
- Verification Owner: FV
- System Requirement State: Approved
- Primary Discipline: SW
- ASIL Rating: QM

##### TFDCX32348-12506: (G3) Constant Parameters (Heading)
- System Requirement State: Approved

###### TFDCX32348-17389: (G3) Constants (System Requirement)
(G3) Constants
| # | Parameter Name | Resolution & Unit | Value | Description |
| --- | --- | --- | --- | --- |
| 1 | G3_WKP_JUDGE_TIME | 1 sec | 3300 sec | Monitoring duration |
| 2 | G3_WKP_TERM_JUDGE_TIME | 1 sec | 240 sec | Judge monitoring duration reset time |
| 3 | G3_WKP_BORDER_NUM | 1 time | 27 times | Number of wake up to determine excessive wakeups |
- Verification Criteria: Verify by executing test cases
- Verification Method: System Qualification Test
- Verification Owner: FV
- System Requirement State: Approved
- Primary Discipline: SW
- ASIL Rating: QM

##### TFDCX32348-12508: (G3) Save Information into NVM (Heading)
- System Requirement State: Approved

###### TFDCX32348-80200: (G3) Save Information Flow (System Requirement)
(G3) Save Information Flow
This processing corresponds to the action of (T18) transition in (G3) detection flow . Refer to TFDCX32348-17387 .
When an excessive CAN wakeup is detected, the detection information is saved to NVM as snapshot data.
Three sets of the snapshot data are maintained, and the most recent three data sets are saved.
Follow the flowchart below to save the snapshot data to NVM.
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(1) Select snapshot storage set according to NVM_U2A1200_Snapshot. Refer to (*2) of the below Table-1.
(2) Write the detection information to selected data set in NVM. Refer to TFDCX32348-17391 .
(3) Refer to (*3) of the below Table-1.
(4) Wait until NVM writing is completed.
Table-1
| # | Input | Output |  | Remarks |
| --- | --- | --- | --- | --- |
| # | NVM - NVM_U2A1200_Snapshot current value (*1) | Snapshot storage set selection (*2) | NVM - NVM_U2A1200_Snapshot update value (*3) | Remarks |
| 1 | 0x00 | Set 1 | 0x01 | No data set is available. Save data to set 1. |
| 2 | 0x01 | Set 2 | 0x02 | 1 data set is available. Save data to set 2. |
| 3 | 0x02 | Set 3 | 0x83 | 2 data sets are available. Save data to set 3. |
| 4 | 0x83 | Set 1 | 0x81 | 3 data sets are available. Overwrite data to set 1. |
| 5 | 0x81 | Set 2 | 0x82 | 3 data sets are available. Overwrite data to set 2. |
| 6 | 0x82 | Set 3 | 0x83 | 3 data sets are available. Overwrite data to set 3. |
(*1) This parameter is used to manage the data set to store the snapshot data. Bit7 (0x80) is used to flag that all data sets are used.
Change the value every snapshot writing : 0x00 → 0x01 → 0x02 → 0x83 → 0x81 → 0x82 → 0x83 → 0x81 → 0x82 → 0x83 …
(*2) This corresponds to box (1) of the above flowchart. Select the data set according to the NVM_U2A1200_Snapshot value.
(*3) This corresponds to box (3) of the above flowchart.
- Verification Criteria: Verify by executing test cases
- Verification Method: System Qualification Test
- Verification Owner: FV
- System Requirement State: Approved
- Primary Discipline: SW
- ASIL Rating: QM

###### TFDCX32348-17391: (G3) Save information into NVM (System Requirement)
(G3) Save information into NVM
This corresponds to box (2) of the flowchart (TFDCX32348-80200 )
There are 3 sets of the NVM storages to save the information. See box (1) of the flowchart (TFDCX32348-80200 ) for the destination data set.
| # | Parameter | NVM Parameter (Set 1) | NVM Parameter (Set 2) | NVM Parameter (Set 3) | Type | Set Value | Remarks |
| --- | --- | --- | --- | --- | --- | --- | --- |
| 1 | Snapshot destination | NVM_U2A1200_Snapshot (Common for all sets) | NVM_U2A1200_Snapshot (Common for all sets) | NVM_U2A1200_Snapshot (Common for all sets) | UINT8 | Refer to (*3) in Table-1 of TFDCX32348-80200 | Where to store the latest snapshot |
| 2 | Trip Count | NVM_U2A1200_TripCnt_1 | NVM_U2A1200_TripCnt_2 | NVM_U2A1200_TripCnt_3 | UINT16 | G3Trip_Cnt | Trip counter |
| 3 | Time Stamp | NVM_U2A1200_TimeCnt_1 | NVM_U2A1200_TimeCnt_2 | NVM_U2A1200_TimeCnt_3 | UINT32 | G3Time_Cnt | Time counter |
| 4 | ODO | NVM_U2A1200_Odo_1 | NVM_U2A1200_Odo_2 | NVM_U2A1200_Odo_3 | UINT32 | G3Odo | ODO value |
| 5 | UTC Year | NVM_U2A1200_Year_1 | NVM_U2A1200_Year_2 | NVM_U2A1200_Year_3 | UINT8 | G3Year |  |
| 6 | UTC Month | NVM_U2A1200_Mont_1 | NVM_U2A1200_Mont_2 | NVM_U2A1200_Mont_3 | UINT8 | G3Mont |  |
| 7 | UTC Date | NVM_U2A1200_Date_1 | NVM_U2A1200_Date_2 | NVM_U2A1200_Date_3 | UINT8 | G3Date |  |
| 8 | UTC Hour | NVM_U2A1200_Hour_1 | NVM_U2A1200_Hour_2 | NVM_U2A1200_Hour_3 | UINT8 | G3Hour |  |
| 9 | UTC Minute | NVM_U2A1200_Min_1 | NVM_U2A1200_Min_2 | NVM_U2A1200_Min_3 | UINT8 | G3Min |  |
| 10 | UTC Second | NVM_U2A1200_Sec_1 | NVM_U2A1200_Sec_2 | NVM_U2A1200_Sec_3 | UINT8 | G3Sec |  |
| 11 | Last Received NM ID | NVM_U2A1200_LastNM_1[10] | NVM_U2A1200_LastNM_2[10] | NVM_U2A1200_LastNM_3[10] | UINT8[10] | Copy the data of G3LastNM[10] (*1) | Lower 8 bit of last received NM frame ID for 10 cycle of CAN sleeps after CAN excessive wake up is determined. |
| 12 | First Received Frames | NVM_U2A1200_Frame_1[10][3] | NVM_U2A1200_Frame_2[10][3] | NVM_U2A1200_Frame_3[10][3] | UINT32[10][3] | Copy the data of G3FrameInfo[10][3] | CAN ID first received NM, DIAG, Control CAN frame information for 10 cycle of CAN wake up after CAN excessive wake up is determined. |
(*1) (ver.2.1) SRD error fix G2LastNM → G3LastNM
- Verification Criteria: Verify by executing test cases
- Verification Method: System Qualification Test
- Verification Owner: FV
- System Requirement State: Approved
- Primary Discipline: SW
- ASIL Rating: QM

#### TFDCX32348-10302: (G4) CAN Sleep NG Continued Detection (Global Cause) (Heading)
- System Requirement State: Approved

##### TFDCX32348-12510: (G4) Summary of the Detection Logic (Heading)
- System Requirement State: Approved

###### TFDCX32348-17393: (G4) Summary of the detection logic (Information)
This function detects an incident that CAN communication keeps awake after IG OFF for specified time.
If the incident is detected, stores gathered information into NVM.
- System Requirement State: Approved

##### TFDCX32348-12512: (G4) Internal Parameters (Heading)
- System Requirement State: Approved

###### TFDCX32348-17395: (G4) Internal parameters (System Requirement)
(G4) Internal parameters
| # | Parameter Name | Type | Resolution & Unit | Storage | Usage |
| --- | --- | --- | --- | --- | --- |
| 1 | G4StartTime | Depends on implementation | - | RAM | Used to hold the monitoring start date & time |
| 2 | G4NMIndex | UINT8 | 1 | RAM | Index of G4NMFrame[]. |
| 3 | G4NMFrame[5] | UINT8 array | - | RAM | Memory lower 8 bit of NM frame ID for 5 frames received after AN sleep NG continuation determination. |
| 4 | G4DiagIndex | UINT8 | 1 | RAM | Index of G4DiagFrame[]. |
| 5 | G4DiagFrame[5] | UINT8 array | - | RAM | Memory lower 8 bit of DIAG frame ID for 5 frames received after AN sleep NG continuation determination. |
| 6 | G4EventIndex | UINT8 | 1 | RAM | Index of G4EventFrame[]. |
| 7 | G4EventFrame[5] | UINT16 array | - | RAM | Memory EVENT frame ID for 5 frames received after CAN sleep NG continuation determination. |
- Verification Criteria: Verify by design/code review
- Verification Method: Code/Design Review
- Verification Owner: SW
- System Requirement State: Approved
- Primary Discipline: SW
- ASIL Rating: QM

##### TFDCX32348-12515: (G4) CAN Sleep NG Continued Detection Flow (Heading)
- System Requirement State: Approved

###### TFDCX32348-17397: (G4) Detection flow (System Requirement)
(G4) Detection flow
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(T0) CPU reset start.
(T1)(T2) If cluster sleep/wake up is occurred, return to previous state and continue the processing.
(T3) Monitoring start after IG and ACC are OFF and DiagMaskCondition == 0 and if battery voltage is normal.
Considering input circuit variation, error of +/-0.5V is allowed during validation.
(T4) If CAN network is active, start monitoring of CAN sleep NG continuation.
(T5) If CAN communication exits network mode, back to monitoring start state (B).
(T6) Measure CAN communication active time until the time reaches G4_SLP_JUDGE_TIME.
(T7) If CAN communication active time continued G4_SLP_JUDGE_TIME, it is determined CAN sleep NG continued then start gathering CAN frame ID information.
(T8) Memorize 5 received NM frame IDs (lower 8 bit) after CAN sleep NG continued is determined.
(T9) Memorize 5 received Diag frame IDs (lower 8 bit) after CAN sleep NG continued is determined.
(T10) Memorize 5 received Event frame IDs after CAN sleep NG continued is determined.
(T11) If all CAN ID memories of NM, Diag, Event frames completed, or passed 10 seconds in state (D) or CAN communication status left network mode, save information into NVM, and call fn_diag_U2A1300_Detected() to memory the DTC.
(T12) Back to monitoring inactive state when IG of ACC is ON or DiagMaskCondition == 1.
(*1) Refer to TFDCX32348-10606 for CurrentTime.
(*2) Refer to TFDCX32348-13088 for NM CAN IDs.
(*3) Refer to TFDCX32348-12132 for Diag CAN IDs. (For frames from service tool to meter.)
(*4) Followings are the target IDs/message names of Event frame.
(ver.2.1) Updated target IDs for event frame.
$013 CGW1S11
$014 CGW1S12
$015 CGW1S13
$016 CGW1S14
$017 CGW1S15
$018 CGW1S16
$019 CGW1S17
$01A CGW1S18
$01B CGW1S21
$01C CGW1S22
$01D CGW1S23
$01E CGW1S24
$01F CGW1S25
$62C BDB1S13
$698 BDB1S22
$3D3 ENG1S28
$3D4 ECT1S80
$641 IDT1G01
$673 RSE1G80
$608 DS11S40
$620 BDB1S01
$622 BDB1S03
$623 BDB1S04
$626 BDB1S10
$629 BDB1S27
$62A BDB1S28
$62C BDB1S13
$633 IDT1S02
$638 BDB1S05
$639 BDB1F01
$63A BDB1F02
$644 BDB1S29
$654 BDB1S30
$656 BKD1S02
$65C DRR1S03
$66C DRL1S03
$678 BKD1S01
$691 ITS1S04
$6A1 DST1S02
$6AC IDT1S07
$6B0 PST1S01
$6BC PLG1G14
$6E1 TPM1S02
$6E2 TPM1S03
(*5) Refer to TFDCX32348-80207 .
- Verification Criteria: Verify by executing test cases
- Verification Method: System Qualification Test
- Verification Owner: FV
- System Requirement State: Approved
- Primary Discipline: SW
- ASIL Rating: QM

##### TFDCX32348-12517: (G4) Constant Parameters (Heading)
- System Requirement State: Approved

###### TFDCX32348-17399: (G4) Constants (System Requirement)
(G4) Constants
| # | Parameter Name | Resolution & Unit | Value | Description |
| --- | --- | --- | --- | --- |
| 1 | G4_SLP_JUDGE_TIME | 1 sec | 3300 sec | Sleep NG judge time |
- Verification Criteria: Verify by executing test cases
- Verification Method: System Qualification Test
- Verification Owner: FV
- System Requirement State: Approved
- Primary Discipline: SW
- ASIL Rating: QM

##### TFDCX32348-12519: (G4) Save Information into NVM (Heading)
- System Requirement State: Approved

###### TFDCX32348-80207: (G4) Save Information Flow (System Requirement)
(G4) Save Information Flow
This processing corresponds to the action of (T11) transition in (G2) detection flow . Refer to TFDCX32348-17397 .
When CAN communication keeps awake long time , the detection information is saved to NVM as snapshot data.
Three sets of the snapshot data are maintained, and the most recent three data sets are saved.
Follow the flowchart below to save the snapshot data to NVM.
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(1) Select snapshot storage set according to NVM_U2A1300_Snapshot. Refer to (*2) of the below Table-1.
(2) Write the detection information to selected data set in NVM. Refer to TFDCX32348-17400 .
(3) Refer to (*3) of the below Table-1.
(4) Wait until NVM writing is completed.
Table-1
| # | Input | Output |  | Remarks |
| --- | --- | --- | --- | --- |
| # | NVM - NVM_U2A1300_Snapshot current value (*1) | Snapshot storage set selection (*2) | NVM - NVM_U2A1300_Snapshot update value (*3) | Remarks |
| 1 | 0x00 | Set 1 | 0x01 | No data set is available. Save data to set 1. |
| 2 | 0x01 | Set 2 | 0x02 | 1 data set is available. Save data to set 2. |
| 3 | 0x02 | Set 3 | 0x83 | 2 data sets are available. Save data to set 3. |
| 4 | 0x83 | Set 1 | 0x81 | 3 data sets are available. Overwrite data to set 1. |
| 5 | 0x81 | Set 2 | 0x82 | 3 data sets are available. Overwrite data to set 2. |
| 6 | 0x82 | Set 3 | 0x83 | 3 data sets are available. Overwrite data to set 3. |
(*1) This parameter is used to manage the data set to store the snapshot data. Bit7 (0x80) is used to flag that all data sets are used.
Change the value every snapshot writing : 0x00 → 0x01 → 0x02 → 0x83 → 0x81 → 0x82 → 0x83 → 0x81 → 0x82 → 0x83 …
(*2) This corresponds to box( 1) of the above flowchart. Select the data set according to the NVM_U2A1300_Snapshot value.
(*3) This corresponds to box (3) of the above flowchart.
- Verification Criteria: Verify by executing test cases
- Verification Method: System Qualification Test
- Verification Owner: FV
- System Requirement State: Approved
- Primary Discipline: SW
- ASIL Rating: QM

###### TFDCX32348-17400: (G4) Save information into NVM (System Requirement)
(G4) Save information into NVM
This corresponds to box (2) of the flowchart ()
There are 3 sets of the NVM storages to save the information. See box (1) of the flowchart () for the destination data set.
| # | Parameter | NVM Parameter (Set 1) | NVM Parameter (Set 2) | NVM Parameter (Set 3) | Type | Set Value | Remarks |
| --- | --- | --- | --- | --- | --- | --- | --- |
| 1 | Snapshot destination | NVM_U2A1300_SnapShot (Common for all sets) | NVM_U2A1300_SnapShot (Common for all sets) | NVM_U2A1300_SnapShot (Common for all sets) | UINT8 | Refer to (*3) in Table-1 of TFDCX32348-80207 | Where to store the latest snapshot |
| 2 | Trip Count | NVM_U2A1300_TripCnt_1 | NVM_U2A1300_TripCnt_2 | NVM_U2A1300_TripCnt_3 | UINT16 | NVM - NVM_TripCounter |  |
| 3 | Time Stamp | NVM_U2A1300_TimeCnt_1 | NVM_U2A1300_TimeCnt_2 | NVM_U2A1300_TimeCnt_3 | UINT32 | NVM - NVM_TimeCounter |  |
| 4 | ODO | NVM_U2A1300_Odo_1 | NVM_U2A1300_Odo_2 | NVM_U2A1300_Odo_3 | UINT32 | Internal Signal - VehicleOdoInfo | ODO value |
| 5 | UTC Year | NVM_U2A1300_Year_1 | NVM_U2A1300_Year_2 | NVM_U2A1300_Year_3 | UINT8 | UTC_Year | Refer to TFDCX32348-80133 . |
| 6 | UTC Month | NVM_U2A1300_Mont_1 | NVM_U2A1300_Mont_2 | NVM_U2A1300_Mont_3 | UINT8 | UTC_Mont | Refer to TFDCX32348-80133 . |
| 7 | UTC Date | NVM_U2A1300_Date_1 | NVM_U2A1300_Date_2 | NVM_U2A1300_Date_3 | UINT8 | UTC_Date | Refer to TFDCX32348-80133 . |
| 8 | UTC Hour | NVM_U2A1300_Hour_1 | NVM_U2A1300_Hour_2 | NVM_U2A1300_Hour_3 | UINT8 | UTC_Hour | Refer to TFDCX32348-80133 . |
| 9 | UTC Minute | NVM_U2A1300_Min_1 | NVM_U2A1300_Min_2 | NVM_U2A1300_Min_3 | UINT8 | UTC_Min | Refer to TFDCX32348-80133 . |
| 10 | UTC Second | NVM_U2A1300_Sec_1 | NVM_U2A1300_Sec_2 | NVM_U2A1300_Sec_3 | UINT8 | UTC_Sec | Refer to TFDCX32348-80133 . |
| 11 | Received NM Frame ID | NVM_U2A1300_NMFrame_1[5] | NVM_U2A1300_NMFrame_2[5] | NVM_U2A1300_NMFrame_3[5] | UINT8[5] | Copy the data of G4NMFrame[5] | Lower 8 bit of received NM frame ID for 5 frames after CAN sleep NG continuation determination. |
| 12 | Received DIAG Frame ID | NVM_U2A1300_DiagFrame_1[5] | NVM_U2A1300_DiagFrame_2[5] | NVM_U2A1300_DiagFrame_3[5] | UINT8[5] | Copy the data of G4DiagFrame[5] | Lower 8 bit of received DIAG frame ID for 5 frames after CAN sleep NG continuation determination. |
| 13 | Received EVENT Frame ID | NVM_U2A1300_EventFrame_1[5] | NVM_U2A1300_EventFrame_2[5] | NVM_U2A1300_EventFrame_3[5] | UINT16[5] | Copy the data of G4EventFrame[5] | Received EVENT frame ID for 5 frames after CAN sleep NG continuation determination. |
- Verification Criteria: Verify by executing test cases
- Verification Method: System Qualification Test
- Verification Owner: FV
- System Requirement State: Approved
- Primary Discipline: SW
- ASIL Rating: QM

### TFDCX32348-79964: ECU Sleep Diag (Heading)
- System Requirement State: Approved

#### TFDCX32348-80282: Parameter Bit Meaning of AppWorkingReason, ShutdownHoldReason, and ClusterWakeupCause (Heading)
- System Requirement State: Approved

##### TFDCX32348-80283 (Information)
AppWorkingReason/ShutdownHoldReason/ClusterWakeupCause
This feature refers the following parameters output from ope-mode processing to determine the factor of cluster active condition.
AppWorkingReason, ShutdownHoldReason, and ClusterWakeupCause have bitwise meaning as described in the below table.
| # | Bit | Meaning of bit |  |  |
| --- | --- | --- | --- | --- |
| # | Bit | AppWorkingReason | ShutdownHoldReason | ClusterWakeupCause |
| 1 | bit 0 (0x0001) | IG ON | - | IG ON |
| 2 | bit 1 (0x0002) | CAN is not sleep | - | CAN dominant |
| 3 | bit 2 (0x0004) | FUEL is not ready to sleep | - | LST1/LSTM input edge |
| 4 | bit 3 (0x0008) | NVM is not ready to sleep | NVM is not ready to sleep | - |
| 5 | bit 4 (0x0010) | Buzzer is not ready to sleep | Buzzer is not ready to sleep | - |
| 6 | bit 5 (0x0020) | Turn-L blinking | - | Turn-L input change |
| 7 | bit 6 (0x0040) | Turn-R blinking | - | Turn-R input change |
| 8 | bit 7 (0x0080) | TFT display | Illumination is not ready to sleep | - |
| 9 | bit 8 (0x0100) | - | CXPI communication is not ready to sleep | CXPI wakeup pulse |
| 10 | bit 9 (0x0200) | - | - | - |
| 11 | bit 10 (0x0400) | - | - | - |
| 12 | bit 11 (0x0800) | - | - | - |
| 13 | bit 12 (0x1000) | - | - | - |
| 14 | bit 13 (0x2000) | - | - | - |
| 15 | bit 14 (0x4000) | - | - | - |
| 16 | bit 15 (0x8000) | - | - | - |
- System Requirement State: Approved

#### TFDCX32348-80284: (E1) Cluster Excessive Wake up Detection (Heading)
- System Requirement State: Approved

##### TFDCX32348-80286: (E1) Summary of the Detection Logic (Heading)
- System Requirement State: Approved

###### TFDCX32348-80287: (E1) Summary of the Detection Logic (Information)
(E1) Summary of the Detection Logic
This function detects an incident that the cluster frequently repeats sleep and wake up.
If the incident is detected, stores gathered information into NVM.
- System Requirement State: Approved

##### TFDCX32348-80288: (E1) Internal Parameters (Heading)
- System Requirement State: Approved

###### TFDCX32348-80289: (E1) Internal Parameters (System Requirement)
(E1) Internal Parameters
| # | Parameter Name | Type | Resolution & Unit | Storage | Usage |
| --- | --- | --- | --- | --- | --- |
| 1 | E1StartTime | Depends on implementation | - | Backup RAM | Used to hold the monitoring start date & time |
| 2 | E1WakeupCount | UINT8 | - | Backup RAM | Used to count the number of wake up within the monitoring period |
| 3 | E1WakeupCause[10] | UINT16 array | - | Backup RAM | Used to memorize the wake up trigger conditions |
| 4 | E1ElapsedTime | UINT16 | 1 sec | RAM | Elapsed time ssince monitoring start. Need to clip at 65535 when the calculated elapsed time exceeds 65535 sec. |
- Verification Criteria: Verify by executing test cases
- Verification Method: System Qualification Test
- Verification Owner: FV
- System Requirement State: Approved
- Primary Discipline: SW
- ASIL Rating: QM

##### TFDCX32348-80290: (E1) Cluster Excessive Wakeup Detection Flow (Heading)
- System Requirement State: Approved

###### TFDCX32348-80291: (E1) Detection Flow (System Requirement)
(E1) Detection Flow
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(T0) CPU reset start.
(T1) If cluster sleep/wake up is occurred, return to previous state and continue the processing.
(T2) Monitoring start after IG and ACC are OFF and DiagMaskCondition == 0 and battery voltage is normal.
Considering input circuit variation, error of +/-0.5V is allowed during validation.
(T3) Memorize the monitoring start time and clear the gathering information.
(T4) If cluster awake time duration exceeds the monitoring period (E1_WKP_JUDGE_TIME), return to (B) and reset the monitoring period.
(T5) When cluster enters to sleep mode, transition to (D).
(T6) When cluster wakes up, calculates the elapsed time from monitoring start, counts up the wakeup counter, memorizes the wakeup factor, then transitions to (E).
The wake up factor is determined based on the last 10 wake up causes. (Last 10 wake up causes are saved to E1WakeupCause[10] array.)
(T7) If elapsed time exceeds specified time (E1_WKP_JUDGE_TIME), reset cluster excessive wake up monitoring duration.
(T8) If wakeup count did not reach to the excessive wake up count (E1_WKP_BORDER_NUM), back to (C) for checking next cluster wake up event.
(T9) if wakeup count reached to the threshold of cluster excessive wake up, memorize the information into NVM, and call fn_diag_U2A0000_Detected() to memory the DTC.
(T10) After the NVM writing is completed, if (T11) condition is not satisfied and regulation related processing is not working (BatteryDrainLogicStatus == ENABLE), then force a CPU reset to recover.
(T11) Back to monitoring inactive state when IG or ACC is ON or DiagMaskCondition == 1.
(*1) Refer to TFDCX32348-10606 for CurrentTime.
(*2) Clear all array elements.
(*2) Refer to TFDCX32348-80283 for bit meaning of ClusterWakeupCause.
(*3) Refer to TFDCX32348-80295 .
- Verification Criteria: Verify by executing test cases
- Verification Method: System Qualification Test
- Verification Owner: FV
- System Requirement State: Approved
- Primary Discipline: SW
- ASIL Rating: QM

##### TFDCX32348-80292: (E1) Constant Parameters (Heading)
- System Requirement State: Approved

###### TFDCX32348-80293: (E1) Constants (System Requirement)
(E1) Constants
| # | Parameter Name | Resolution / Unit | Value | Description |
| --- | --- | --- | --- | --- |
| 1 | E1_WKP_JUDGE_TIME | 1 sec | 4200 sec | Monitoring duration |
| 2 | E1_WKP_BORDER_NUM | 1 time | 30 | Number of wake up to determine excessive wake up |
- Verification Criteria: Verify by executing test cases
- Verification Method: System Qualification Test
- Verification Owner: FV
- System Requirement State: Approved
- Primary Discipline: SW
- ASIL Rating: QM

##### TFDCX32348-80294: (E1) Save Information into NVM (Heading)
- System Requirement State: Approved

###### TFDCX32348-80295: (E1) Save Information Flow (System Requirement)
(E1) Save Information Flow
This processing corresponds to the action of (T9) in (E1) detection flow. Refer to TFDCX32348-80291 .
When an excessive cluster wakeup is detected, the detection information is saved to NVM as snapshot data.
Three sets of the snapshot data are maintained, and the most recent three data sets are saved.
Follow the flowchart below to save the snapshot data to NVM.
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(1) Select snapshot storage set according to NVM_U2A0000_Snapshot. Refer to (*2) of the below table-1.
(2) Write the detection information to selected data set in NVM. Refer to TFDCX32348-80308 .
(3) Refer to (*3) of the below table-1.
(4) Wait until NVM writing is completed.
Table-1
| # | Input | Output |  | Remarks |
| --- | --- | --- | --- | --- |
| # | NVM - NVM_U2A0000_Snapshot current value (*1) | Snapshot storage set selection (*2) | NVM - NVM_U2A0000_Snapshot update value (*3) | Remarks |
| 1 | 0x00 | Set 1 | 0x01 | No data set is available. Save data to set 1. |
| 2 | 0x01 | Set 2 | 0x02 | 1 data set is available. Save data to set 2. |
| 3 | 0x02 | Set 3 | 0x83 | 2 data sets are available. Save data to set 3. |
| 4 | 0x83 | Set 1 | 0x81 | 3 data sets are available. Overwrite data to set 1. |
| 5 | 0x81 | Set 2 | 0x82 | 3 data sets are available. Overwrite data to set 2. |
| 6 | 0x82 | Set 3 | 0x83 | 3 data sets are available. Overwrite data to set 3. |
(*1) This parameter is used to manage the data set to store the snapshot data. Bit7 (0x80) is used to flag that all data sets are used.
Change the value every snapshot writing : 0x00 -> 0x01 -> 0x02 -> 0x83 -> 0x81 -> 0x82 -> 0x83 -> 0x81 …
(*2) This corresponds to box (1) of the above flowchart. Select the data set according to the NVM_U2A1700_Snapshot value.
(*3) This corresponds to box (3) of the above flowchart.
- Verification Criteria: Verify by executing test cases
- Verification Method: System Qualification Test
- Verification Owner: FV
- System Requirement State: Approved
- Primary Discipline: SW
- ASIL Rating: QM

###### TFDCX32348-80296: (E1) Save Information into NVM (System Requirement)
(E1) Save Information into NVM
This corresponds to box (2) of the flowchart (TFDCX32348-80295 )
There are 3 sets of the NVM storages to save the information. See box (1) of the flowchart (TFDCX32348-80295 ) for the destination data set.
Calculate the arithmetic OR of the values in array E1WakeupCause[0] through E1WakeupCause[9] and store the result in E1Cause before processing below table.
( E1Cause = E1WakeupCause[0] | E1WakeupCause[1] | E1WakeupCause[2] | … | E1WakeupCause[9] )
| # | Parameter | NVM Parameter (Set 1) | NVM Parameter (Set 2) | NVM Parameter (Set 3) | Type | Set Value | Remarks |
| --- | --- | --- | --- | --- | --- | --- | --- |
| 1 | Snapshot destination | NVM_U2A0000_SnapShot (Common for all sets) | NVM_U2A0000_SnapShot (Common for all sets) | NVM_U2A0000_SnapShot (Common for all sets) | UINT8 | Refer to (*3) in Table-1 of TFDCX32348-80295 | Where to store the latest snapshot |
| 2 | Trip Count | NVM_U2A0000_TripCnt_1 | NVM_U2A0000_TripCnt_2 | NVM_U2A0000_TripCnt_3 | UINT16 | NVM - NVM_TripCounter | Trip counter |
| 3 | Time Stamp | NVM_U2A0000_TimeCnt_1 | NVM_U2A0000_TimeCnt_2 | NVM_U2A0000_TimeCnt_3 | UINT32 | NVM - NVM_TimeCounter | Time counter |
| 4 | ODO | NVM_U2A0000_Odo_1 | NVM_U2A0000_Odo_2 | NVM_U2A0000_Odo_3 | UINT32 | Internal Signal - VehicleOdoInfo | ODO value |
| 5 | UTC Year | NVM_U2A0000_Year_1 | NVM_U2A0000_Year_2 | NVM_U2A0000_Year_3 | UINT8 | UTC_Year | Refer to TFDCX32348-80133 . |
| 6 | UTC Month | NVM_U2A0000_Mont_1 | NVM_U2A0000_Mont_2 | NVM_U2A0000_Mont_3 | UINT8 | UTC_Mont | Refer to TFDCX32348-80133 . |
| 7 | UTC Date | NVM_U2A0000_Date_1 | NVM_U2A0000_Date_2 | NVM_U2A0000_Date_3 | UINT8 | UTC_Date | Refer to TFDCX32348-80133 . |
| 8 | UTC Hour | NVM_U2A0000_Hour_1 | NVM_U2A0000_Hour_2 | NVM_U2A0000_Hour_3 | UINT8 | UTC_Hour | Refer to TFDCX32348-80133 . |
| 9 | UTC Minute | NVM_U2A0000_Min_1 | NVM_U2A0000_Min_2 | NVM_U2A0000_Min_3 | UINT8 | UTC_Min | Refer to TFDCX32348-80133 . |
| 10 | UTC Second | NVM_U2A0000_Sec_1 | NVM_U2A0000_Sec_2 | NVM_U2A0000_Sec_3 | UINT8 | UTC_Sec | Refer to TFDCX32348-80133 . |
| 11 | Factor 0x01 | NVM_U2A0000_Factor01_1 | NVM_U2A0000_Factor01_2 | NVM_U2A0000_Factor01_3 | BOOLEAN (UINT8) | If "(MCUID0432 == 1) && ((E1Cause & 0x0004) != 0)" then 1 else 0 | LSTM input edge |
| 12 | Factor 0x02 | NVM_U2A0000_Factor02_1 | NVM_U2A0000_Factor02_2 | NVM_U2A0000_Factor02_3 | BOOLEAN (UINT8) | If "(E1Cause & 0x0100) != 0" then 1 else 0 | CXPI wakeup |
| 13 | Factor 0x04 | NVM_U2A0000_Factor04_1 | NVM_U2A0000_Factor04_2 | NVM_U2A0000_Factor04_3 | BOOLEAN (UINT8) | If "(E1Cause & 0x0002) != 0" then 1 else 0 | CAN dominant |
| 14 | Factor 0x05 | NVM_U2A0000_Factor05_1 | NVM_U2A0000_Factor05_2 | NVM_U2A0000_Factor05_3 | BOOLEAN (UINT8) | If "(MCUID0432 == 2) && ((E1Cause & 0x0004) != 0)" then 1 else 0 | LST1 input edge |
| 15 | Factor 0x0E | NVM_U2A0000_Factor0E_1 | NVM_U2A0000_Factor0E_2 | NVM_U2A0000_Factor0E_3 | BOOLEAN (UINT8) | If "(E1Cause & 0x0060) != 0" then 1 else 0 | Other factor (Turn L/R) |
- Verification Criteria: Verify by executing test cases
- Verification Method: System Qualification Test
- Verification Owner: FV
- System Requirement State: Approved
- Primary Discipline: SW
- ASIL Rating: QM

#### TFDCX32348-80297: (E2) Cluster Sleep NG Continued Detection (Heading)
- System Requirement State: Approved

##### TFDCX32348-80298: (E2) Summary of the Detection Logic (Heading)
- System Requirement State: Approved

###### TFDCX32348-80299: (E2) Summary of the Detection Logic (Information)
(E2) Summary of the Detection Logic
This function detects an incident that the cluster keeps awake long time.
If the incident is detected, stores gathered information into NVM.
- System Requirement State: Approved

##### TFDCX32348-80300: (E2) Internal Parameters (Heading)
- System Requirement State: Approved

###### TFDCX32348-80301: (E2) Internal Parameters (System Requirement)
(E2) Internal Parameters
| # | Parameter Name | Type | Resolution & Unit | Storage | Usage |
| --- | --- | --- | --- | --- | --- |
| 1 | E2StartTime | Depends on implementation | - | RAM | Used to hold the monitoring start date & time |
- Verification Criteria: Verify by executing test cases
- Verification Method: System Qualification Test
- Verification Owner: FV
- System Requirement State: Approved
- Primary Discipline: SW
- ASIL Rating: QM

##### TFDCX32348-80302: (E2) Cluster Sleep NG Continued Detection Flow (Heading)
- System Requirement State: Approved

###### TFDCX32348-80303: (E2) Detection Flow (System Requirement)
(E2) Detection Flow
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(T0) CPU reset start.
(T1) If cluster sleep/wake up is occurred, return to previous state and continue the processing.
(T2) Monitoring start after IG and ACC are OFF and DiagMaskCondition == 0 and battery voltage is normal.
Considering input circuit variation, error of +/-0.5V is allowed during validation.
(T3) Memorize the monitoring start time.
(T4) Wait until the specified time (E2_SLP_JUDGE_TIME) has elapsed.
(T5) If the cluster goes to sleep and wakes up, transition to state (B). (T6) When the cluster remains up for the specified time (E2_SLP_JUDGE_TIME), an incident of the sleep NG continued is determined.
Then memorize the information into NVM, and call fn_diag_U2A0100_Detected() to memory the DTC.
(T7) After the NVM writing is completed, if (T8) condition is not satisfied and regulation related processing is not working (BatteryDrainLogicState == ENABLE), then force a CPU reset to recover.
(T8) Back to monitoring inactive state when IG or ACC is ON or DiagMaskCondition == 1.
(*1) Refer to TFDCX32348-10606 for CurrentTime.
(*2) Refer to TFDCX32348-80307 .
- Verification Criteria: Verify by executing test cases
- Verification Method: System Qualification Test
- Verification Owner: FV
- System Requirement State: Approved
- Primary Discipline: SW
- ASIL Rating: QM

##### TFDCX32348-80304: (E2) Constant Parameters (Heading)
- System Requirement State: Approved

###### TFDCX32348-80305: (E2) Constants (System Requirement)
(E2) Constants
| # | Parameter Name | Resolution / Unit | Value | Description |
| --- | --- | --- | --- | --- |
| 1 | E2_SLP_JUDGE_TIME | 1 sec | 4200 sec | Monitoring duration |
- Verification Criteria: Verify by executing test cases
- Verification Method: System Qualification Test
- Verification Owner: FV
- System Requirement State: Approved
- Primary Discipline: SW
- ASIL Rating: QM

##### TFDCX32348-80306: (E2) Save Information into NVM (Heading)
- System Requirement State: Approved

###### TFDCX32348-80307: (E2) Save Information Flow (System Requirement)
(E2) Save Information Flow
This processing corresponds to the action of (T7) in (E2) detection flow. Refer to TFDCX32348-80303
When sleep NG for long time is detected, the detection information is saved to NVM as snapshot data.
Three sets of the snapshot data are maintained, and the most recent three data sets are saved.
Follow the flowchart below to save the snapshot data to NVM.
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(1) Select snapshot storage set according to NVM_U2A0100_SnapShot. Refer to (*2) of the below table-1.
(2) Write the detection information to selected data set in NVM. Refer to TFDCX32348-80308 .
(3) Refer to (*3) of the below Table-1.
(4) Wait 60 seconds to complete NVM writing. Since this a function to recover sleep NG incident.
Here, do not check the NVM writing status because NVM writing may be stuck.
Table-1
| # | Input | Output |  | Remarks |
| --- | --- | --- | --- | --- |
| # | NVM - NVM_U2A0100_Snapshot current value (*1) | Snapshot storage set selection (*2) | NVM - NVM_U2A0100_Snapshot update value (*3) | Remarks |
| 1 | 0x00 | Set 1 | 0x01 | No data set is available. Save data to set 1. |
| 2 | 0x01 | Set 2 | 0x02 | 1 data set is available. Save data to set 2. |
| 3 | 0x02 | Set 3 | 0x83 | 2 data sets are available. Save data to set 3. |
| 4 | 0x83 | Set 1 | 0x81 | 3 data sets are available. Overwrite data to set 1. |
| 5 | 0x81 | Set 2 | 0x82 | 3 data sets are available. Overwrite data to set 2. |
| 6 | 0x82 | Set 3 | 0x83 | 3 data sets are available. Overwrite data to set 3. |
(*1) This parameter is used to manage the data set to store the snapshot data. Bit7 (0x80) is used to flag that all data sets are used.
Change the value every snapshot writing : 0x00 -> 0x01 -> 0x02 -> 0x83 -> 0x81 -> 0x82 -> 0x83 -> 0x81 …
(*2) This corresponds to box (1) of the above flowchart. Select the data set according to the NVM_U2A0100_Snapshot value.
(*3) This corresponds to box (3) of the above flowchart.
- Verification Criteria: Verify by executing test cases
- Verification Method: System Qualification Test
- Verification Owner: FV
- System Requirement State: Approved
- Primary Discipline: SW
- ASIL Rating: QM

###### TFDCX32348-80308: (E2) Save Information into NVM (System Requirement)
(E2) Save Information into NVM
This corresponds to box (2) of thw flowchart (TFDCX32348-80307 )
There are 3 sets of thw NVM storages to save the informaiton. See box (1) of thw flowchart (TFDCX32348-80307 ) for the destination data set.
| # | Parameter | NVM Parameter (Set 1) | NVM Parameter (Set 2) | NVM Parameter (Set 3) | Type | Set Value | Remarks |
| --- | --- | --- | --- | --- | --- | --- | --- |
| 1 | Snapshot destination | NVM_U2A0100_SnapShot (Common for all sets) | NVM_U2A0100_SnapShot (Common for all sets) | NVM_U2A0100_SnapShot (Common for all sets) | UINT8 | Refer to (*3) in Table-1 of *** | Where to store the latest snapshot |
| 2 | Trip Count | NVM_U2A0100_TripCnt_1 | NVM_U2A0100_TripCnt_2 | NVM_U2A0100_TripCnt_3 | UINT16 | NVM - NVM_TripCounter | Trip counter |
| 3 | Time Stamp | NVM_U2A0100_TimeCnt_1 | NVM_U2A0100_TimeCnt_2 | NVM_U2A0100_TimeCnt_3 | UINT32 | NVM - NVM_TimeCounter | Time counter |
| 4 | ODO | NVM_U2A0100_Odo_1 | NVM_U2A0100_Odo_2 | NVM_U2A0100_Odo_3 | UINT32 | Internal Signal - VehicleOdoInfo | ODO value |
| 5 | UTC Year | NVM_U2A0100_Year_1 | NVM_U2A0100_Year_2 | NVM_U2A0100_Year_3 | UINT8 | UTC_Year | Refer to TFDCX32348-80133 . |
| 6 | UTC Month | NVM_U2A0100_Mont_1 | NVM_U2A0100_Mont_2 | NVM_U2A0100_Mont_3 | UINT8 | UTC_Mont | Refer to TFDCX32348-80133 . |
| 7 | UTC Date | NVM_U2A0100_Date_1 | NVM_U2A0100_Date_2 | NVM_U2A0100_Date_3 | UINT8 | UTC_Date | Refer to TFDCX32348-80133 . |
| 8 | UTC Hour | NVM_U2A0100_Hour_1 | NVM_U2A0100_Hour_2 | NVM_U2A0100_Hour_3 | UINT8 | UTC_Hour | Refer to TFDCX32348-80133 . |
| 9 | UTC Minute | NVM_U2A0100_Min_1 | NVM_U2A0100_Min_2 | NVM_U2A0100_Min_3 | UINT8 | UTC_Min | Refer to TFDCX32348-80133 . |
| 10 | UTC Second | NVM_U2A0100_Sec_1 | NVM_U2A0100_Sec_2 | NVM_U2A0100_Sec_3 | UINT8 | UTC_Sec | Refer to TFDCX32348-80133 . |
| 11 | Factor 0x09 | NVM_U2A0100_Factor09_1 | NVM_U2A0100_Factor09_2 | NVM_U2A0100_Factor09_3 | BOOLEAN (UINT8) | Refer to Table-2. | CAN active |
| 12 | Factor 0x0A | NVM_U2A0100_Factor0A_1 | NVM_U2A0100_Factor0A_2 | NVM_U2A0100_Factor0A_3 | BOOLEAN (UINT8) | Refer to Table-2. | FUEL module busy |
| 13 | Factor 0x0C | NVM_U2A0100_Factor0C_1 | NVM_U2A0100_Factor0C_2 | NVM_U2A0100_Factor0C_3 | BOOLEAN (UINT8) | Refer to Table-2. | EEPROM busy |
| 14 | Factor 0x0E | NVM_U2A0100_Factor0E_1 | NVM_U2A0100_Factor0E_2 | NVM_U2A0100_Factor0E_3 | BOOLEAN (UINT8) | Refer to Table-2. | Other factor (Buzzer, TFT, CXPI) |
Table-2
| # | Input |  |  | Output |  |  |  | Remarks |
| --- | --- | --- | --- | --- | --- | --- | --- | --- |
| # | Internal Signal - App Mode | Internal Signal - AppWorkingReason (*1) | Internal Signal - ShutdownHoldReason (*1) | NVM - NVM_U2A0100_Factor09_* (*2) | NVM - NVM_U2A0100_Factor0A_* (*3) | NVM - NVM_U2A0100_Factor0C_* (*4) | NVM - NVM_U2A0100_Factor0E_* (*5) | Remarks |
| 1 | "Normal Newtork Mode" or "Normal Standalone Mode" | 0x0002 | X | 1 | 0 | 0 | 0 | CAN active |
| 2 | "Normal Newtork Mode" or "Normal Standalone Mode" | 0x0004 | X | 0 | 1 | 0 | 0 | FUEL module busy |
| 3 | "Normal Newtork Mode" or "Normal Standalone Mode" | 0x0008 | X | 0 | 0 | 1 | 0 | NVN busy |
| 4 | "Normal Newtork Mode" or "Normal Standalone Mode" | 0x0010 or 0x0020 or 0x0040 or 0x0080 | X | 0 | 0 | 0 | 1 | Other (Buzzer, TurnL/R, TFT) |
| 5 | "Sleep Mode" | X | 0x0008 | 0 | 0 | 1 | 0 | NVM busy |
| 6 | "Sleep Mode" | X | 0x0010 or 0x0080 or 0x0100 | 0 | 0 | 0 | 1 | Other (Buzzer, TFT, CXPI) |
| 7 | Other than above |  |  | 0 | 0 | 0 | 0 | Unknown |
(*1) Refer to TFDCX32348-80283 for the value meaning of AppWorkingReason/ShutdownHoldReason.
(*2) NVM_U2A0100_Factor09_1 or NVM_U2A0100_Factor09_2 or NVM_U2A0100_Factor09_3 according to storage set selection.
(*3) NVM_U2A0100_Factor0A_1 or NVM_U2A0100_Factor0A_2 or NVM_U2A0100_Factor0A_3 according to storage set selection.
(*4) NVM_U2A0100_Factor0C_1 or NVM_U2A0100_Factor0C_2 or NVM_U2A0100_Factor0C_3 according to storage set selection.
(*5) NVM_U2A0100_Factor0E_1 or NVM_U2A0100_Factor0E_2 or NVM_U2A0100_Factor0E_3 according to storage set selection.
Refer to TFDCX32348-80307 for the storage set selection.
- Verification Criteria: Verify by executing test cases
- Verification Method: System Qualification Test
- Verification Owner: FV
- System Requirement State: Approved
- Primary Discipline: SW
- ASIL Rating: QM

### TFDCX32348-10304: RoB Data Clear (Heading)
- System Requirement State: Approved

#### TFDCX32348-12522: RoB data clear (System Requirement)
When fn_NM_Sleep_diag_RoB_clear() function is called, clear all NVM data specified in
(G1) CAN Excessive Wake up (Internal) - TFDCX32348-17360: (G1) ,
{ NVM_U2A1600_Snapshot, NVM_U2A1600_TripCnt_*, NVM_U2A1600_TimeCnt_*, NVM_U2A1600_Odo_*, NVM_U2A1600_Year_*, NVM_U2A1600_Mont_*, NVM_U2A1600_Date_*, NVM_U2A1600_Hour_*, NVM_U2A1600_Min_*, NVM_U2A1600_Sec_*, NVM_U2A1600_Factor00_*, NVM_U2A1600_Factor01_*, NVM_U2A1600_Factor02_*, NVM_U2A1600_Factor04_* }
(G2) CAN Sleep NG Continued (Intenal) - TFDCX32348-17371: (G2) ,
{ NVM_U2A1700_Snapshot, NVM_U2A1700_TripCnt_*, NVM_U2A1700_TimeCnt_*, NVM_U2A1700_Odo_*, NVM_U2A1700_Year_*, NVM_U2A1700_Mont_*, NVM_U2A1700_Date_*, NVM_U2A1700_Hour_*, NVM_U2A1700_Min_*, NVM_U2A1700_Sec_*, NVM_U2A1700_Factor00_*, NVM_U2A1700_Factor01_*, NVM_U2A1700_Factor02_*, NVM_U2A1700_Factor04_* }
(L1) CXPI Excessive Wake up - ,
(G3) CAN Excessive Wake up (Global) - TFDCX32348-17391: (G3) ,
{ NVM_U2A1200_Snapshot, NVM_U2A1200_TripCnt_*, NVM_U2A1200_TimeCnt_*, NVM_U2A1200_Odo_*, NVM_U2A1200_Year_*, NVM_U2A1200_Mont_*, NVM_U2A1200_Date_*, NVM_U2A1200_Hour_*, NVM_U2A1200_Min_*, NVM_U2A1200_Sec_*, NVM_U2A1200_LastNM_*[10], NVM_U2A1200_Frame_*[10][3] }
(G4) CAN Sleep NG Continued (Global) - TFDCX32348-17400: (G4) ,
{ NVM_U2A1300_Snapshot, NVM_U2A1300_TripCnt_*, NVM_U2A1300_TimeCnt_*, NVM_U2A1300_Odo_*, NVM_U2A1300_Year_*, NVM_U2A1300_Mont_*, NVM_U2A1300_Date_*, NVM_U2A1300_Hour_*, NVM_U2A1300_Min_*, NVM_U2A1300_Sec_*, NVM_U2A1300_NMFrame_*[5], NVM_U2A1300_DiagFrame_*[5], NVM_U2A1300_EventFrame_*[5] }
(E1) Cluster Excessive Wake up - TFDCX32348-80296: (E1),
{ NVM_U2A0000_Snapshot, NVM_U2A0000_TripCnt_*, NVM_U2A0000_TimeCnt_*, NVM_U2A0000_Odo_*, NVM_U2A0000_Year_*, NVM_U2A0000_Mont_*, NVM_U2A0000_Date_*, NVM_U2A0000_Hour_*, NVM_U2A0000_Min_*, NVM_U2A0000_Sec_*, NVM_U2A0000_Factor01_*, NVM_U2A0000_Factor02_*, NVM_U2A0000_Factor04_*, NVM_U2A0000_Factor05_*, NVM_U2A0000_Factor0E_* }
(E2) Cluster Sleep NG Continued - TFDCX32348-80308: (E2) .
{ NVM_U2A0100_Snapshot, NVM_U2A0100_TripCnt_*, NVM_U2A0100_TimeCnt_*, NVM_U2A0100_Odo_*, NVM_U2A0100_Year_*, NVM_U2A0100_Mont_*, NVM_U2A0100_Date_*, NVM_U2A0100_Hour_*, NVM_U2A0100_Min_*, NVM_U2A0100_Sec_*, NVM_U2A0100_Factor09_*, NVM_U2A0100_Factor0A_*, NVM_U2A0100_Factor0C_*, NVM_U2A0100_Factor0E_* }
(Write 0 to all NVM data)
Here * corresponds to “1”, and “2”, and “3”.
- Verification Criteria: Verify by executing test cases
- Verification Method: System Qualification Test
- Verification Owner: FV
- System Requirement State: Approved
- Primary Discipline: SW
- ASIL Rating: QM

### TFDCX32348-79940: Heading TEMPLATE (Heading)
- System Requirement State: Approved

#### TFDCX32348-79941: System Requirement - TEMPLATE (System Requirement)
TEMPLATE
Ignore this artifact.
- Verification Criteria: Verify by executing test cases
- Verification Method: System Qualification Test
- Verification Owner: FV
- System Requirement State: Approved
- Primary Discipline: SW
- ASIL Rating: QM

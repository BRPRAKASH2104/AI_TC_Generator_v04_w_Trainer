# Json2ReqIF Transformation

# Specification: DIAG_ETM_DTC
- JDA Snapshot Date: 2025-10-31 08:01:21

## TFDCX32348-74133: ETM_DTC (Heading)
- System Requirement State: Draft
- Primary Discipline: TBD
- ASIL Rating: TBD

## TFDCX32348-74134: History (Heading)
- System Requirement State: Draft
- Primary Discipline: TBD
- ASIL Rating: TBD

### TFDCX32348-74135: Version... (Information)
| Version | Date | Name | Description of change | SRD Baseline |
| --- | --- | --- | --- | --- |
| 0.1 | 2025/03/11 | Mathieu Lenoble | TFDCX32348-74557: [SYS][12.3FDC][APP][ETM] Addition of SW version and DTC | BL_20250328 |
| 0.2 | 2025/06/17 | Baviskar Tejaswini | Updated DTC display count to from 30 to 32. TFDCX32348-93389: [SYS][12.3FDC][APP][ETM] Increase of the number of DTC to be displayed in ETM | BL_20250624_01 |
| 0.3 | 2025/10/15 | Baviskar Tejaswini | Added visio image for ETM-DTC display() TFDCX32348-113997: [SYS][12.3FDC][APP][ETM] SW Part Number LB2 update for ETM mode | BL_20251015_01 |
- System Requirement State: Draft
- Primary Discipline: TBD
- ASIL Rating: TBD

## TFDCX32348-74136: Overview (Heading)
- System Requirement State: Draft
- Primary Discipline: TBD
- ASIL Rating: TBD

### TFDCX32348-74137: This SRD defines the requirement for ... (Information)
This SRD defines the requirement for DTC screen of ETM, within this screen the DTC recorded at the time ETM is triggered will be displayed. This functional is executed in ETM mode only.
- System Requirement State: Draft
- Primary Discipline: TBD
- ASIL Rating: TBD

## TFDCX32348-74138: Input Requirements (Heading)
- System Requirement State: Draft
- Primary Discipline: TBD
- ASIL Rating: TBD

### TFDCX32348-74139: Switch Input (Heading)
- System Requirement State: Draft
- Primary Discipline: TBD
- ASIL Rating: TBD

#### TFDCX32348-74140: H/W DI - ODO_TripKnobInput (System Interface)
- System Requirement State: Draft
- Primary Discipline: TBD
- ASIL Rating: TBD

## TFDCX32348-74154: Output Requirements (Heading)
- System Requirement State: Draft
- Primary Discipline: TBD
- ASIL Rating: TBD

## TFDCX32348-74165: Performance Requirements (Heading)
- System Requirement State: Draft
- Primary Discipline: TBD
- ASIL Rating: TBD

### TFDCX32348-74166: DTC (Heading)
- System Requirement State: Draft
- Primary Discipline: TBD
- ASIL Rating: TBD

#### TFDCX32348-74167: The ETM DTC shall show the number... (System Requirement)
The ETM DTC shall show the number of DTC that is currently recorded in the meter at the time ETM mode is trigger.
- Verification Criteria: Verify by executing test cases
- Verification Method: Software Qualification Test, System Qualification Test, Unit Test
- Verification Owner: FV, SW
- System Requirement State: Approved
- Secondary Disciplines: FV, SW
- Primary Discipline: SW
- ASIL Rating: QM

#### TFDCX32348-74196 (System Requirement)
The ETM DTC shall show the name and status of each DTC that is recorded in the meter at the time ETM is triggered.
A DTC is composed of:
- DTC name → 3 bytes
- DTC status → 1 byte
Notes:
1. Refer to the DTC SRD for the details on the DTC name and status: TFDCX32348-7296: DIAG_DTC
2. The information to be shown on the screen shall be similar to what is read out from service 19 (refer to TFDCX32348-9468: Read DTC Information (SID 0x19))
- Verification Criteria: Verify by executing test cases
- Verification Method: Software Qualification Test, System Qualification Test, Unit Test
- Verification Owner: FV, SW
- System Requirement State: Approved
- Secondary Disciplines: FV, SW
- Primary Discipline: SW
- ASIL Rating: QM

### TFDCX32348-74172: SW Versions Display... (Heading)
SW Versions Display
- System Requirement State: Draft
- Primary Discipline: TBD
- ASIL Rating: TBD

#### TFDCX32348-74173: The screen for ETM DTC shall follow... (System Requirement)
The screen for ETM DTC shall follow the sample screen below.
It shall be possible to display 32 (.*) DTCs within one screen, multiple column are allowed and font can be set small to fit all the DTCs in one screen.
(.*) - (Out of 32, 25 are U-code DTCs and 7 are B-code DTCs)
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For displaying DTC status in ETM , bits 0-3 are considered instead of bits 0-7.
Please refer this Visio file for ETM -DTC Display.
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- Verification Criteria: Verify by executing test cases
- Verification Method: Functional Verification / Validation
- Verification Owner: FV, SW
- System Requirement State: Draft
- Primary Discipline: SW
- ASIL Rating: QM

# Json2ReqIF Transformation

# Specification: SysFS04_Gauges
- JDA Snapshot Date: 2025-08-21 12:52:40

## MS22029826-34644: Table of Revision (Heading)
- Stakeholder Requirement State: In Review
- System Requirement State: Draft
- Software Requirement State: Draft
- Primary Discipline: TBD
- Requirement Type: TBD

### MS22029826-44081: Revision (Heading)
| Revision | DATE | Author | Modifications |
| --- | --- | --- | --- |
| BL23 | 30-10-2020 | cmathyam | Key On Homing is not applicable and parameter updated for angle and time Req ID: 1533486, 3269316, 2574558,3579135 |
| BL27 | 19-4-2021 | cmathyam | Fuel table update :Req ID: 2681676 |
| BL34 | 10-02-2022 | bsathyak | ReqID: 1589882 Updated Fuel Table ReqID: 2609162 Updated Constant values for issue fix |
- Stakeholder Requirement State: In Review
- System Requirement State: Draft
- Software Requirement State: Draft
- Primary Discipline: TBD
- Requirement Type: TBD

### MS22029826-104738: Revision (Heading)
| Revision | DATE | Author | Modifications |
| --- | --- | --- | --- |
| 0.1 | 09/10/2024 | kkumara5 | Initial Content (Dynamic tachometer added) |
| 0.2 | 24/3/2025 | CMATHYAM | Fuel guage table added for silverbox adaptation MS22029826-120328: [S220_Adoption]: Fuel Tank 60 Liters table to implement similar to W502 - Application Implementation |
- Variant: S220_SB_ADP_W601-V1, S220_SB_ADP_W601-V2
- Stakeholder Requirement State: In Review
- System Requirement State: Draft
- Software Requirement State: Draft
- Primary Discipline: TBD
- Requirement Type: TBD

### MS22029826-129519: Revision (Heading)
| Revision | DATE | Author | Modifications |
| --- | --- | --- | --- |
| 0.1 | 30-05-2025 | mganase | MS22029826-34678 : Added Z112 variant for applicable requirements of tachometer section |
- Variant: Z112_SB_ADP_Z101-V5, Z112_SB_ADP_Z101-V6, Z112_SB_ADP_Z101-V7
- Stakeholder Requirement State: In Review
- System Requirement State: Draft
- Software Requirement State: Draft
- Primary Discipline: TBD
- Requirement Type: TBD

## MS22029826-34697: Rendered Gauges (Heading)
- Variant: S220, S237, W502
- Stakeholder Requirement State: In Review
- System Requirement State: Draft
- Software Requirement State: Draft
- Primary Discipline: TBD
- Requirement Type: TBD

### MS22029826-34648: Generic Gauges (Heading)
- Variant: S220, S237, W502
- Stakeholder Requirement State: In Review
- System Requirement State: Draft
- Software Requirement State: Draft
- Primary Discipline: TBD
- Requirement Type: TBD

#### MS22029826-34650: Input Requirements (Heading)
- Variant: S220, S237, W502
- Stakeholder Requirement State: In Review
- System Requirement State: Draft
- Software Requirement State: Draft
- Primary Discipline: TBD
- Requirement Type: TBD

##### MS22029826-44083: IgnMode (Value: Off, On) (System Requirement)
- Variant: S220, S237, W502
- Stakeholder Requirement State: In Review
- System Requirement State: Draft
- Secondary Disciplines: FV
- Software Requirement State: Draft
- Primary Discipline: SW
- Requirement Type: Functional

##### MS22029826-44085: LVSD/HVSD Flag (Value: Not Set, Set) (System Requirement)
- Variant: S220, S237, W502
- Stakeholder Requirement State: In Review
- System Requirement State: Draft
- Secondary Disciplines: FV
- Software Requirement State: Draft
- Primary Discipline: SW
- Requirement Type: Functional

##### MS22029826-44087: VAR_CODING_ANTILOCK_BRAKING_SYSTEM (Value: 0-Not Present, 1-Present) (System Requirement)
- Variant: S220, S237, W502
- Stakeholder Requirement State: In Review
- System Requirement State: Draft
- Secondary Disciplines: FV
- Software Requirement State: Draft
- Primary Discipline: SW
- Requirement Type: Functional

##### MS22029826-44090: VAR_CODING_ELECTRONIC_STABILITY_CONTROL (Value: 0-Not Present, 1-Present) (System Requirement)
- Variant: S220, S237, W502
- Stakeholder Requirement State: In Review
- System Requirement State: Draft
- Software Requirement State: Draft
- Primary Discipline: SW
- Requirement Type: Functional

##### MS22029826-44092: VAR_CODING_ENGINE_MANAGEMENT_SYSTEM(Value: 0-Not Present, 1-Present) (System Requirement)
- Variant: S220, W502
- Stakeholder Requirement State: In Review
- System Requirement State: Draft
- Software Requirement State: Draft
- Primary Discipline: SW
- Requirement Type: Functional

##### MS22029826-70978: VAR_CODING_VEHICLE_CONTROL_UNIT (Value: 0-Not Present, 1-Present) (System Requirement)
- Variant: S237
- Stakeholder Requirement State: In Review
- System Requirement State: Draft
- Software Requirement State: Draft
- Primary Discipline: SW
- Requirement Type: Functional

#### MS22029826-34652: Output Requirements (Heading)
- Variant: S220, S237, W502
- Stakeholder Requirement State: In Review
- System Requirement State: Draft
- Software Requirement State: Draft
- Primary Discipline: TBD
- Requirement Type: TBD

##### MS22029826-44098: Speedometer Output (System Requirement)
- Variant: S220, S237, W502
- Stakeholder Requirement State: In Review
- System Requirement State: Draft
- Secondary Disciplines: FV
- Software Requirement State: Draft
- Primary Discipline: SW
- Requirement Type: Functional

##### MS22029826-44100: Tachometer Output (System Requirement)
- Variant: S220, W502
- Stakeholder Requirement State: In Review
- System Requirement State: Draft
- Secondary Disciplines: FV
- Software Requirement State: Draft
- Primary Discipline: SW
- Requirement Type: Functional

##### MS22029826-44094: Power Regen Output (System Requirement)
- Variant: S237
- Stakeholder Requirement State: In Review
- System Requirement State: Draft
- Secondary Disciplines: FV
- Software Requirement State: Draft
- Primary Discipline: SW
- Requirement Type: Functional

#### MS22029826-34654: Performance Requirements (Heading)
- Variant: S220, S237, W502
- Stakeholder Requirement State: In Review
- System Requirement State: Draft
- Software Requirement State: Draft
- Primary Discipline: TBD
- Requirement Type: TBD

##### MS22029826-34656: Table - Gauge Configuration (Heading)
- Variant: S220, S237, W502
- Stakeholder Requirement State: In Review
- System Requirement State: Draft
- Software Requirement State: Draft
- Primary Discipline: TBD
- Requirement Type: TBD

###### MS22029826-44102: Table - Gauge Configuration (Heading)
| VAR_CODING_ELECTRONIC_STABILITY_CONTROL | VAR_CODING_ANTILOCK_BRAKING_SYSTEM | Gauge Configuration |
| --- | --- | --- |
| 0 | 0 | 0 |
| 0 | 1 | 1 |
| 1 | 0 | 1 |
| 1 | 1 | 0 (DTC Shall be logged) |
- Variant: S220, S237, W502
- Stakeholder Requirement State: In Review
- System Requirement State: Draft
- Software Requirement State: Draft
- Primary Discipline: TBD
- Requirement Type: Functional

##### MS22029826-34658: Table - Gauge Summary (Heading)
- Variant: S220, S237, W502
- Stakeholder Requirement State: In Review
- System Requirement State: Draft
- Software Requirement State: Draft
- Primary Discipline: TBD
- Requirement Type: TBD

###### MS22029826-44104: Gauge (System Requirement)
| f | Gauge | Gauge Type | Configuration | Pointer Move Direction | Allowed IgnMode | LVSD Flag # | HVSD Flag # | Input Signal | Total Graphics Sweep Angle (°) | Angle to Stop (°) | Response Time (Lag) (msec) | Full Scale Response Time (sec) | Hysteresis (°) |
| --- | --- | --- | --- | --- | --- | --- | --- | --- | --- | --- | --- | --- | --- |
| 1 | Speedometer | TFT | Gauge Configuration | Clockwise | IGN On | Applicable | Applicable | VSpd In (Refer -4842877 | 240 | 0 | <300 | <1.3 | N/A |
| 2 | Tachometer | TFT | VAR_CODING_ENGINE_MANAGEMENT_SYSTEM | Clockwise | IGN On | Applicable | Applicable | EngSpd In | 240 | 0 | <300 | <1.3 | N/A |
- Variant: S220, W502
- Verification Criteria: To be verified by Detailed Gauge TDR
- Stakeholder Requirement State: In Review
- System Requirement State: Draft
- Secondary Disciplines: FV
- Software Requirement State: Draft
- Primary Discipline: SW
- Requirement Type: Non-Functional

###### MS22029826-44106: Gauge (System Requirement)
|  | Gauge | Gauge Ty pe | Configuration | Pointer Move Direction | All ow ed Ign Mo de | LV SD Fla g # | HV SD Fla g # | Input Signal | Tot al Gra phi cs Sweep Angle (°) | Angle to St o p (° ) | Response Time (La g) (msec) | Full Scale Response Tim e (sec ) | Hysteresis (°) |
| --- | --- | --- | --- | --- | --- | --- | --- | --- | --- | --- | --- | --- | --- |
|  | Speedometer | TFT | Gauge Configuration | Clockwise | IGN On | Applicable | Applicable | VSpd In (Refer - 5227840) | 240 | 0 | <300 | <1.3 | N/A |
|  | POWER- REGEN | TFT | VAR_CODING_VEHI CLE_CONTROL_UNI T | Clockwise | IGN On | Applicable | Applicable | POWER_REGEN_METER | 240 | 0 | <300 | <1.3 | N/A |
- Variant: S237
- Verification Criteria: To be verified by Detailed Gauge TDR
- Stakeholder Requirement State: In Review
- System Requirement State: Draft
- Secondary Disciplines: FV
- Software Requirement State: Draft
- Primary Discipline: SW
- Requirement Type: Non-Functional

###### MS22029826-44108: Gauge (System Requirement)
| FEATURE_CODE_DISTANCE_SPEED_INPUT_SEL | Message Name | CAN Signal (VSpd In) |
| --- | --- | --- |
| 0 | ESC2_10 | VEHICLE_SPEED_ESC |
| 1 | ESC12_10 | VEHICLE_SPEED_ESC12 |
- Variant: S220, S237, W502
- Stakeholder Requirement State: In Review
- System Requirement State: Draft
- Secondary Disciplines: FV
- Software Requirement State: Draft
- Primary Discipline: SW
- Requirement Type: Non-Functional

##### MS22029826-34660: Figure - Gauge High Level Processing (Heading)
- Variant: S220, S237, W502
- Stakeholder Requirement State: In Review
- System Requirement State: Draft
- Software Requirement State: Draft
- Primary Discipline: TBD
- Requirement Type: TBD

###### MS22029826-43291: Image 0 (System Requirement)
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- Variant: S220, S237, W502
- Stakeholder Requirement State: In Review
- System Requirement State: Draft
- Secondary Disciplines: FV
- Software Requirement State: Draft
- Primary Discipline: SW
- Requirement Type: Functional

##### MS22029826-34662: Figure - Gauge Common Processing (Heading)
- Variant: S220, S237, W502
- Stakeholder Requirement State: In Review
- System Requirement State: Draft
- Software Requirement State: Draft
- Primary Discipline: TBD
- Requirement Type: TBD

###### MS22029826-43293: word.docx (System Requirement)
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- Variant: S220, S237, W502
- Stakeholder Requirement State: In Review
- System Requirement State: Draft
- Software Requirement State: Draft
- Primary Discipline: SW
- Requirement Type: Functional

##### MS22029826-34664: Table - Speedo and Tacho Block Storage Parameters (Heading)
- Variant: S220, S237, W502
- Stakeholder Requirement State: In Review
- System Requirement State: Draft
- Software Requirement State: Draft
- Primary Discipline: TBD
- Requirement Type: TBD

###### MS22029826-43295: Parameter (System Requirement)
|  | Parameter | Bytes | Range | Resolution / Scaling | Engineering Value | Software Value |
| --- | --- | --- | --- | --- | --- | --- |
| 1 | aTS1 (speedo) | 1 | 1 - 4 | 1 | 3 | 3 |
| 2 | aTS2 (speedo) | 1 | 1 - 4 | 1 | 3 | 3 |
| 3 | aTT1 (tach) | 1 | 1 - 4 | 1 | 2 | 2 |
| 4 | aTT2 (tach) | 1 | 1 - 4 | 1 | 1 | 1 |
- Variant: S220, W502
- Stakeholder Requirement State: In Review
- System Requirement State: Draft
- Secondary Disciplines: FV
- Software Requirement State: Draft
- Primary Discipline: SW
- Requirement Type: Functional

###### MS22029826-44096: Parameter (System Requirement)
|  | Parameter | Bytes | Range | Resolution / Scaling | Engineering Value | Software Value |
| --- | --- | --- | --- | --- | --- | --- |
| 1 | aTS1 (speedo) | 1 | 1 - 4 | 1 | 3 | 3 |
| 2 | aTS2 (speedo) | 1 | 1 - 4 | 1 | 3 | 3 |
| 3 | aTT1 (POWER-REGEN) | 1 | 1 - 4 | 1 | 2 | 2 |
| 4 | aTT2 (POWER-REGEN) | 1 | 1 - 4 | 1 | 1 | 1 |
- Variant: S237
- Stakeholder Requirement State: In Review
- System Requirement State: Draft
- Secondary Disciplines: FV
- Software Requirement State: Draft
- Primary Discipline: SW
- Requirement Type: Functional

### MS22029826-34665: Speedometer (Heading)
- Variant: S220, S237, W502
- Stakeholder Requirement State: In Review
- System Requirement State: Draft
- Software Requirement State: Draft
- Primary Discipline: TBD
- Requirement Type: TBD

#### MS22029826-43297: Input Requirements (Heading)
- Variant: S220, S237, W502
- Stakeholder Requirement State: In Review
- System Requirement State: Draft
- Software Requirement State: Draft
- Primary Discipline: TBD
- Requirement Type: TBD

##### MS22029826-52072: Speedometer Preconditions (System Requirement)
- Variant: S220, S237, W502
- Stakeholder Requirement State: In Review
- System Requirement State: Draft
- Secondary Disciplines: FV
- Software Requirement State: Draft
- Primary Discipline: SW
- Requirement Type: Functional

##### MS22029826-52074: VSpd In : ESC2_10: VEHICLE_SPEED_ESC (System Requirement)
VSpd In : ESC2_10: VEHICLE_SPEED_ESC
ESC12_10:VEHICLE_SPEED_ESC12 (Value,: 0xFFFE-Default, 0xFFFF-Invalid, Range: 0-300km/h, Factor: 0.015625)
- Variant: S220, S237, W502
- Stakeholder Requirement State: In Review
- System Requirement State: Draft
- Secondary Disciplines: FV
- Software Requirement State: Draft
- Primary Discipline: SW
- Requirement Type: Functional

##### MS22029826-52076: ESC12_10:ESC12_CRC(Value:0x0 to 0xFF) (System Requirement)
- Variant: S220, S237, W502
- Stakeholder Requirement State: In Review
- System Requirement State: Draft
- Secondary Disciplines: FV
- Software Requirement State: Draft
- Primary Discipline: SW
- Requirement Type: Functional

##### MS22029826-52079: Diag RW Min VehSpeed Threshold (Default: 6km/h) (System Requirement)
- Variant: S220, S237, W502
- Stakeholder Requirement State: In Review
- System Requirement State: Draft
- Secondary Disciplines: FV
- Software Requirement State: Draft
- Primary Discipline: SW
- Requirement Type: Functional

##### MS22029826-52081: DiagRWOverSpeedLevel1Val (Default: 80kmph). (System Requirement)
- Variant: S220, S237, W502
- Stakeholder Requirement State: In Review
- System Requirement State: Draft
- Secondary Disciplines: FV
- Software Requirement State: Draft
- Primary Discipline: SW
- Requirement Type: Functional

##### MS22029826-52083: DiagRWOverSpeedLevel2Val (Default: 120kmph). (System Requirement)
- Variant: S220, S237, W502
- Stakeholder Requirement State: In Review
- System Requirement State: Draft
- Secondary Disciplines: FV
- Software Requirement State: Draft
- Primary Discipline: SW
- Requirement Type: Functional

##### MS22029826-52084: DiagRWOverSpeedHysteresis(Default: 5%) (System Requirement)
- Variant: S220, S237, W502
- Stakeholder Requirement State: In Review
- System Requirement State: Draft
- Secondary Disciplines: FV
- Software Requirement State: Draft
- Primary Discipline: SW
- Requirement Type: Functional

#### MS22029826-34667: Output Requirements (Heading)
- Variant: S220, S237, W502
- Stakeholder Requirement State: In Review
- System Requirement State: Draft
- Software Requirement State: Draft
- Primary Discipline: TBD
- Requirement Type: TBD

##### MS22029826-43299: VSpd Ind (Value,: 0xFFFE-Default, 0xFFFF-Invalid, Range: 0-300km/h, Factor: 0.015625) (System Requirement)
- Variant: S220, S237, W502
- Stakeholder Requirement State: In Review
- System Requirement State: Draft
- Secondary Disciplines: FV
- Software Requirement State: Draft
- Primary Discipline: SW
- Requirement Type: Functional

##### MS22029826-43301: VSpd In Fault (System Requirement)
- Variant: S220, S237, W502
- Stakeholder Requirement State: In Review
- System Requirement State: Draft
- Secondary Disciplines: FV
- Software Requirement State: Draft
- Primary Discipline: SW
- Requirement Type: Functional

##### MS22029826-43303: Vehicle Moving St (System Requirement)
- Variant: S220, S237, W502
- Stakeholder Requirement State: In Review
- System Requirement State: Draft
- Secondary Disciplines: FV
- Software Requirement State: Draft
- Primary Discipline: SW
- Requirement Type: Functional

##### MS22029826-43305: IC7_1000_TEST: VEHICLE_SPEED_IC (System Requirement)
- Variant: S220, S237, W502
- Stakeholder Requirement State: In Review
- System Requirement State: Draft
- Secondary Disciplines: FV
- Software Requirement State: Draft
- Primary Discipline: SW
- Requirement Type: Functional

##### MS22029826-43307: IC10_200: VEHICLE_SPEED_IC_DISPLAYED (System Requirement)
- Variant: S220, S237, W502
- Stakeholder Requirement State: In Review
- System Requirement State: Draft
- Secondary Disciplines: FV
- Software Requirement State: Draft
- Primary Discipline: SW
- Requirement Type: Functional

#### MS22029826-34669: Performance Requirements (Heading)
- Variant: S220, S237, W502
- Stakeholder Requirement State: In Review
- System Requirement State: Draft
- Software Requirement State: Draft
- Primary Discipline: TBD
- Requirement Type: TBD

##### MS22029826-43328: The Speedometer gauge shall be functional only in IGN ON (System Requirement)
- Variant: S220, S237, W502
- Stakeholder Requirement State: In Review
- System Requirement State: Draft
- Software Requirement State: Draft
- Primary Discipline: SW
- Requirement Type: Functional

##### MS22029826-43320: The pointer shall respond to the given input within 100 ms (System Requirement)
- Variant: S220, S237, W502
- Stakeholder Requirement State: In Review
- System Requirement State: Draft
- Software Requirement State: Draft
- Primary Discipline: SW
- Requirement Type: Functional

##### MS22029826-43315: In case of rendered gauge, the pointer shall move smoothly & continuously from low to high indication without any step / jerk movement within a span of 3 secs. (System Requirement)
- Variant: S220, S237, W502
- Verification Criteria: To be verified by Detailed Gauge TDR
- Stakeholder Requirement State: In Review
- System Requirement State: Draft
- Software Requirement State: Draft
- Primary Discipline: SW
- Requirement Type: Non-Functional

##### MS22029826-43313: There shall be no pointer overshoot for a ramp input up to 60 km/h. (System Requirement)
- Variant: S220, S237, W502
- Verification Criteria: To be verified by Detailed Gauge TDR
- Stakeholder Requirement State: In Review
- System Requirement State: Draft
- Software Requirement State: Draft
- Primary Discipline: SW
- Requirement Type: Non-Functional

##### MS22029826-43311: The response of the Speedometer gauge shall be defined by the 2-stage filter constants T11 =3, T12 = 3. (System Requirement)
- Variant: S220, S237, W502
- Stakeholder Requirement State: In Review
- System Requirement State: Draft
- Software Requirement State: Draft
- Primary Discipline: SW
- Requirement Type: Functional

##### MS22029826-43318: The pointer tolerance of the Speedometer gauge shall not exceed +/- 1 km/h (1.23 deg) (System Requirement)
- Variant: S237
- Verification Criteria: To be verified by Detailed Gauge TDR
- Stakeholder Requirement State: In Review
- System Requirement State: Draft
- Software Requirement State: Draft
- Primary Discipline: SW
- Requirement Type: Non-Functional

##### MS22029826-43326: In case of IGN Off, the cluster shall drive the stepper to park position (refer Speedo Table) (System Requirement)
- Variant: S237
- Stakeholder Requirement State: In Review
- System Requirement State: Draft
- Software Requirement State: Draft
- Primary Discipline: SW
- Requirement Type: Functional

##### MS22029826-43309: The Speedometer gauge shall follow a linear scale (System Requirement)
- Variant: S237
- Stakeholder Requirement State: In Review
- System Requirement State: Draft
- Software Requirement State: Draft
- Primary Discipline: SW
- Requirement Type: Functional

##### MS22029826-34671: Speedometer Input and Gauge Processing (Heading)
- Variant: S220, S237, W502
- Stakeholder Requirement State: In Review
- System Requirement State: Draft
- Software Requirement State: Draft
- Primary Discipline: TBD
- Requirement Type: TBD

###### MS22029826-43332: Figure - Speedometer Input and Gauge... (System Requirement)
Figure - Speedometer Input and Gauge Processing.docx:
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- Variant: S220, S237, W502
- Stakeholder Requirement State: In Review
- System Requirement State: Draft
- Software Requirement State: Draft
- Primary Discipline: SW
- Requirement Type: Functional

###### MS22029826-43336: FEATURE_CODE_DISTANCE_SPEED_INPUT_SEL (System Requirement)
| FEATURE_CODE_DISTANCE_SPEED_INPUT_SEL | Message Name | CAN Signal (VSpd In) |
| --- | --- | --- |
| 0 | ESC2_10 | VEHICLE_SPEED_ESC |
| 1 | ESC12_10 | VEHICLE_SPEED_ESC12 |
Based on the FEATURE_CODE_DISTANCE_SPEED_INPUT_SEL Input CAN signal for Speedo calculation shall be considered.
- Variant: S220, S237, W502
- Stakeholder Requirement State: In Review
- System Requirement State: Draft
- Software Requirement State: Draft
- Primary Discipline: SW
- Requirement Type: Functional

##### MS22029826-34673: Table - Speedometer Transfer Function and Tolerance (Heading)
- Variant: S220, S237, W502
- Stakeholder Requirement State: In Review
- System Requirement State: Draft
- Software Requirement State: Draft
- Primary Discipline: TBD
- Requirement Type: TBD

###### MS22029826-43334: Table 1 - Speedometer Transfer Function and Tolerance (System Requirement)
VSpd In for S220 Variant -Refer 4837363
| S.No | Vehicle Speed (KMPH) | VSpd In Comp(Dec) | Speedometer Pointer Indication (VSpd Ind) (KMPH) Cluster Target Tolerance | Speedometer Pointer Indication (Angular Degrees) | Speedometer Pointer Percentage Indication (%) |
| --- | --- | --- | --- | --- | --- |
| S.No | (VSpd In) | VSpd In Comp(Dec) | Speedometer Pointer Indication (VSpd Ind) (KMPH) Cluster Target Tolerance | Speedometer Pointer Indication (Angular Degrees) | Speedometer Pointer Percentage Indication (%) |
| 1 | Park | Position | 0 | 0 | 0 |
| 2 | Diag | Position | 220 | 240 | 100 |
| 3 | 0 | 0 | 0 | 0 | 0 |
| 4 | 10 | 640 | 13 | 10.9 | 4.5 |
| 5 | 20 | 1280 | 23 | 21.8 | 9 |
| 6 | 30 | 1920 | 33 | 32.7 | 13.5 |
| 7 | 40 | 2560 | 43 | 43.6 | 18 |
| 8 | 50 | 3200 | 53 | 54.5 | 22.5 |
| 9 | 60 | 3840 | 63 | 65.4 | 27 |
| 10 | 70 | 4480 | 73 | 76.3 | 31.5 |
| 11 | 80 | 5120 | 83 | 87.2 | 36 |
| 12 | 90 | 5760 | 93 | 98.2 | 40.5 |
| 13 | 100 | 6400 | 103 | 109.1 | 45 |
| 14 | 110 | 7040 | 113 | 120 | 49.5 |
| 15 | 120 | 7680 | 123 | 130.9 | 54 |
| 16 | 130 | 8320 | 134 | 141.8 | 58.5 |
| 17 | 140 | 8960 | 144 | 152.7 | 63 |
| 18 | 150 | 9600 | 154 | 163.6 | 67.5 |
| 19 | 160 | 10240 | 164 | 174.5 | 72 |
| 20 | 170 | 10880 | 174 | 185.4 | 76.5 |
| 21 | 180 | 11520 | 184 | 196.3 | 81 |
| 22 | 190 | 12160 | 194 | 207.3 | 85.5 |
| 23 | 200 | 12800 | 204 | 218.2 | 90 |
| 24 | 210 | 13440 | 214 | 229.1 | 94.5 |
| 25 | 220 | 14080 | 224 (VSpd Ind Max) | 240 | 100 |
- Variant: S220
- Stakeholder Requirement State: In Review
- System Requirement State: Draft
- Software Requirement State: Draft
- Primary Discipline: SW
- Requirement Type: Functional

###### MS22029826-43337: Table 1 - Speedometer Transfer Function and Tolerance (System Requirement)
| S.No | Vehicle Speed (KMPH) VSpd In | VSpd In Comp(Dec) | Speedometer Pointer Indication (VSpd Ind) (KMPH) Cluster Target Tolerance | Speedometer Pointer Indication (Angular Degrees) | Speedometer Pointer Percentage Indication (%) |
| --- | --- | --- | --- | --- | --- |
| 1 | Park | Position | 0 | 0 | 0 |
| 2 | Diag | Position | 180 | 240 | 100 |
| 3 | 0 | 0 | 0 | 0 | 0 |
| 4 | 10 | 640 | 13 | 13.3 | 5.5 |
| 5 | 20 | 1280 | 23 | 26.7 | 11 |
| 6 | 30 | 1920 | 33 | 40 | 16.5 |
| 7 | 40 | 2560 | 43 | 53.3 | 22 |
| 8 | 50 | 3200 | 53 | 66.6 | 27.5 |
| 9 | 60 | 3840 | 63 | 80 | 33 |
| 10 | 70 | 4480 | 73 | 93.3 | 38.5 |
| 11 | 80 | 5120 | 83 | 106.6 | 44 |
| 12 | 90 | 5760 | 93 | 120 | 49.5 |
| 13 | 100 | 6400 | 103 | 133.3 | 55 |
| 14 | 110 | 7040 | 113 | 146.6 | 60.5 |
| 15 | 120 | 7680 | 123 | 160 | 66 |
| 16 | 130 | 8320 | 134 | 173.3 | 71.5 |
| 17 | 140 | 8960 | 144 | 186.6 | 77 |
| 18 | 150 | 9600 | 154 | 200 | 82.5 |
| 19 | 160 | 10240 | 164 | 213.3 | 88 |
| 20 | 170 | 10880 | 174 | 226.6 | 93.5 |
| 21 | 180 | 11520 | 184 (VSpd Ind Max) | 240 | 100 |
- Variant: S237, W502
- Stakeholder Requirement State: In Review
- System Requirement State: Draft
- Software Requirement State: Draft
- Primary Discipline: SW
- Requirement Type: Functional

##### MS22029826-34674: Figure - Vehicle Moving Status Processing (Heading)
- Variant: S220, S237, W502
- Stakeholder Requirement State: In Review
- System Requirement State: Draft
- Software Requirement State: Draft
- Primary Discipline: TBD
- Requirement Type: TBD

###### MS22029826-43344: Vehicle Moving St: Vehicle Moving St (System Requirement)
Vehicle Moving St:
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- Variant: S220, S237, W502
- Stakeholder Requirement State: In Review
- System Requirement State: Draft
- Software Requirement State: Draft
- Primary Discipline: SW
- Requirement Type: Functional

##### MS22029826-34676: CAN Output (Heading)
- Variant: S220, S237, W502
- Stakeholder Requirement State: In Review
- System Requirement State: Draft
- Software Requirement State: Draft
- Primary Discipline: TBD
- Requirement Type: TBD

###### MS22029826-43346: If Vspd Ind >= DiagRWOverSpeedLevel2Val, then cluster shall transmit INDC_HIGH_SPD = 0x1 (System Requirement)
- Variant: S220, S237, W502
- Stakeholder Requirement State: In Review
- System Requirement State: Draft
- Secondary Disciplines: FV
- Software Requirement State: Draft
- Primary Discipline: SW
- Requirement Type: Functional

###### MS22029826-43348: If Vspd Ind <=DiagRWOverSpeedLevel2Val - DiagRWOverSpeedHysteresis, then cluster shall transmit INDC_HIGH_SPD = 0x0 (System Requirement)
- Variant: S220, S237, W502
- Stakeholder Requirement State: In Review
- System Requirement State: Draft
- Secondary Disciplines: FV
- Software Requirement State: Draft
- Primary Discipline: SW
- Requirement Type: Functional

###### MS22029826-43351: The cluster shall update VSpd Ind in the messages 'IC7_1000_TEST: VEHICLE_SPEED_IC' and 'IC10_200: VEHICLE_SPEED_IC_DISPLAYED' in case VSpd In Fault = 'False' (System Requirement)
- Variant: S220, S237, W502
- Stakeholder Requirement State: In Review
- System Requirement State: Draft
- Secondary Disciplines: FV
- Software Requirement State: Draft
- Primary Discipline: SW
- Requirement Type: Functional

###### MS22029826-43353: The cluster shall update 0xFFFF(Invalid) in the messages 'IC7_1000_TEST: VEHICLE_SPEED_IC' and 'IC10_200: VEHICLE_SPEED_IC_DISPLAYED' in case VSpd In Fault = 'True' (System Requirement)
- Variant: S220, S237, W502
- Stakeholder Requirement State: In Review
- System Requirement State: Draft
- Secondary Disciplines: FV
- Software Requirement State: Draft
- Primary Discipline: SW
- Requirement Type: Functional

### MS22029826-34678: Tachometer (Heading)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

#### MS22029826-34679: Input Requirements (Heading)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-43355: Tachometer Preconditions (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Secondary Disciplines: FV
- Software Requirement State: Draft
- Primary Discipline: SW
- Requirement Type: Functional

##### MS22029826-43357: EngSpd In: EMS36_10: ENG_SPD1 (Value: 0xFFFF-Invalid, Range: 0-7999rpm) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Secondary Disciplines: FV
- Software Requirement State: Draft
- Primary Discipline: SW
- Requirement Type: Functional

##### MS22029826-43359: EMS36_10: EMS36_CRC (Value: 0x0 to 0xFF) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Secondary Disciplines: FV
- Software Requirement State: Draft
- Primary Discipline: SW
- Requirement Type: Functional

##### MS22029826-43361: EMS1_10:STS_ENG (System Requirement)
EMS1_10:STS_ENG
(Value 0x0: Engine Not Running,
0x01: Engine Cranking due to T50,
0x02- Engine Running,
0x03-Engine Auto stop,
0x04-Engine stalled,
0x05-Engine cranking due to ESS,
0x06-Reserved,
0x07 Reserved)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Secondary Disciplines: FV
- Software Requirement State: Draft
- Primary Discipline: SW
- Requirement Type: Functional

##### MS22029826-43363: FEATURE_CODE_FUEL_TYPE (Value: 0-Gasoline, 1-Diesel) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-104650: EMS37_500(0X585) - ENG_OIL_TEMP (Range : -40 to 214 ,Factor :1 Offset :-40) (System Requirement)
- Variant: S220_SB_ADP_W601-V1, S220_SB_ADP_W601-V2
- Stakeholder Requirement State: In Review
- System Requirement State: Draft
- Software Requirement State: Draft
- Primary Discipline: SW
- Requirement Type: Functional

##### MS22029826-104651: EMS37_500(0X585) - ENG_OIL_PRESSURE_VAL( Range :0 to 30 , Factor 1, Offset -0) (System Requirement)
- Variant: S220_SB_ADP_W601-V1, S220_SB_ADP_W601-V2
- Stakeholder Requirement State: In Review
- System Requirement State: Draft
- Secondary Disciplines: FV
- Software Requirement State: Draft
- Primary Discipline: SW
- Requirement Type: Functional

#### MS22029826-34681: Output Requirements (Heading)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-43369: Engine Running St (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Secondary Disciplines: FV
- Software Requirement State: Draft
- Primary Discipline: SW
- Requirement Type: Functional

##### MS22029826-43371: Eng Spd In Fault (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Secondary Disciplines: FV
- Software Requirement State: Draft
- Primary Discipline: SW
- Requirement Type: Functional

##### MS22029826-104652: Tacho RedBand (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Secondary Disciplines: FV
- Software Requirement State: Draft
- Primary Discipline: SW
- Requirement Type: Functional

#### MS22029826-34682: Performance Requirements (Heading)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-34684: Figure - Tachometer Input and Gauge Processing (Heading)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-43375: tacho.vsd: (System Requirement)
tacho.vsd:
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- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-34686: Table - Tachometer Transfer Function and Tolerance (Heading)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-43377: Engine (System Requirement)
| S.No | Engin(RPM) | EngSpd Ind(Dec) | Tachometer Pointer Indication Cluster Tolerance | Tachometer Pointer Indication (Angular Degrees) | Tachometer Pointer Percentage Indication (%) |
| --- | --- | --- | --- | --- | --- |
| 1 | Park | Position | 0 | 0 | 0 |
| 2 | Diagnostic | Position | 7000 | 270 | 100 |
| 3 | 0 | 0 | 0 | 0 | 0 |
| 4 | 1000 | 1000 | 1000 | 38.57 | 14.3 |
| 5 | 2000 | 2000 | 2000 | 77.14 | 28.6 |
| 6 | 3000 | 3000 | 3000 | 115.71 | 42.9 |
| 7 | 4000 | 4000 | 4000 | 154.29 | 57.2 |
| 8 | 5000 | 5000 | 5000 | 192.86 | 71.5 |
| 9 | 6000 | 6000 | 6000 | 231.43 | 85.8 |
| 10 | 7000 | 7000 | 7000 | 270 | 100 |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Secondary Disciplines: FV
- Software Requirement State: Draft
- Primary Discipline: SW
- Requirement Type: Functional

###### MS22029826-43379: Engine (System Requirement)
FEATURE_CODE_FUEL_TYPE = 0 (Gasoline)
| S.No | Engin(RPM) | EngSpd Ind(Dec) | Tachometer Pointer Indication Cluster Tolerance | Tachometer Pointer Indication | Tachometer Pointer Percentage Indication (%) |
| --- | --- | --- | --- | --- | --- |
| S.No | Engin(RPM) | EngSpd Ind(Dec) | Tachometer Pointer Indication Cluster Tolerance | (Angular Degrees) | Tachometer Pointer Percentage Indication (%) |
| 1 | Park | Position | 0 | 0 | 0 |
| 2 | Diagnostic | Position | 7000 | 270 | 100 |
| 3 | 0 | 0 | 0 | 0 | 0 |
| 4 | 1000 | 1000 | 1000 | 33.75 | 12.5 |
| 5 | 2000 | 2000 | 2000 | 67.5 | 25 |
| 6 | 3000 | 3000 | 3000 | 101.25 | 37.5 |
| 7 | 4000 | 4000 | 4000 | 135 | 50 |
| 8 | 5000 | 5000 | 5000 | 168.75 | 62.5 |
| 9 | 6000 | 6000 | 6000 | 202.5 | 75 |
| 10 | 7000 | 7000 | 7000 | 236.25 | 87.5 |
| 11 | 8000 | 8000 | 8000 | 270 | 100 |
FEATURE_CODE_FUEL_TYPE = 1 (Diesel)
| S.No | Engin(RPM) | EngSpd Ind(Dec) | Tachometer Pointer Indication Cluster Tolerance | Tachometer Pointer Indication (Angular Degrees) | Tachometer Pointer Percentage Indication (%) |
| --- | --- | --- | --- | --- | --- |
| 1 | Park | Position | 0 | 0 | 0 |
| 2 | Diagnostic | Position | 6000 | 270 | 100 |
| 3 | 0 | 0 | 0 | 0 | 0 |
| 4 | 1000 | 1000 | 1000 | 45 | 16.6 |
| 5 | 2000 | 2000 | 2000 | 90 | 33.3 |
| 6 | 3000 | 3000 | 3000 | 135 | 49.9 |
| 7 | 4000 | 4000 | 4000 | 180 | 66.6 |
| 8 | 5000 | 5000 | 5000 | 225 | 83.2 |
| 9 | 6000 | 6000 | 6000 | 270 | 100 |
- Variant: S220, W502
- Stakeholder Requirement State: In Review
- System Requirement State: Draft
- Software Requirement State: Draft
- Primary Discipline: SW
- Requirement Type: Functional

##### MS22029826-34687: Table - Tachometer Gauge Constant Block Storage Parameters (Heading)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-43383: Parameter (System Requirement)
|  | Parameter | Bytes | Range | Resolution / Scaling | Engineering Value | Software Value |
| --- | --- | --- | --- | --- | --- | --- |
| 1 | IDLE_FILT_ENABLE | 1 bit | 0 (Off), 1 (On) | 1 | 1 | 1 |
| 2 | A_LMT (Clamped Idle RPM Value) | 2 | 0-65535 | 2 RPM | 800 RPM | 400 |
| 3 | IDLE_L_LMT (Lower Idle Band Limit) | 2 | 0-65535 | 2 RPM | 500 RPM | 250 |
| 4 | IDLE_U_LMT (Upper Idle Band Limit) | 2 | 0-65535 | 2 RPM | 1000 RPM | 500 |
| 5 | SHIFT_FILTER_CONSTANT |  |  |  | 1/16 th | 16 |
| 6 | IDLE_FILT_DELAY | 1 | 0-255 | 0.5 sec | 10 sec | 20 |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Secondary Disciplines: FV
- Software Requirement State: Draft
- Primary Discipline: SW
- Requirement Type: Functional

##### MS22029826-34689: Figure - Engine Running Status Processing (Heading)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-43385: Figure - Engine Running Status Proce... (System Requirement)
Figure - Engine Running Status Processing.docx:
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- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-43387: The Tachometer gauge shall follow a linear scale (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-43627: In case of rendered gauge, the pointer shall move smoothly & continuously from low to high indication without any step / jerk movement within a span of 2 secs. (System Requirement)
- Variant: S220, S220_SB_ADP_W601-V1, S220_SB_ADP_W601-V2, W502, Z112_SB_ADP_Z101-V5, Z112_SB_ADP_Z101-V6, Z112_SB_ADP_Z101-V7
- Verification Criteria: To be verified by Detailed Gauge TDR
- Stakeholder Requirement State: In Review
- System Requirement State: Draft
- Software Requirement State: Draft
- Primary Discipline: SW
- Requirement Type: Non-Functional

###### MS22029826-43630: When in normal operating condition with steady input, Tacho response must be steady with noise or jitter of not more than +/- 10 rpm. (System Requirement)
- Variant: S220, S220_SB_ADP_W601-V1, S220_SB_ADP_W601-V2, W502, Z112_SB_ADP_Z101-V5, Z112_SB_ADP_Z101-V6, Z112_SB_ADP_Z101-V7
- Verification Criteria: To be verified by Detailed Gauge TDR
- Stakeholder Requirement State: In Review
- System Requirement State: Draft
- Software Requirement State: Draft
- Primary Discipline: SW
- Requirement Type: Non-Functional

###### MS22029826-43632: The pointer shall respond to the given input within 100 ms (System Requirement)
- Variant: S220, S220_SB_ADP_W601-V1, S220_SB_ADP_W601-V2, W502, Z112_SB_ADP_Z101-V5, Z112_SB_ADP_Z101-V6, Z112_SB_ADP_Z101-V7
- Verification Criteria: To be verified by Detailed Gauge TDR
- Stakeholder Requirement State: In Review
- System Requirement State: Draft
- Software Requirement State: Draft
- Primary Discipline: SW
- Requirement Type: Non-Functional

###### MS22029826-43634: The response of the Tachometer gauge shall be defined by the 2-stage filter constants T11 =2, T12 = 1. (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-34692: Tachometer Idling Strategy (Heading)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-43636: The Tachometer gauge response shall be damped using the Idle Filter strategy while in idle mode so as to keep the pointer steady despite the rpm fluctuation (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-43638: Idling range shall be defined as from 500 to 1000 rpm, inclusive of both values. (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-43640: The stabilization time to enter Idle mode shall be 10 sec. (System Requirement)
- Variant: S220, S220_SB_ADP_W601-V1, S220_SB_ADP_W601-V2, W502, Z112_SB_ADP_Z101-V5, Z112_SB_ADP_Z101-V6, Z112_SB_ADP_Z101-V7
- Verification Criteria: To be verified by Detailed Gauge TDR
- Stakeholder Requirement State: In Review
- System Requirement State: Draft
- Software Requirement State: Draft
- Primary Discipline: SW
- Requirement Type: Non-Functional

###### MS22029826-43642 (System Requirement)
Outside of this range, the idling filter shall not apply and the tachometer response shall meet the lag requirement
When in idle mode, an additional 1/16 integer damping filter shall be applied.
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-43644: The Tachometer Idle Filter response shall be such that while in the defined idle band, the pointer movement shall correspond to a change of 1 rpm for an input change of 16 RPM. (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-34694: Tachometer RedBand (Heading)
Moving Tachometer RedBand
- Variant: S220, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-43650: FEATURE_CODE_FUEL_TYPE =0 (System Requirement)
FEATURE_CODE_FUEL_TYPE =0 (S220 GSL)
Upper Limit red band -8000rpm
Lower Limit red band- 5500 rpm
FEATURE_CODE_FUEL_TYPE =1 (S220 DSL)
Upper Limit red band -6000rpm
Lower Limit red band- 4500 rpm
- Variant: S220, S220_SB_ADP_W601-V1, S220_SB_ADP_W601-V2, W502
- Stakeholder Requirement State: In Review
- System Requirement State: Draft
- Software Requirement State: Draft
- Primary Discipline: SW
- Requirement Type: Functional

###### MS22029826-43652: FEATURE_CODE_FUEL_TYPE =0 (System Requirement)
FEATURE_CODE_FUEL_TYPE =0 (W502 GSL)
Upper Limit red band -7000rpm
Lower Limit red band- 5500 rpm
FEATURE_CODE_FUEL_TYPE =1 (W502 DSL)
Upper Limit red band -7000rpm
Lower Limit red band- 5000 rpm
- Variant: W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-104646: Moving Tachometer Redband (Heading)
- Variant: S220_SB_ADP_W601-V1, S220_SB_ADP_W601-V2
- Stakeholder Requirement State: In Review
- System Requirement State: Draft
- Software Requirement State: Draft

###### MS22029826-104633: The (System Requirement)
The Moving Tacho RedBand is applicable only if Moving Tacho RedBand configuration is 1
| FEATURE_CODE_FUEL_TYPE | Moving Tacho Red Band configuration |
| --- | --- |
| 0 | 1 |
| 1 | 0 |
- Variant: S220_SB_ADP_W601-V1, S220_SB_ADP_W601-V2
- Stakeholder Requirement State: In Review
- System Requirement State: Draft
- Software Requirement State: Draft
- Primary Discipline: SW
- Requirement Type: Functional

###### MS22029826-104634 (System Requirement)
Lower limit(red band) is modified based on the below table
Upper limit shall always be fixed to 7000 rpm
- Variant: S220_SB_ADP_W601-V1, S220_SB_ADP_W601-V2
- Stakeholder Requirement State: In Review
- System Requirement State: Draft
- Software Requirement State: Draft
- Primary Discipline: SW
- Requirement Type: Functional

###### MS22029826-104636: Table: Moving Tacho RedBand (System Requirement)
| EMS37_500(0x585) - ENG_OIL_TEMP (Deg C) | EMS37_500(0x585) - ENG_OIL_PRESSURE_VAL (Bar) |  |  |  |  |  |  |  |  |
| --- | --- | --- | --- | --- | --- | --- | --- | --- | --- |
| EMS37_500(0x585) - ENG_OIL_TEMP (Deg C) |  | 1 | 2 | 3 | 4 | 5 | 6 | 7 | 8 |
| EMS37_500(0x585) - ENG_OIL_TEMP (Deg C) | -25 | 5500 | 5500 | 5500 | 5500 | 5500 | 3000 | 2000 | 1000 |
| EMS37_500(0x585) - ENG_OIL_TEMP (Deg C) | -20 | 5500 | 5500 | 5500 | 5500 | 5500 | 3500 | 2500 | 1500 |
| EMS37_500(0x585) - ENG_OIL_TEMP (Deg C) | -15 | 5500 | 5500 | 5500 | 5500 | 5500 | 4000 | 3000 | 2000 |
| EMS37_500(0x585) - ENG_OIL_TEMP (Deg C) | -10 | 5500 | 5500 | 5500 | 5500 | 5500 | 4250 | 3500 | 2750 |
| EMS37_500(0x585) - ENG_OIL_TEMP (Deg C) | -5 | 5500 | 5500 | 5500 | 5500 | 5500 | 4500 | 4000 | 3500 |
| EMS37_500(0x585) - ENG_OIL_TEMP (Deg C) | 0 | 5500 | 5500 | 5500 | 5500 | 5500 | 4750 | 4250 | 3750 |
| EMS37_500(0x585) - ENG_OIL_TEMP (Deg C) | 5 | 5500 | 5500 | 5500 | 5500 | 5500 | 5000 | 4500 | 4000 |
| EMS37_500(0x585) - ENG_OIL_TEMP (Deg C) | 10 | 5500 | 5500 | 5500 | 5500 | 5500 | 5000 | 4500 | 4000 |
| EMS37_500(0x585) - ENG_OIL_TEMP (Deg C) | 15 | 5500 | 5500 | 5500 | 5500 | 5500 | 5000 | 4500 | 4000 |
| EMS37_500(0x585) - ENG_OIL_TEMP (Deg C) | 20 | 5500 | 5500 | 5500 | 5500 | 5500 | 5000 | 4500 | 4000 |
| EMS37_500(0x585) - ENG_OIL_TEMP (Deg C) | 25 | 5500 | 5500 | 5500 | 5500 | 5500 | 5000 | 4500 | 4000 |
| EMS37_500(0x585) - ENG_OIL_TEMP (Deg C) | 30 | 5500 | 5500 | 5500 | 5500 | 5500 | 5100 | 4600 | 4100 |
| EMS37_500(0x585) - ENG_OIL_TEMP (Deg C) | 35 | 5500 | 5500 | 5500 | 5500 | 5500 | 5200 | 4700 | 4200 |
| EMS37_500(0x585) - ENG_OIL_TEMP (Deg C) | 40 | 5500 | 5500 | 5500 | 5500 | 5500 | 5300 | 4800 | 4300 |
| EMS37_500(0x585) - ENG_OIL_TEMP (Deg C) | 45 | 5500 | 5500 | 5500 | 5500 | 5500 | 5400 | 4900 | 4400 |
| EMS37_500(0x585) - ENG_OIL_TEMP (Deg C) | 50 | 5500 | 5500 | 5500 | 5500 | 5500 | 5500 | 5000 | 4500 |
| EMS37_500(0x585) - ENG_OIL_TEMP (Deg C) | 55 | 5500 | 5500 | 5500 | 5500 | 5500 | 5500 | 5000 | 4500 |
| EMS37_500(0x585) - ENG_OIL_TEMP (Deg C) | 60 | 5500 | 5500 | 5500 | 5500 | 5500 | 5500 | 5000 | 4500 |
| EMS37_500(0x585) - ENG_OIL_TEMP (Deg C) | 65 | 5500 | 5500 | 5500 | 5500 | 5500 | 5500 | 5000 | 4500 |
| EMS37_500(0x585) - ENG_OIL_TEMP (Deg C) | 70 | 5500 | 5500 | 5500 | 5500 | 5500 | 5500 | 5000 | 4500 |
| EMS37_500(0x585) - ENG_OIL_TEMP (Deg C) | 75 | 5500 | 5500 | 5500 | 5500 | 5500 | 5500 | 5000 | 4500 |
| EMS37_500(0x585) - ENG_OIL_TEMP (Deg C) | 80 | 5500 | 5500 | 5500 | 5500 | 5500 | 5500 | 5000 | 4500 |
| EMS37_500(0x585) - ENG_OIL_TEMP (Deg C) | 85 | 5500 | 5500 | 5500 | 5500 | 5500 | 5500 | 5000 | 4500 |
| EMS37_500(0x585) - ENG_OIL_TEMP (Deg C) | 90 | 5500 | 5500 | 5500 | 5500 | 5500 | 5500 | 5000 | 4500 |
- Variant: S220_SB_ADP_W601-V1, S220_SB_ADP_W601-V2
- Stakeholder Requirement State: In Review
- System Requirement State: Draft
- Software Requirement State: Draft
- Primary Discipline: SW
- Requirement Type: Functional

###### MS22029826-104637 (System Requirement)
There shall be a Negative hysteresis of 1 Bar (DiagRWNegTachoRedOilPressureHysteris)
There shall be a Negative hysteresis of 5 Deg C (DiagRWNegTachoRedOilTempHysteris) to avoid fluctuation in the red band
- Variant: S220_SB_ADP_W601-V1, S220_SB_ADP_W601-V2
- Stakeholder Requirement State: In Review
- System Requirement State: Draft
- Software Requirement State: Draft
- Primary Discipline: SW
- Requirement Type: Functional

###### MS22029826-104638: If the Moving Tacho Redband is not applicable, i.e in case of Diesel variant, the lower limit of the red band shall always be 5000 rpm and the upper limit shall be fixed at 7000 rpm. (System Requirement)
- Variant: S220_SB_ADP_W601-V1, S220_SB_ADP_W601-V2
- Stakeholder Requirement State: In Review
- System Requirement State: Draft
- Software Requirement State: Draft
- Primary Discipline: SW
- Requirement Type: Functional

###### MS22029826-104644: Fail Safe Scenario (Heading)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft

###### MS22029826-104639: When CAN message is missing/ Invalid: The red lower limit shall be 5500(Default value) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-34711: Fuel Gauge (Heading)
- Variant: S220, W502
- Stakeholder Requirement State: In Review
- System Requirement State: Draft
- Software Requirement State: Draft
- Primary Discipline: TBD
- Requirement Type: TBD

#### MS22029826-34713: Input Requirements (Heading)
- Variant: S220, W502
- Stakeholder Requirement State: In Review
- System Requirement State: Draft
- Software Requirement State: Draft
- Primary Discipline: TBD
- Requirement Type: TBD

##### MS22029826-43716: IgnMode (Value: Off, On) (System Requirement)
- Variant: S220, W502
- Stakeholder Requirement State: In Review
- System Requirement State: Draft
- Secondary Disciplines: FV
- Software Requirement State: Draft
- Primary Discipline: SW
- Requirement Type: Functional

##### MS22029826-43718: LVSD/HVSD Flag (Not Set, Set) (System Requirement)
- Variant: S220, W502
- Stakeholder Requirement State: In Review
- System Requirement State: Draft
- Secondary Disciplines: FV
- Software Requirement State: Draft
- Primary Discipline: SW
- Requirement Type: Functional

##### MS22029826-43721: Fuel Sender AD In (Range: 0 ~ 170 ohms (System Requirement)
- Variant: S220, W502
- Stakeholder Requirement State: In Review
- System Requirement State: Draft
- Secondary Disciplines: FV
- Software Requirement State: Draft
- Primary Discipline: SW
- Requirement Type: Functional

##### MS22029826-43723: FEATURE_CODE_FUEL TABLE_SELECTION(0-Z101, 1-W601) (System Requirement)
- Variant: S220, W502
- Stakeholder Requirement State: In Review
- System Requirement State: Draft
- Secondary Disciplines: FV
- Software Requirement State: Draft
- Primary Discipline: SW
- Requirement Type: Functional

##### MS22029826-43725: Doc8.docx: Doc8.docx (System Requirement)
Doc8.docx:
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- Variant: S220, W502
- Stakeholder Requirement State: In Review
- System Requirement State: Draft
- Software Requirement State: Draft
- Primary Discipline: SW
- Requirement Type: Functional

##### MS22029826-43480: Diag value for Resistance Calibration (Application Parameter)
Diag value for Resistance Calibration
DiagRWFuelGaugeL1
DiagRWFuelGaugeL2
DiagRWFuelGaugeL3
DiagRWFuelGaugeL4
DiagRWFuelGaugeL5
DiagRWFuelGaugeL6
DiagRWFuelGaugeL7
DiagRWFuelGaugeL8
DiagRWFuelGaugeL9
- Variant: S220, W502
- Stakeholder Requirement State: In Review
- System Requirement State: Draft
- Software Requirement State: Draft
- Primary Discipline: TBD
- Requirement Type: Functional

##### MS22029826-43654: Diag value for Volume Calibration (System Requirement)
Diag value for Volume Calibration
DiagRWFuelGaugeVolL1
DiagRWFuelGaugeVolL2
DiagRWFuelGaugeVolL3
DiagRWFuelGaugeVolL4
DiagRWFuelGaugeVolL5
DiagRWFuelGaugeVolL6
DiagRWFuelGaugeVolL7
DiagRWFuelGaugeVolL8
DiagRWFuelGaugeVolL9
- Variant: S220, W502
- Stakeholder Requirement State: In Review
- System Requirement State: Draft
- Software Requirement State: Draft
- Primary Discipline: SW
- Requirement Type: Functional

##### MS22029826-43648: Diag value for Resistance Calibration (System Requirement)
Diag value for Resistance Calibration
DiagRWDEADVOLUMEL
DiagRWDEADVOLUMEH
DiagRWTankCapacity: (42/45/60) Liters
- Variant: S220, W502
- Stakeholder Requirement State: In Review
- System Requirement State: Draft
- Software Requirement State: Draft
- Primary Discipline: SW
- Requirement Type: Functional

#### MS22029826-34715: Output Requirements (Heading)
- Variant: S220, W502
- Stakeholder Requirement State: In Review
- System Requirement State: Draft
- Software Requirement State: Draft
- Primary Discipline: TBD
- Requirement Type: TBD

##### MS22029826-43390: Fuel Display Fault (System Requirement)
- Variant: S220, W502
- Stakeholder Requirement State: In Review
- System Requirement State: Draft
- Secondary Disciplines: FV
- Software Requirement State: Draft
- Primary Discipline: SW
- Requirement Type: Functional

##### MS22029826-43393: Fuel Disp Bar (System Requirement)
- Variant: S220, W502
- Stakeholder Requirement State: In Review
- System Requirement State: Draft
- Secondary Disciplines: FV
- Software Requirement State: Draft
- Primary Discipline: SW
- Requirement Type: Functional

##### MS22029826-43395: DispFuelStep (System Requirement)
- Variant: S220, W502
- Stakeholder Requirement State: In Review
- System Requirement State: Draft
- Secondary Disciplines: FV
- Software Requirement State: Draft
- Primary Discipline: SW
- Requirement Type: Functional

##### MS22029826-43397: Fuel Sender AD Out – IC6_1000_TEST: FLOAT_RESISTANCE_RAW (Range: 0-5 V, Factor: 0.00489) (System Requirement)
- Variant: S220, W502
- Stakeholder Requirement State: In Review
- System Requirement State: Draft
- Secondary Disciplines: FV
- Software Requirement State: Draft
- Primary Discipline: SW
- Requirement Type: Functional

##### MS22029826-43401: Fuel Sender AD Filt Out – IC6_1000_TEST: FLOAT_RESISTANCE_FILTER (Range: 0-5 V, Factor: 0.00489) (System Requirement)
- Variant: S220, W502
- Stakeholder Requirement State: In Review
- System Requirement State: Draft
- Secondary Disciplines: FV
- Software Requirement State: Draft
- Primary Discipline: SW
- Requirement Type: Functional

##### MS22029826-43403: Fuel Lvl Raw Out – IC6_1000_TEST:FUEL_LVL_RAW (0xFFFE-Default, 0xFFFF-Invalid) (System Requirement)
- Variant: S220, W502
- Stakeholder Requirement State: In Review
- System Requirement State: Draft
- Secondary Disciplines: FV
- Software Requirement State: Draft
- Primary Discipline: SW
- Requirement Type: Functional

##### MS22029826-43405: Fuel Lvl Filt Out – IC6_1000_TEST: FUEL_LVL_DTE_FILTER (0xFFFE-Default, 0xFFFF-Invalid) (System Requirement)
- Variant: S220, W502
- Stakeholder Requirement State: In Review
- System Requirement State: Draft
- Secondary Disciplines: FV
- Software Requirement State: Draft
- Primary Discipline: SW
- Requirement Type: Functional

#### MS22029826-34716: Performance Requirement (Heading)
- Variant: S220, W502
- Stakeholder Requirement State: In Review
- System Requirement State: Draft
- Software Requirement State: Draft
- Primary Discipline: TBD
- Requirement Type: TBD

##### MS22029826-43407: FLPS Per Liter = Maximum FLPS(i.e., 254)/Max. Tank Capacity(i.e., 60) (System Requirement)
- Variant: S220, W502
- Stakeholder Requirement State: In Review
- System Requirement State: Draft
- Secondary Disciplines: FV
- Software Requirement State: Draft
- Primary Discipline: SW
- Requirement Type: Functional

##### MS22029826-43410 (System Requirement)
In case of IGN On, Fuel gauge should indicate the current value after welcome strategy routine.
In case of IGN Off, Fuel gauge display shall be Off.
- Variant: S220, W502
- Stakeholder Requirement State: In Review
- System Requirement State: Draft
- Secondary Disciplines: FV
- Software Requirement State: Draft
- Primary Discipline: SW
- Requirement Type: Functional

##### MS22029826-34718: Table – Fuel Constant Block Storage Parameters (Heading)
- Variant: S220, W502
- Stakeholder Requirement State: In Review
- System Requirement State: Draft
- Software Requirement State: Draft
- Primary Discipline: TBD
- Requirement Type: TBD

###### MS22029826-43412: Fuel Parameter Name (System Requirement)
|  | Fuel Parameter Name | # of Bytes | Range | Scaling / Resolution | Engineering value | Software Value |
| --- | --- | --- | --- | --- | --- | --- |
| 1 | FUEL03_FAST_FILL_ENABLE | 1 bit | 0, 1 | 0 = Disabled, 1 = Enabled | 1 | 1 |
| 2 | FUEL03_MIN_FAST_FILL_TIME | 1 | 1 - 255 | 100ms | 5000ms | 50 |
| 3 | FUEL03_NEGATIVE_FAST_FILL_DELTA | 1 | 1 - 255 | 1 FLPS | 10 L | 42 |
| 4 | FUEL03_POSITIVE_FAST_FILL_DELTA | 1 | 1 - 255 | 1 FLPS | 5 L | 21 |
| 5 | FUEL03_ZERO_SPEED_COUNTER | 2 | 0 - 65535 | 100ms | 13000ms | 130 |
| 6 | FUEL03_OPEN_SHORT_FAULT_TIME | 2 | 0 - 65535 | 100ms | 30000ms | 300 |
| 7 | FUEL03_OPEN_SHORT_RECOVERY_TIME | 2 | 0 - 65535 | 100ms | 30000ms | 300 |
| 8 | FUEL03_SEC_NEG_INIT_FILL_DELTA | 1 | 1 - 255 | 1 FLPS | (DiagRWTankCapacity/2) L | 127 |
| 9 | FUEL03_ SEC_POS_INIT_FILL_DELTA | 1 | 1 - 255 | 1 FLPS | (DiagRWTankCapacity/2) L | 127 |
| 10 | FUEL03_INIT_DELAY_COUNT_TIME | 1 | 0 - 255 | 100ms | 1500ms | 15 |
| 11 | FUEL03_INIT_GOOD_SAMPLES_REQUIRED | 1 | 0 - 255 | 1 Sample | 7 samples | 7 |
| 12 | FUEL03_KEY_ON_DELAY_TIME | 1 | 0 - 255 | 100ms | 300ms | 3 |
| 13 | FUEL03_KEY_OFF_SAMPLE_TIME | 2 | 0 - 65535 | 100ms | 15000ms | 150 |
| 14 | FUEL03_SENDERA_RC_FILL_DELTA | 1 | 1 - 255 | 1 FLPS | 5 L | 21 |
| 15 | FUEL03_SENDERA_RC_FILL_THRESHOLD | 1 | 1 - 255 | 1 FLPS | (DiagRWTankCapacity/2) L | 127 |
| 16 | FUEL03_PERCENT_FULL_NEGATIVE_HYST | 2 | 0 - 65535 | 1/256 FLPS | 0.2 L | 217 |
| 17 | FUEL03_PERCENT_FULL_POSITIVE_HYST | 2 | 0 - 65535 | 1/256 FLPS | 0.4 L | 434 |
- Variant: S220, W502
- Stakeholder Requirement State: In Review
- System Requirement State: Draft
- Secondary Disciplines: FV
- Software Requirement State: Draft
- Primary Discipline: SW
- Requirement Type: Functional

##### MS22029826-34720: Gauge Operation State Transition flow (Heading)
- Variant: S220, W502
- Stakeholder Requirement State: In Review
- System Requirement State: Draft
- Software Requirement State: Draft
- Primary Discipline: TBD
- Requirement Type: TBD

###### MS22029826-43415: diagram : (System Requirement)
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- Variant: S220, W502
- Stakeholder Requirement State: In Review
- System Requirement State: Draft
- Software Requirement State: Draft
- Primary Discipline: SW
- Requirement Type: Functional

###### MS22029826-43417: Fast Fill Entry Flow (System Requirement)
- Variant: S220, W502
- Stakeholder Requirement State: In Review
- System Requirement State: Draft
- Software Requirement State: Draft
- Primary Discipline: SW
- Requirement Type: Functional

###### MS22029826-43419: Fast Fill Entry Flow.docx: Fast Fill... (System Requirement)
Fast Fill Entry Flow.docx
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:
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- Variant: S220, W502
- Stakeholder Requirement State: In Review
- System Requirement State: Draft
- Software Requirement State: Draft
- Primary Discipline: SW
- Requirement Type: Functional

###### MS22029826-43421: Open circuit Resistance: 170 ohms (System Requirement)
Open circuit Resistance: 170 ohms
Short circuit resistance: 10 ohms
- Variant: S220, W502
- Stakeholder Requirement State: In Review
- System Requirement State: Draft
- Secondary Disciplines: FV
- Software Requirement State: Draft
- Primary Discipline: SW
- Requirement Type: Functional

###### MS22029826-120825 (Information)
Based on the variant Diag values to be calibrated and Tested, No Feature code to be associated with the Fuel table
- Variant: S220, S220_SB_ADP_W601-V1, S220_SB_ADP_W601-V2, S225, W502
- Stakeholder Requirement State: In Review
- System Requirement State: Draft
- Secondary Disciplines: FV
- Software Requirement State: Draft
- Primary Discipline: SW
- Requirement Type: Functional

###### MS22029826-43424 (System Requirement)
FUEL TABLE S220 :DiagRWTankCapacity = 42L
| Default Resistance | Liters | Display % | Fuel Step | LFW TT | NVM Parameter for Resistance | NVM Parameter for Volume | Percentage | Fuel step |
| --- | --- | --- | --- | --- | --- | --- | --- | --- |
| >170 | Blink all segments | - | - | Blink at (1/6) HZ | - | - |  |  |
| 141 | 3 | 0 | 0 | Blink at 2HZ | 140 | DEAD VOLUME +L |  |  |
| 136 | 4 | 0 | 0 | Blink at 2HZ | DiagRWFuelGaugeL1 | DiagRWFuelGaugeVolL1 | 0% | 0 |
| 116 | 8 | DiagRWFuelGaugeVolL2/DiagRWTankCapacity | (DiagRWFuelGaugeVolL2/DiagRWTankCapacity)*254 | ON | DiagRWFuelGaugeL2 | DiagRWFuelGaugeVolL2 | 19% | 48 |
| 105 | 11 | DiagRWFuelGaugeVolL3/DiagRWTankCapacity | (DiagRWFuelGaugeVolL3/DiagRWTankCapacity)*254 | OFF | DiagRWFuelGaugeL3 | DiagRWFuelGaugeVolL3 | 26% | 67 |
| 84 | 16 | DiagRWFuelGaugeVolL4/DiagRWTankCapacity | (DiagRWFuelGaugeVolL4/DiagRWTankCapacity)*254 | OFF | DiagRWFuelGaugeL4 | DiagRWFuelGaugeVolL4 | 38% | 97 |
| 65 | 21 | DiagRWFuelGaugeVolL5/DiagRWTankCapacity | (DiagRWFuelGaugeVolL5/DiagRWTankCapacity)*254 | OFF | DiagRWFuelGaugeL5 | DiagRWFuelGaugeVolL5 | 50% | 127 |
| 49 | 26 | DiagRWFuelGaugeVolL6/DiagRWTankCapacity | (DiagRWFuelGaugeVolL6/DiagRWTankCapacity)*254 | OFF | DiagRWFuelGaugeL6 | DiagRWFuelGaugeVolL6 | 62% | 157 |
| 39 | 31 | DiagRWFuelGaugeVolL7/DiagRWTankCapacity | (DiagRWFuelGaugeVolL7/DiagRWTankCapacity)*254 | OFF | DiagRWFuelGaugeL7 | DiagRWFuelGaugeVolL7 | 74% | 187 |
| 29 | 35 | DiagRWFuelGaugeVolL8/DiagRWTankCapacity | (DiagRWFuelGaugeVolL8/DiagRWTankCapacity)*254 | OFF | DiagRWFuelGaugeL8 | DiagRWFuelGaugeVolL8 | 83% | 212 |
| 24 | 39 | 100 | 254 | OFF | DiagRWFuelGaugeL9 | DiagRWFuelGaugeVolL9 | 100% | 254 |
| 20 | 40 | 100 | 254 | OFF | 20 | DEAD VOLUME +H |  |  |
| <10 | Blink all segments | 0 | Blink at (1/6) HZ | - | - |  |  |  |
- Variant: S220
- Stakeholder Requirement State: In Review
- System Requirement State: Draft
- Secondary Disciplines: FV
- Software Requirement State: Draft
- Primary Discipline: SW
- Requirement Type: Functional

###### MS22029826-43426: FUEL TABLE W502 DiagRWTankCapacity= 45L (System Requirement)
FUEL TABLE W502 DiagRWTankCapacity= 45L
| Default Resistance | Liters | Display % | Fuel Step | LFW TT | NVM Parameter for Resistance | NVM Parameter for Volume | Percentage | Fuel step |
| --- | --- | --- | --- | --- | --- | --- | --- | --- |
| >170 | Blink all segments | - | - | Blink at (1/6) HZ | - | - |  |  |
| 140 | 3 | 0 | 0 | Blink at 2HZ | 140 | DiagRWDEADVOLUMEL |  |  |
| 133 | 4 | 0 | 0 | Blink at 2HZ | DiagRWFuelGaugeL1 | DiagRWFuelGaugeVolL1 | 0% | 0 |
| 115 | 9 | DiagRWFuelGaugeVolL2/DiagRWTankCapacity | (DiagRWFuelGaugeVolL2/DiagRWTankCapacity)*254 | ON | DiagRWFuelGaugeL2 | DiagRWFuelGaugeVolL2 | 20% | 51 |
| 108 | 11 | DiagRWFuelGaugeVolL3/DiagRWTankCapacity | (DiagRWFuelGaugeVolL3/DiagRWTankCapacity)*254 | OFF | DiagRWFuelGaugeL3 | DiagRWFuelGaugeVolL3 | 24% | 62 |
| 92 | 16 | DiagRWFuelGaugeVolL4/DiagRWTankCapacity | (DiagRWFuelGaugeVolL4/DiagRWTankCapacity)*254 | OFF | DiagRWFuelGaugeL4 | DiagRWFuelGaugeVolL4 | 36% | 90 |
| 76 | 22 | DiagRWFuelGaugeVolL5/DiagRWTankCapacity | (DiagRWFuelGaugeVolL5/DiagRWTankCapacity)*254 | OFF | DiagRWFuelGaugeL5 | DiagRWFuelGaugeVolL5 | 49% | 124 |
| 60 | 27 | DiagRWFuelGaugeVolL6/DiagRWTankCapacity | (DiagRWFuelGaugeVolL6/DiagRWTankCapacity)*254 | OFF | DiagRWFuelGaugeL6 | DiagRWFuelGaugeVolL6 | 60% | 152 |
| 43 | 33 | DiagRWFuelGaugeVolL7/DiagRWTankCapacity | (DiagRWFuelGaugeVolL7/DiagRWTankCapacity)*254 | OFF | DiagRWFuelGaugeL7 | DiagRWFuelGaugeVolL7 | 73% | 186 |
| 31 | 37 | DiagRWFuelGaugeVolL8/DiagRWTankCapacity | (DiagRWFuelGaugeVolL8/DiagRWTankCapacity)*254 | OFF | DiagRWFuelGaugeL8 | DiagRWFuelGaugeVolL8 | 82% | 209 |
| 24 | 41 | 100 | 254 | OFF | DiagRWFuelGaugeL9 | DiagRWFuelGaugeVolL9 | 100% | 254 |
| 20 | 42 | 100 | 254 | OFF | 20 | DiagRWDEADVOLUMEH |  |  |
| <10 | Blink all segments | 0 | Blink at (1/6) HZ | - | - |  |  |  |
- Variant: W502
- Stakeholder Requirement State: In Review
- System Requirement State: Draft
- Secondary Disciplines: FV
- Software Requirement State: Draft
- Primary Discipline: SW
- Requirement Type: Functional

###### MS22029826-72252: FUEL TABLE for W502 -60 L (System Requirement)
FUEL TABLE for W502 -60 L
| Default Resistance | Liters | Display % | Fuel Step | LFW TT | NVM Parameter for Resistance | NVM Parameter for Volume | Percentage | Fuel step |
| --- | --- | --- | --- | --- | --- | --- | --- | --- |
| >170 | Blink all segments | - | - | Blink at (1/6) HZ | - | - |  |  |
| 140 | 3 | 0 | 0 | Blink at 2HZ | 140 | DiagRWDEADVOLUMEL |  |  |
| 136 | 5 | 0 | 0 | Blink at 2HZ | DiagRWFuelGaugeL1 | DiagRWFuelGaugeVolL1 | 0% | 0.00 |
| 118 | 12 | DiagRWFuelGaugeVolL2/DiagRWTankCapacity | (DiagRWFuelGaugeVolL2/DiagRWTankCapacity)*254 | ON | DiagRWFuelGaugeL2 | DiagRWFuelGaugeVolL2 | 20% | 50.80 |
| 111 | 15 | DiagRWFuelGaugeVolL3/DiagRWTankCapacity | (DiagRWFuelGaugeVolL3/DiagRWTankCapacity)*254 | OFF | DiagRWFuelGaugeL3 | DiagRWFuelGaugeVolL3 | 25% | 63.50 |
| 95 | 22 | DiagRWFuelGaugeVolL4/DiagRWTankCapacity | (DiagRWFuelGaugeVolL4/DiagRWTankCapacity)*254 | OFF | DiagRWFuelGaugeL4 | DiagRWFuelGaugeVolL4 | 37% | 93.13 |
| 79 | 30 | DiagRWFuelGaugeVolL5/DiagRWTankCapacity | (DiagRWFuelGaugeVolL5/DiagRWTankCapacity)*254 | OFF | DiagRWFuelGaugeL5 | DiagRWFuelGaugeVolL5 | 50% | 127.00 |
| 62 | 37 | DiagRWFuelGaugeVolL6/DiagRWTankCapacity | (DiagRWFuelGaugeVolL6/DiagRWTankCapacity)*254 | OFF | DiagRWFuelGaugeL6 | DiagRWFuelGaugeVolL6 | 62% | 156.63 |
| 46 | 44 | DiagRWFuelGaugeVolL7/DiagRWTankCapacity | (DiagRWFuelGaugeVolL7/DiagRWTankCapacity)*254 | OFF | DiagRWFuelGaugeL7 | DiagRWFuelGaugeVolL7 | 73% | 186.27 |
| 34 | 50 | DiagRWFuelGaugeVolL8/DiagRWTankCapacity | (DiagRWFuelGaugeVolL8/DiagRWTankCapacity)*254 | OFF | DiagRWFuelGaugeL8 | DiagRWFuelGaugeVolL8 | 83% | 211.67 |
| 24 | 57 | 100 | 254 | OFF | DiagRWFuelGaugeL9 | DiagRWFuelGaugeVolL9 | 100% | 254.00 |
| 20 | 58 | 100 | 254 | OFF | 20 | DiagRWDEADVOLUMEH |  |  |
| <10 | Blink all segments | 0 | Blink at (1/6) HZ | - | - |  |  |  |
- Variant: W502
- Stakeholder Requirement State: In Review
- System Requirement State: Draft
- Secondary Disciplines: FV
- Software Requirement State: Draft
- Primary Discipline: SW
- Requirement Type: Functional

###### MS22029826-120455: FUEL TABLE S220 Silverbox adaptation :DiagRWTankCapacity = 60L (System Requirement)
FUEL TABLE S220 Silver box adaptation: DiagRWTankCapacity = 60L
| Default Resistance | Liters | Display % | Fuel Step | LFW TT | NVM Parameter for Resistance | NVM Parameter for Volume | Percentage | Fuel step |
| --- | --- | --- | --- | --- | --- | --- | --- | --- |
| >170 | Blink all segments | - | - | Blink at (1/6) HZ | - | - |  |  |
| 140 | 3 | 0 | 0 | Blink at 2HZ | 140 | DiagRWDEADVOLUMEL |  |  |
| 136 | 5 | 0 | 0 | Blink at 2HZ | DiagRWFuelGaugeL1 | DiagRWFuelGaugeVolL1 | 0% | 0 |
| 118 | 12 | DiagRWFuelGaugeVolL2/DiagRWTankCapacity | (DiagRWFuelGaugeVolL2/DiagRWTankCapacity)*254 | ON | DiagRWFuelGaugeL2 | DiagRWFuelGaugeVolL2 | 20% | 51 |
| 111 | 15 | DiagRWFuelGaugeVolL3/DiagRWTankCapacity | (DiagRWFuelGaugeVolL3/DiagRWTankCapacity)*254 | OFF | DiagRWFuelGaugeL3 | DiagRWFuelGaugeVolL3 | 25% | 63.75 |
| 97 | 24 | DiagRWFuelGaugeVolL4/DiagRWTankCapacity | (DiagRWFuelGaugeVolL4/DiagRWTankCapacity)*254 | OFF | DiagRWFuelGaugeL4 | DiagRWFuelGaugeVolL4 | 40% | 102 |
| 85 | 30 | DiagRWFuelGaugeVolL5/DiagRWTankCapacity | (DiagRWFuelGaugeVolL5/DiagRWTankCapacity)*254 | OFF | DiagRWFuelGaugeL5 | DiagRWFuelGaugeVolL5 | 50% | 127.5 |
| 75 | 37 | DiagRWFuelGaugeVolL6/DiagRWTankCapacity | (DiagRWFuelGaugeVolL6/DiagRWTankCapacity)*254 | OFF | DiagRWFuelGaugeL6 | DiagRWFuelGaugeVolL6 | 62% | 157.25 |
| 63 | 44 | DiagRWFuelGaugeVolL7/DiagRWTankCapacity | (DiagRWFuelGaugeVolL7/DiagRWTankCapacity)*254 | OFF | DiagRWFuelGaugeL7 | DiagRWFuelGaugeVolL7 | 73% | 187 |
| 47 | 49 | DiagRWFuelGaugeVolL8/DiagRWTankCapacity | (DiagRWFuelGaugeVolL8/DiagRWTankCapacity)*254 | OFF | DiagRWFuelGaugeL8 | DiagRWFuelGaugeVolL8 | 82% | 208.25 |
| 24 | 57 | 100 | 255 | OFF | DiagRWFuelGaugeL9 | DiagRWFuelGaugeVolL9 | 100% | 255 |
| 20 | 58 | 100 | 254 | OFF | 20 | DiagRWDEADVOLUMEH |  |  |
| <10 | Blink all segments | 0 | Blink at (1/6) HZ | - | - |  |  |  |
- Variant: S220_SB_ADP_W601-V1, S220_SB_ADP_W601-V2
- Stakeholder Requirement State: In Review
- System Requirement State: Draft
- Secondary Disciplines: FV
- Software Requirement State: Draft
- Primary Discipline: SW
- Requirement Type: Functional

###### MS22029826-43428 (System Requirement)
The Resistance and Volume value shall be calibrated through DID.
DiagRWDEADVOLUMEL - Lower Dead Volume in tank
DiagRWDEADVOLUMEH -High Dead Volume in tank
DiagRWTankCapacity -Based on Tank capacity (42/45/60) liters.
Below points need to be noted While calibration:
1. Fuel step less than DiagRWFuelGaugeL1/DiagRWFuelGaugeVolL1 corresponds to Tank Empty.
The Fuel shall display Empty Guage.
1. Fuel step corresponding to DiagRWFuelGaugeL2/DiagRWFuelGaugeVolL2 corresponds to Tank Reserved.
Red line in fuel Guage shall be Indicated for the same. TT shall be ON.
3.The Red Line shall always correspond to 20% with ± 2 Tolerance.
4..DiagRWFuelGaugeVolL3 Corresponds to 25% Of fuel in tank display in Fuel Guage with ± 2Tolerance
DiagRWFuelGaugeVolL5 Corresponds to 50% Of fuel in tank display in Fuel Guage with ± 2Tolerance
DiagRWFuelGaugeVolL7 Corresponds to 75% Of fuel in tank display in Fuel Guage with ± 2Tolerance
DiagRWFuelGaugeVolL9 Corresponds to 100% Of fuel in tank display in Fuel Guage with ± 2Tolerance
4.Difference between two successive resistance values shall be no less that 2x Tolerance( 2*2ohms)
5.If the above points 3 & 4 are not followed during calibration NRC 22 [Conditions not correct] shall be provided.
- Variant: S220, W502
- Stakeholder Requirement State: In Review
- System Requirement State: Draft
- Secondary Disciplines: FV
- Software Requirement State: Draft
- Primary Discipline: SW
- Requirement Type: Functional

###### MS22029826-43430 (System Requirement)
IC shall add a display hysteresis to fuel indication to prevent fluctuation as below
fuel.docx:
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- Variant: S220, W502
- Stakeholder Requirement State: In Review
- System Requirement State: Draft
- Software Requirement State: Draft
- Primary Discipline: SW
- Requirement Type: Functional

###### MS22029826-43431: DETERMINE FUEL HYSTERESIS: (System Requirement)
DETERMINE FUEL HYSTERESIS:
Determine_full_hys.docx:
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- Variant: S220, W502
- Stakeholder Requirement State: In Review
- System Requirement State: Draft
- Software Requirement State: Draft
- Primary Discipline: SW
- Requirement Type: Functional

###### MS22029826-43433: APPLY HYSTERESIS (System Requirement)
APPLY HYSTERESIS
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- Variant: S220, W502
- Stakeholder Requirement State: In Review
- System Requirement State: Draft
- Software Requirement State: Draft
- Primary Discipline: SW
- Requirement Type: Functional

###### MS22029826-43435: Parameter table : (System Requirement)
| Parameter | Description | Size | Default | Min | Max | Unit |
| --- | --- | --- | --- | --- | --- | --- |
| DISP_HYST | Hysteresis for displayed fuel | 1 | 8 | 1 | 50 | No Unit |
| FILL_HYST | Hysteresis during refuel | 1 | 0 | 1 | 50 | No Unit |
| FUELFULL | Fuel Full Step | 1 | 255 | 0 | 255 | No Unit |
| FUELEMPTY | Fuel Empty Step | 1 | 0 | 0 | 255 | No Unit |
- Variant: S220, W502
- Stakeholder Requirement State: In Review
- System Requirement State: Draft
- Software Requirement State: Draft
- Primary Discipline: SW
- Requirement Type: Functional

###### MS22029826-43437 (System Requirement)
DispFuelStep Shall be intialized to FuelStep on Ignition Transition, once fuel fill/loss is detected as below
DispFuelStep.docx:
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- Variant: S220, W502
- Stakeholder Requirement State: In Review
- System Requirement State: Draft
- Software Requirement State: Draft
- Primary Discipline: SW
- Requirement Type: Functional

###### MS22029826-43440: Fuel Slew Parameter is incremented with 1 step every 100ms (System Requirement)
- Variant: S220, W502
- Stakeholder Requirement State: In Review
- System Requirement State: Draft
- Software Requirement State: Draft
- Primary Discipline: SW
- Requirement Type: Functional

###### MS22029826-43442: The Gauge shall damp the input using a filter, and under normal mode a change from E bar to F bar and vice versa shall take not less than 40 minutes and this value is not configurable (System Requirement)
- Variant: S220, W502
- Stakeholder Requirement State: In Review
- System Requirement State: Draft
- Software Requirement State: Draft
- Primary Discipline: SW
- Requirement Type: Functional

###### MS22029826-43444: In fast fill mode, the fuel gauge E to F response time shall be less than 60 seconds. (System Requirement)
- Variant: S220, W502
- Stakeholder Requirement State: In Review
- System Requirement State: Draft
- Software Requirement State: Draft
- Primary Discipline: SW
- Requirement Type: Functional

###### MS22029826-43447 (System Requirement)
During ignition cycling (IGN ON to OFF) the IC shall memorize the fuel level value at ignition off (Key off Reference) to be used in next cycle. If no key off reference is available then IC shall display previous displayed value till initialization is complete.
- Variant: S220, W502
- Stakeholder Requirement State: In Review
- System Requirement State: Draft
- Secondary Disciplines: FV
- Software Requirement State: Draft
- Primary Discipline: SW
- Requirement Type: Functional

###### MS22029826-43449: Then if after (1500ms + 300ms), a change in fuel level is detected then the fuel gauge should be updated to the new fuel level. (System Requirement)
- Variant: S220, W502
- Stakeholder Requirement State: In Review
- System Requirement State: Draft
- Secondary Disciplines: FV
- Software Requirement State: Draft
- Primary Discipline: SW
- Requirement Type: Functional

###### MS22029826-43451: Key OFF sampling time = 15sec. (System Requirement)
- Variant: S220, W502
- Stakeholder Requirement State: In Review
- System Requirement State: Draft
- Secondary Disciplines: FV
- Software Requirement State: Draft
- Primary Discipline: SW
- Requirement Type: Functional

###### MS22029826-43454: Current fuel level in milliliters shall be transmitted in CAN. (System Requirement)
- Variant: S220, W502
- Stakeholder Requirement State: In Review
- System Requirement State: Draft
- Secondary Disciplines: FV
- Software Requirement State: Draft
- Primary Discipline: SW
- Requirement Type: Functional

###### MS22029826-43456: The fuel gauge shall have a response time of 2.5 seconds or less from the key off zero position to the maximum indication possible upon cluster power on. (System Requirement)
- Variant: S220, W502
- Stakeholder Requirement State: In Review
- System Requirement State: Draft
- Secondary Disciplines: FV
- Software Requirement State: Draft
- Primary Discipline: SW
- Requirement Type: Functional

###### MS22029826-43459: Shall provide the ability to indicate fuel volume changes quickly while the vehicle is stopped (Speed<0.5 Kmph) for more than 13 seconds with IGN ON. (System Requirement)
- Variant: S220, W502
- Stakeholder Requirement State: In Review
- System Requirement State: Draft
- Secondary Disciplines: FV
- Software Requirement State: Draft
- Primary Discipline: SW
- Requirement Type: Functional

###### MS22029826-43461: With IGN ON (not first IGN ON after battery connect) and speed <0.5 Km/h, cluster shall wait for 13 sec and store fuel level at that instanct as ‘FUEL ref’ ( Fuel reference value). (System Requirement)
- Variant: S220, W502
- Stakeholder Requirement State: In Review
- System Requirement State: Draft
- Secondary Disciplines: FV
- Software Requirement State: Draft
- Primary Discipline: SW
- Requirement Type: Functional

###### MS22029826-43464 (System Requirement)
Cluster shall compare value of FUEL ref with FUEL pre to decide entry to Fast Fill mode.
Fast Fuel shall be entered in any of the following 2 cases.
a. When the fuel volume changes (increase) by more than 5 liters if the current fuel volume is less than (DiagRWFuelGaugeVolL9/2) Liters.
b. When the fuel volume changes (decrease) by more than 10 liters if the current fuel volume is less than (DiagRWFuelGaugeVolL9/2) Liters.
c. When the fuel volume changes (increase) by more than 5 liters, if the current fuel volume is more is than DiagRWFuelGaugeVolL9/2) Liters.
- Variant: S220, W502
- Stakeholder Requirement State: In Review
- System Requirement State: Draft
- Secondary Disciplines: FV
- Software Requirement State: Draft
- Primary Discipline: SW
- Requirement Type: Functional

###### MS22029826-43466: A change in Fuel level shall be detected only when the change in Fuel level by 0.4liter (positive hysteresis) by 0.2liter (negative hysteresis). (System Requirement)
- Variant: S220, W502
- Stakeholder Requirement State: In Review
- System Requirement State: Draft
- Secondary Disciplines: FV
- Software Requirement State: Draft
- Primary Discipline: SW
- Requirement Type: Functional

##### MS22029826-34722: Fail Safe Requirements (Heading)
- Variant: S220, W502
- Stakeholder Requirement State: In Review
- System Requirement State: Draft
- Software Requirement State: Draft
- Primary Discipline: TBD
- Requirement Type: TBD

###### MS22029826-43468: When open/short circuit detected >=30 seconds: Gauge shall blink at (1/6) Hz. i.e 3 sec ON and 3 sec OFF. (System Requirement)
- Variant: S220, W502
- Stakeholder Requirement State: In Review
- System Requirement State: Draft
- Secondary Disciplines: FV
- Software Requirement State: Draft
- Primary Discipline: SW
- Requirement Type: Functional

###### MS22029826-43471: When open/short circuit detected at key ON >= 30 seconds: Gauge shall blink at (1/6) Hz. i.e 3 sec ON and 3 sec OFF. (System Requirement)
- Variant: S220, W502
- Stakeholder Requirement State: In Review
- System Requirement State: Draft
- Secondary Disciplines: FV
- Software Requirement State: Draft
- Primary Discipline: SW
- Requirement Type: Functional

###### MS22029826-43473: Open/short circuit recovery: Gauge shall recover to normal reading after 30 seconds of valid input. While recovering from error input cluster shall sample the input for 30 sec and after 30 sec shall indicate immediately the respective fuel level. (System Requirement)
- Variant: S220, W502
- Stakeholder Requirement State: In Review
- System Requirement State: Draft
- Secondary Disciplines: FV
- Software Requirement State: Draft
- Primary Discipline: SW
- Requirement Type: Functional

###### MS22029826-43475: If the fuel sender is short / open, IC shall send the failsafe value (0xFFFF) through FUEL_LEVEL CAN signal. (System Requirement)
- Variant: S220, W502
- Stakeholder Requirement State: In Review
- System Requirement State: Draft
- Secondary Disciplines: FV
- Software Requirement State: Draft
- Primary Discipline: SW
- Requirement Type: Functional

###### MS22029826-43478: When Low or high voltage state (before debounce): Gauge shall operate normally. (System Requirement)
- Variant: S220, W502
- Stakeholder Requirement State: In Review
- System Requirement State: Draft
- Secondary Disciplines: FV
- Software Requirement State: Draft
- Primary Discipline: SW
- Requirement Type: Functional

###### MS22029826-43482: When normal voltage recovered (after debounce): Gauge shall display the actual status. (System Requirement)
- Variant: S220, W502
- Stakeholder Requirement State: In Review
- System Requirement State: Draft
- Secondary Disciplines: FV
- Software Requirement State: Draft
- Primary Discipline: SW
- Requirement Type: Functional

### MS22029826-34699: Temperature Gauge (Heading)
- Variant: S220, W502
- Stakeholder Requirement State: In Review
- System Requirement State: Draft
- Software Requirement State: Draft
- Primary Discipline: TBD
- Requirement Type: TBD

#### MS22029826-43658: Temperature gauge indicates the engine temperature of vehicle. Input to the cluster is through engine management system. (System Requirement)
- Variant: S220, W502
- Stakeholder Requirement State: In Review
- System Requirement State: Draft
- Secondary Disciplines: FV
- Software Requirement State: Draft
- Primary Discipline: SW
- Requirement Type: Functional

#### MS22029826-34701: Input Requirements (Heading)
- Variant: S220, W502
- Stakeholder Requirement State: In Review
- System Requirement State: Draft
- Software Requirement State: Draft
- Primary Discipline: TBD
- Requirement Type: TBD

##### MS22029826-43660: LVSD / HVSD Flag (System Requirement)
- Variant: S220, W502
- Stakeholder Requirement State: In Review
- System Requirement State: Draft
- Secondary Disciplines: FV
- Software Requirement State: Draft
- Primary Discipline: SW
- Requirement Type: Functional

##### MS22029826-43662: Eng Temp In: EMS1_10:ENG_TEMP (Value: 0x82-Default, Range: -40 degC ~ 214 degC, Offset: -40) (System Requirement)
- Variant: S220, W502
- Stakeholder Requirement State: In Review
- System Requirement State: Draft
- Secondary Disciplines: FV
- Software Requirement State: Draft
- Primary Discipline: SW
- Requirement Type: Functional

##### MS22029826-43664: VAR_CODING_ENGINE_MANAGEMENT_SYSTEM (0-Not Present, 1-Present) (System Requirement)
- Variant: S220, W502
- Stakeholder Requirement State: In Review
- System Requirement State: Draft
- Secondary Disciplines: FV
- Software Requirement State: Draft
- Primary Discipline: SW
- Requirement Type: Functional

##### MS22029826-43666: Doc7.docx: (System Requirement)
Doc7.docx:
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- Variant: S220, W502
- Stakeholder Requirement State: In Review
- System Requirement State: Draft
- Software Requirement State: Draft
- Primary Discipline: SW
- Requirement Type: Functional

#### MS22029826-34703: Output Requirements (Heading)
- Variant: S220, W502
- Stakeholder Requirement State: In Review
- System Requirement State: Draft
- Software Requirement State: Draft
- Primary Discipline: TBD
- Requirement Type: TBD

##### MS22029826-43668: ECT Gauge Disp % (System Requirement)
- Variant: S220, W502
- Stakeholder Requirement State: In Review
- System Requirement State: Draft
- Secondary Disciplines: FV
- Software Requirement State: Draft
- Primary Discipline: SW
- Requirement Type: Functional

#### MS22029826-34705: Performance Requirements (Heading)
- Variant: S220, W502
- Stakeholder Requirement State: In Review
- System Requirement State: Draft
- Software Requirement State: Draft
- Primary Discipline: TBD
- Requirement Type: TBD

##### MS22029826-43670: Gauge Operation State Transition flow (System Requirement)
- Variant: S220, W502
- Stakeholder Requirement State: In Review
- System Requirement State: Draft
- Secondary Disciplines: FV
- Software Requirement State: Draft
- Primary Discipline: SW
- Requirement Type: Functional

##### MS22029826-43672: Diagram : Gauge Operation State Transition flow (System Requirement)
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- Variant: S220, W502
- Stakeholder Requirement State: In Review
- System Requirement State: Draft
- Software Requirement State: Draft
- Primary Discipline: SW
- Requirement Type: Functional

##### MS22029826-43674: The Engine Coolant Temperature gauge shall be functional only in IGN ON (System Requirement)
- Variant: S220, W502
- Stakeholder Requirement State: In Review
- System Requirement State: Draft
- Secondary Disciplines: FV
- Software Requirement State: Draft
- Primary Discipline: SW
- Requirement Type: Functional

##### MS22029826-43676: In case of IGN Off, display shall be off. (System Requirement)
- Variant: S220, W502
- Stakeholder Requirement State: In Review
- System Requirement State: Draft
- Secondary Disciplines: FV
- Software Requirement State: Draft
- Primary Discipline: SW
- Requirement Type: Functional

##### MS22029826-43678: The pointer shall move smoothly & continuously from low to high indication without any step / jerk movement within a span of 3 secs (System Requirement)
- Variant: S220, W502
- Stakeholder Requirement State: In Review
- System Requirement State: Draft
- Secondary Disciplines: FV
- Software Requirement State: Draft
- Primary Discipline: SW
- Requirement Type: Functional

##### MS22029826-43680: The pointer shall respond to the given input within 100 ms (System Requirement)
- Variant: S220, W502
- Stakeholder Requirement State: In Review
- System Requirement State: Draft
- Secondary Disciplines: FV
- Software Requirement State: Draft
- Primary Discipline: SW
- Requirement Type: Functional

##### MS22029826-43682: The response of the Tachometer gauge shall be defined by the 2-stage filter constants T11 =3, T12 = 3. (System Requirement)
- Variant: S220, W502
- Stakeholder Requirement State: In Review
- System Requirement State: Draft
- Secondary Disciplines: FV
- Software Requirement State: Draft
- Primary Discipline: SW
- Requirement Type: Functional

##### MS22029826-34707: Temperature gauge table: (Heading)
- Variant: S220, W502
- Stakeholder Requirement State: In Review
- System Requirement State: Draft
- Software Requirement State: Draft
- Primary Discipline: TBD
- Requirement Type: TBD

###### MS22029826-43684: S.No (System Requirement)
| S.No | Temperature value (Deg C) | Temperature value (Dec) | Parameter | Pointer Indication (%) |
| --- | --- | --- | --- | --- |
| 1 | -40 | 0 | - | 0 |
| 2 | 10 | 50 | DiagRWTempGaugeLUT1 | 0 |
| 3 | 50 | 90 | DiagRWTempGaugeLUT2 | 25 |
| 4 | 70 | 110 | DiagRWTempGaugeLUT3 | 38 |
| 5 | 90 | 130 | DiagRWTempGaugeLUT4 | 50 |
| 6 | 101 | 141 | DiagRWTempGaugeLUT5 | 50 |
| 7 | 106 | 146 | DiagRWTempGaugeLUT6 | 65 |
| 8 | 109 | 149 | DiagRWTempGaugeLUT7 | 65 |
| 9 | 110 | 150 | DiagRWTempGaugeLUT8 | 82.5 |
| 10 | 113 | 153 | DiagRWTempGaugeLUT9 | 82.5 |
| 11 | 114 | 154 | DiagRWTempGaugeLUT10 | 100 |
| 12 | 214 | 254 | - | 100 |
- Variant: S220, W502
- Stakeholder Requirement State: In Review
- System Requirement State: Draft
- Software Requirement State: Draft
- Primary Discipline: SW
- Requirement Type: Functional

###### MS22029826-43686 (System Requirement)
In forward Direction No Hysteresis is applied.
In Reverse Direction 3 Hysteresis parameters are applicable:
Case1: Exit of fault
Case2:Exit of Critical
Case 3: Normal-2 Deg Hysteresis
- Variant: S220, W502
- Stakeholder Requirement State: In Review
- System Requirement State: Draft
- Software Requirement State: Draft
- Primary Discipline: SW
- Requirement Type: Functional

###### MS22029826-43688: When the Temperature value is >= DiagRWTempGaugeLUT8, the gauge shall indicate critical state (System Requirement)
- Variant: S220, W502
- Stakeholder Requirement State: In Review
- System Requirement State: Draft
- Secondary Disciplines: FV
- Software Requirement State: Draft
- Primary Discipline: SW
- Requirement Type: Functional

###### MS22029826-43690: When the Temperature value is >= DiagRWTempGaugeLUT10, the gauge shall indicate fault state (System Requirement)
- Variant: S220, W502
- Stakeholder Requirement State: In Review
- System Requirement State: Draft
- Secondary Disciplines: FV
- Software Requirement State: Draft
- Primary Discipline: SW
- Requirement Type: Functional

###### MS22029826-43692 (System Requirement)
There shall be a hysteresis of 4 deg C (DiagRWTempGaugeFaultHysteris) in case of exit from Fault states
There shall be a hysteresis of 4 deg Critical (DiagRWTempGaugeCritaicalHysteris) in case of exit from Critical states
- Variant: S220, W502
- Stakeholder Requirement State: In Review
- System Requirement State: Draft
- Secondary Disciplines: FV
- Software Requirement State: Draft
- Primary Discipline: SW
- Requirement Type: Functional

###### MS22029826-43694: Diagram : (System Requirement)
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- Variant: S220, W502
- Stakeholder Requirement State: In Review
- System Requirement State: Draft
- Secondary Disciplines: FV
- Software Requirement State: Draft
- Primary Discipline: SW
- Requirement Type: Functional

###### MS22029826-43696: Case: Critical (System Requirement)
Case: Critical
Gauge Normal (Y) to Blink (X)
Entry @ >= DiagRWTempGaugeLUT8
Exit @ < =DiagRWTempGaugeLUT8 – DiagRWTempGaugeCriticalHysteris
Case: Fault
Gauge Blink (Y) to Fault (X)
Entry @ >= DiagRWTempGaugeLUT10
Exit @ <= DiagRWTempGaugeLUT10 - DiagRWTempGaugeFaultHysteris
- Variant: S220, W502
- Stakeholder Requirement State: In Review
- System Requirement State: Draft
- Software Requirement State: Draft
- Primary Discipline: SW
- Requirement Type: Functional

##### MS22029826-34709: Fail Safe Requirements (Heading)
- Variant: S220, W502
- Stakeholder Requirement State: In Review
- System Requirement State: Draft
- Software Requirement State: Draft
- Primary Discipline: TBD
- Requirement Type: TBD

###### MS22029826-43700: When CAN message is missing: Display empty gauge. (System Requirement)
- Variant: S220, W502
- Stakeholder Requirement State: In Review
- System Requirement State: Draft
- Secondary Disciplines: FV
- Software Requirement State: Draft
- Primary Discipline: SW
- Requirement Type: Functional

###### MS22029826-43702: When CAN message value 0xFF (invalid): All segments to be ON. (System Requirement)
- Variant: S220, W502
- Stakeholder Requirement State: In Review
- System Requirement State: Draft
- Secondary Disciplines: FV
- Software Requirement State: Draft
- Primary Discipline: SW
- Requirement Type: Functional

###### MS22029826-43703: If VAR_CODING_ENGINE_MANAGEMENT_SYSTEM is Not Present (0x0), Display empty gauge. (System Requirement)
If VAR_CODING_ENGINE_MANAGEMENT_SYSTEMis Not Present (0x0), Display empty gauge.
- Variant: S220, W502
- Stakeholder Requirement State: In Review
- System Requirement State: Draft
- Secondary Disciplines: FV
- Software Requirement State: Draft
- Primary Discipline: SW
- Requirement Type: Functional

###### MS22029826-43705: Fault Recovery shall follow the Unlog debounce time. (System Requirement)
- Variant: S220, W502
- Stakeholder Requirement State: In Review
- System Requirement State: Draft
- Secondary Disciplines: FV
- Software Requirement State: Draft
- Primary Discipline: SW
- Requirement Type: Functional

###### MS22029826-43707: When Low or high voltage state (before debounce): Display shall operate normally. (System Requirement)
- Variant: S220, W502
- Stakeholder Requirement State: In Review
- System Requirement State: Draft
- Secondary Disciplines: FV
- Software Requirement State: Draft
- Primary Discipline: SW
- Requirement Type: Functional

###### MS22029826-43709: When Low or high voltage state (after debounce): Display shall be off. (System Requirement)
- Variant: S220, W502
- Stakeholder Requirement State: In Review
- System Requirement State: Draft
- Secondary Disciplines: FV
- Software Requirement State: Draft
- Primary Discipline: SW
- Requirement Type: Functional

###### MS22029826-43711: When normal voltage recovered (after debounce): Display shall operate normally. (System Requirement)
- Variant: S220, W502
- Stakeholder Requirement State: In Review
- System Requirement State: Draft
- Secondary Disciplines: FV
- Software Requirement State: Draft
- Primary Discipline: SW
- Requirement Type: Functional

###### MS22029826-43714: Battery disconnected state: Display shall be off. (System Requirement)
- Variant: S220, W502
- Stakeholder Requirement State: In Review
- System Requirement State: Draft
- Secondary Disciplines: FV
- Software Requirement State: Draft
- Primary Discipline: SW
- Requirement Type: Functional

### MS22029826-72346: Power-Regen (Heading)
- Variant: S237
- Stakeholder Requirement State: In Review
- System Requirement State: Draft
- Software Requirement State: Draft
- Primary Discipline: TBD
- Requirement Type: TBD

#### MS22029826-72347: Input Requirements (Heading)
- Variant: S237
- Stakeholder Requirement State: In Review
- System Requirement State: Draft
- Software Requirement State: Draft
- Primary Discipline: TBD
- Requirement Type: TBD

##### MS22029826-43338: POWER -REGEN Preconditions (System Requirement)
- Variant: S237
- Stakeholder Requirement State: In Review
- System Requirement State: Draft
- Software Requirement State: Draft
- Primary Discipline: SW
- Requirement Type: Functional

##### MS22029826-43316: Msg ID Msg Name (System Requirement)
| Msg ID | Msg Name | Signal Name | Factor | Value Description |
| --- | --- | --- | --- | --- |
| 0x2E7 | VCU11_50 | POWER_REGEN_ME TER | 1 | -100 to 100% Offset: - 100 |
- Variant: S237
- Stakeholder Requirement State: In Review
- System Requirement State: Draft
- Software Requirement State: Draft
- Primary Discipline: SW
- Requirement Type: Non-Functional

#### MS22029826-72348: Output Requirements (Heading)
- Variant: S237
- Stakeholder Requirement State: In Review
- System Requirement State: Draft
- Software Requirement State: Draft
- Primary Discipline: TBD
- Requirement Type: TBD

##### MS22029826-43324: Power Regen Indication (System Requirement)
- Variant: S237
- Stakeholder Requirement State: In Review
- System Requirement State: Draft
- Software Requirement State: Draft
- Primary Discipline: SW
- Requirement Type: Functional

#### MS22029826-72349: Performance Requirements (Heading)
- Variant: S237
- Stakeholder Requirement State: In Review
- System Requirement State: Draft
- Software Requirement State: Draft
- Primary Discipline: TBD
- Requirement Type: TBD

##### MS22029826-72350: Table - POWER-REGEN Gauge Processing (Heading)
- Variant: S237
- Stakeholder Requirement State: In Review
- System Requirement State: Draft
- Software Requirement State: Draft
- Primary Discipline: TBD
- Requirement Type: TBD

###### MS22029826-43322: Ignition State Physical Value(CAN) (System Requirement)
| Ignition State | Physical Value(CAN) | REGEN Pointer Indication (Angular Degrees) |  |  |  |
| --- | --- | --- | --- | --- | --- |
| Ignition State | Physical Value(CAN) | Min | Target | Max | Delta |
| IGN OFF | Park | 0 | -70 | 0 | 1.5 |
| IGN ON | Diag | 238.5 | 240 | 241.5 | 3 |
| IGN ON | -100 | -71.5 | -70 | -68.5 | 3 |
| IGN ON | -90 | -64.5 | -63 | -61.5 | 3 |
| IGN ON | -80 | -57.5 | -56 | -54.5 | 3 |
| IGN ON | -70 | -50.5 | -49 | -47.5 | 3 |
| IGN ON | -60 | -43.5 | -42 | -40.5 | 3 |
| IGN ON | -50 | -36.5 | -35 | -33.5 | 3 |
| IGN ON | -40 | -29.5 | -28 | -26.5 | 3 |
| IGN ON | -30 | -22.5 | -21 | -19.5 | 3 |
| IGN ON | -20 | -15.5 | -14 | -12.5 | 3 |
| IGN ON | -10 | -8.5 | -7 | -5.5 | 3 |
| IGN ON | 0 | -1.5 | 0 | 1.5 | 3 |
| IGN ON | 10 | 15.5 | 17 | 18.5 | 3 |
| IGN ON | 20 | 32.5 | 34 | 35.5 | 3 |
| IGN ON | 30 | 49.5 | 51 | 52.5 | 3 |
| IGN ON | 40 | 66.5 | 68 | 69.5 | 3 |
| IGN ON | 50 | 83.5 | 85 | 86.5 | 3 |
| IGN ON | 60 | 100.5 | 102 | 103.5 | 3 |
| IGN ON | 70 | 117.5 | 119 | 120.5 | 3 |
| IGN ON | 80 | 134.5 | 136 | 137.5 | 3 |
| IGN ON | 90 | 151.5 | 153 | 154.5 | 3 |
| IGN ON | 100 | 168.5 | 170 | 171.5 | 3 |
- Variant: S237
- Stakeholder Requirement State: In Review
- System Requirement State: Draft
- Software Requirement State: Draft
- Primary Discipline: SW
- Requirement Type: Functional

##### MS22029826-43646: In case of rendered gauge, the pointer shall move smoothly & continuously from low to high indication without any step / jerk movement within a span of 2 sec (System Requirement)
- Variant: S237
- Stakeholder Requirement State: In Review
- System Requirement State: Draft
- Software Requirement State: Draft
- Primary Discipline: SW
- Requirement Type: Functional

##### MS22029826-34646: The pointer shall respond to the given input within 100 ms (System Requirement)
- Variant: S237
- Stakeholder Requirement State: In Review
- System Requirement State: Draft
- Software Requirement State: Draft
- Primary Discipline: SW
- Requirement Type: TBD

##### MS22029826-43625: The response of the Powe-Regen gauge shall be defined by the 2-stage filter constants T11 =2, T12 = 1 (System Requirement)
- Variant: S237
- Verification Criteria: To be verified by Detailed Gauge TDR
- Stakeholder Requirement State: In Review
- System Requirement State: Draft
- Software Requirement State: Draft
- Primary Discipline: SW
- Requirement Type: Non-Functional

#### MS22029826-72351: Fail Safe Scenario (Heading)
- Variant: S237
- Stakeholder Requirement State: In Review
- System Requirement State: Draft
- Software Requirement State: Draft
- Primary Discipline: TBD
- Requirement Type: TBD

##### MS22029826-43697: When Default is received: POWER-REGEN shall indicate 0 (0x64) (System Requirement)
- Variant: S237
- Stakeholder Requirement State: In Review
- System Requirement State: Draft
- Software Requirement State: Draft
- Primary Discipline: SW
- Requirement Type: Functional

##### MS22029826-43342 (System Requirement)
When message missing or invalid: POWER-REGEN shall indicate Diag Position
- Variant: S237
- Stakeholder Requirement State: In Review
- System Requirement State: Draft
- Secondary Disciplines: FV
- Software Requirement State: Draft
- Primary Discipline: SW
- Requirement Type: Functional

##### MS22029826-72352: Figure - Engine Running Status Processing (Heading)
- Variant: S237
- Stakeholder Requirement State: In Review
- System Requirement State: Draft
- Software Requirement State: Draft
- Primary Discipline: TBD
- Requirement Type: TBD

###### MS22029826-43364: VCU10_100:INDC_DRIVE_ENABLE(0x0-Default/Vehicle not enabled,0x1-Drive Enabled/Activate Vehicle , 0x2~0x3 -Reserved) (System Requirement)
- Variant: S237
- Stakeholder Requirement State: In Review
- System Requirement State: Draft
- Software Requirement State: Draft
- Primary Discipline: SW
- Requirement Type: Functional

###### MS22029826-43367: VAR_CODING_VEHICLE_CONTROL_UNIT(Value: 0-Not Present, 1-Present) (System Requirement)
- Variant: S237
- Stakeholder Requirement State: In Review
- System Requirement State: Draft
- Software Requirement State: Draft
- Primary Discipline: SW
- Requirement Type: Functional

###### MS22029826-43372: VAR_CODING_VEHICLE_CONTROL_UNIT VCU10_100:INDC_DRIVE_EN ABLE (System Requirement)
| VAR_CODING_VEHICLE_CONTROL_UNIT | VCU10_100:INDC_DRIVE_EN ABLE | Engine Running St |
| --- | --- | --- |
| 0 | X | No |
| 1 | 0X0 | No |
| 1 | 0X1 | Yes |
- Variant: S237
- Stakeholder Requirement State: In Review
- System Requirement State: Draft
- Software Requirement State: Draft
- Primary Discipline: SW
- Requirement Type: Functional

### MS22029826-34724: State of Charge (Heading)
- Variant: S237
- Stakeholder Requirement State: In Review
- System Requirement State: Draft
- Software Requirement State: Draft
- Primary Discipline: TBD
- Requirement Type: TBD

#### MS22029826-34725: Input Requirements (Heading)
- Variant: S237
- Stakeholder Requirement State: In Review
- System Requirement State: Draft
- Software Requirement State: Draft
- Primary Discipline: TBD
- Requirement Type: TBD

##### MS22029826-43656: IgnMode (Value: On, Off) (System Requirement)
- Variant: S237
- Stakeholder Requirement State: In Review
- System Requirement State: Draft
- Software Requirement State: Draft
- Primary Discipline: SW
- Requirement Type: Functional

##### MS22029826-34695: LVSD/HVSD Flag (Value: Not Set, Set) (Software Requirement)
- Variant: S237
- Stakeholder Requirement State: In Review
- System Requirement State: Draft
- Software Requirement State: Draft
- Primary Discipline: SW
- Requirement Type: TBD

##### MS22029826-43381: VAR_CODING_VEHICLE_CONTROL_UNIT (Value: 0-Not Present, 1-Present) (System Requirement)
- Variant: S237
- Stakeholder Requirement State: In Review
- System Requirement State: Draft
- Software Requirement State: Draft
- Primary Discipline: SW
- Requirement Type: Functional

##### MS22029826-43484: VCU10_100(0X30A):STATE_OF_CHARGE(Min-0, Max-100%) (System Requirement)
- Variant: S237
- Stakeholder Requirement State: In Review
- System Requirement State: Draft
- Secondary Disciplines: FV
- Software Requirement State: Draft
- Primary Discipline: SW
- Requirement Type: Functional

##### MS22029826-43486: FEATURE_CODE_RHD_LHD_CONFIG(0-RHD,1-LHD) (System Requirement)
- Variant: S237
- Stakeholder Requirement State: In Review
- System Requirement State: Draft
- Secondary Disciplines: FV
- Software Requirement State: Draft
- Primary Discipline: SW
- Requirement Type: Functional

##### MS22029826-43489: MBFM1_100: STS_DOOR (value: 0x0 – All closed, 0x1 – Back door open, 0x2 – Hood open, 0x4 – FL Door open, 0x8 – FR Door open, 0x10 – RL Door open, 0x20 – RR Door open, 0x3F – All Door open) (System Requirement)
- Variant: S237
- Stakeholder Requirement State: In Review
- System Requirement State: Draft
- Secondary Disciplines: FV
- Software Requirement State: Draft
- Primary Discipline: SW
- Requirement Type: Functional

##### MS22029826-72390: VCU10_100:STS_CHARGE_LIGHT_TT(0x30A) (Value: 0x0-Charge Light OFF/Default, 0x1- Charge Light ON, 0x2-Charge Light Blink, 0x3-Reserved) (System Requirement)
- Variant: S237
- Stakeholder Requirement State: In Review
- System Requirement State: Draft
- Software Requirement State: Draft
- Primary Discipline: TBD
- Requirement Type: TBD

##### MS22029826-72391: DiagRWSOCHysteris (Default -2%) (System Requirement)
- Variant: S237
- Stakeholder Requirement State: In Review
- System Requirement State: Draft
- Software Requirement State: Draft
- Primary Discipline: TBD
- Requirement Type: TBD

##### MS22029826-72393: DiagRWBLINKZONEXIT(Default -6%) (System Requirement)
- Variant: S237
- Stakeholder Requirement State: In Review
- System Requirement State: Draft
- Software Requirement State: Draft
- Primary Discipline: TBD
- Requirement Type: TBD

##### MS22029826-72394: DiagRWREDZONEEXIT(Default -17%) (System Requirement)
- Variant: S237
- Stakeholder Requirement State: In Review
- System Requirement State: Draft
- Software Requirement State: Draft
- Primary Discipline: TBD
- Requirement Type: TBD

#### MS22029826-72450: Output Requirements (Heading)
- Variant: S237
- Stakeholder Requirement State: In Review
- System Requirement State: Draft
- Software Requirement State: Draft
- Primary Discipline: TBD
- Requirement Type: TBD

##### MS22029826-72395: State Of Charge Pointer Indication (System Requirement)
- Variant: S237
- Stakeholder Requirement State: In Review
- System Requirement State: Draft
- Software Requirement State: Draft
- Primary Discipline: TBD
- Requirement Type: TBD

##### MS22029826-72396: SOC Display Processing(%) (System Requirement)
- Variant: S237
- Stakeholder Requirement State: In Review
- System Requirement State: Draft
- Software Requirement State: Draft
- Primary Discipline: TBD
- Requirement Type: TBD

#### MS22029826-72451: Performance Requirements (Heading)
- Variant: S237
- Stakeholder Requirement State: In Review
- System Requirement State: Draft
- Software Requirement State: Draft
- Primary Discipline: TBD
- Requirement Type: TBD

##### MS22029826-72452: Table - State Of Charge percentage Display Processing (Heading)
- Variant: S237
- Stakeholder Requirement State: In Review
- System Requirement State: Draft
- Software Requirement State: Draft
- Primary Discipline: TBD
- Requirement Type: TBD

###### MS22029826-72398: SocIn= STATE_OF_CHARGE (Min-0, Max-100%) (System Requirement)
SocIn= STATE_OF_CHARGE (Min-0, Max-100%)
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- Variant: S237
- Stakeholder Requirement State: In Review
- System Requirement State: Draft
- Software Requirement State: Draft
- Primary Discipline: TBD
- Requirement Type: TBD

##### MS22029826-72399: S No Parameter (System Requirement)
| S No | Parameter | Description | Size(byte s) | Defau lt | Min | Max | Unit |
| --- | --- | --- | --- | --- | --- | --- | --- |
| 1 | SOCAVGCNT | Moving Average Count for SOC | 1 | 5 | 1 | 50 | No Unit |
- Variant: S237
- Stakeholder Requirement State: In Review
- System Requirement State: Draft
- Software Requirement State: Draft
- Primary Discipline: TBD
- Requirement Type: TBD

##### MS22029826-72453: Table - State Of Charge Pointer Indication (Heading)
- Variant: S237
- Stakeholder Requirement State: In Review
- System Requirement State: Draft
- Software Requirement State: Draft
- Primary Discipline: TBD
- Requirement Type: TBD

###### MS22029826-72400: IgnMode (System Requirement)
| 1 2 3 4 | IgnMode | LVSD/HVS D Flag | VAR_CODING_VE HICLE_ CONTROL_UNIT | CAN Signal Missing/ Never Received | SOC[ Refer Artifact 5227959] | State Of Charge Pointer Indication |
| --- | --- | --- | --- | --- | --- | --- |
| 1 2 3 4 | ON/OFF | Set | X | X | X | OFF |
| 1 2 3 4 | ON/OFF | Not Set | 0 | X | X | ‘—‘ All bar is OFF |
| 1 2 3 4 | ON/OFF | Not Set | 1 | 1 | X | ‘—‘ All bar is OFF |
| 1 2 3 4 | ON/OFF | Not Set | 1 | 0 | 0x00 to 0x64 | 0 to 100 |
Note: State of charge value shall be used for Pointer Indication.
- Variant: S237
- Stakeholder Requirement State: In Review
- System Requirement State: Draft
- Software Requirement State: Draft
- Primary Discipline: TBD
- Requirement Type: TBD

##### MS22029826-72401: In forward Direction No Hysteresis is applied (System Requirement)
- Variant: S237
- Stakeholder Requirement State: In Review
- System Requirement State: Draft
- Software Requirement State: Draft
- Primary Discipline: TBD
- Requirement Type: TBD

##### MS22029826-72409 (System Requirement)
Case1: Gauge shall Blink @1HZ
Entry of Blink state(<DiagRWBLINKZONEXIT)
Exit of Blink state/Entry of RED Zone ( >= DiagRWBLINKZONEXIT + DiagRWSOCHysteris)
- Variant: S237
- Stakeholder Requirement State: In Review
- System Requirement State: Draft
- Software Requirement State: Draft
- Primary Discipline: TBD
- Requirement Type: TBD

##### MS22029826-72410 (System Requirement)
Case2: Gauge shall Indicate in RED
Entry of RED Zone: When the SOC value is <=DiagRWREDZONEEXIT, the gauge shall indicate REDZONEENTRY state
Exit of RED Zone: When the SOC Value is >= DiagRWREDZONEEXIT+ DiagRWSOCHysteris, the gauge shall indicate REDZONEEXIT state
- Variant: S237
- Stakeholder Requirement State: In Review
- System Requirement State: Draft
- Software Requirement State: Draft
- Primary Discipline: TBD
- Requirement Type: TBD

##### MS22029826-72411: SOC shall be available in Display in following use cases (System Requirement)
- Variant: S237
- Stakeholder Requirement State: In Review
- System Requirement State: Draft
- Software Requirement State: Draft
- Primary Discipline: TBD
- Requirement Type: TBD

##### MS22029826-72413 (System Requirement)
1. IGN ON
2. SOC shall be available in IGN OFF, when Display in following Trigger conditions are received in IGN OFF
· Driver Door Status is Close -> Open in IGN OFF && VCU10_100: STS_CHARGE_LIGHT_TT = 0x1/0x2
Note: FEATURE_CODE_RHD_LHD_CONFIG =0 (FR door status to be considered, FEATURE_CODE_RHD_LHD_CONFIG =1 (FL door status to be Considered)
· Drive Door is already Open && VCU10_100: STS_CHARGE_LIGHT_TT = 0->1 or 1->2 SOC shall be displayed for 10 sec in IGN OFF, IF above conditions are true.
- Variant: S237
- Stakeholder Requirement State: In Review
- System Requirement State: Draft
- Software Requirement State: Draft
- Primary Discipline: TBD
- Requirement Type: TBD

#### MS22029826-72454: Fail safe requirements (Heading)
- Variant: S237
- Stakeholder Requirement State: In Review
- System Requirement State: Draft
- Software Requirement State: Draft
- Primary Discipline: TBD
- Requirement Type: TBD

##### MS22029826-72414: When VAR_CODING_VEHICLE_CONTROL_UNIT is Disabled /CAN message is missing / invalid(0XFF) / Out of Range (>0x64) : SOC all bar shall be OFF, SOC percentage shall ‘-–‘ (System Requirement)
- Variant: S237
- Stakeholder Requirement State: In Review
- System Requirement State: Draft
- Software Requirement State: Draft
- Primary Discipline: TBD
- Requirement Type: TBD

### MS22029826-72457: Drive Efficiency (Heading)
- Variant: S237
- Stakeholder Requirement State: In Review
- System Requirement State: Draft
- Software Requirement State: Draft
- Primary Discipline: TBD
- Requirement Type: TBD

#### MS22029826-72458: Input Requirements (Heading)
- Variant: S237
- Stakeholder Requirement State: In Review
- System Requirement State: Draft
- Software Requirement State: Draft
- Primary Discipline: TBD
- Requirement Type: TBD

##### MS22029826-72464: IgnMode (Value: Off, On) (System Requirement)
- Variant: S237
- Stakeholder Requirement State: In Review
- System Requirement State: Draft
- Software Requirement State: Draft
- Primary Discipline: TBD
- Requirement Type: TBD

##### MS22029826-72465: LVSD/HVSD Flag (Not Set, Set) (System Requirement)
- Variant: S237
- Stakeholder Requirement State: In Review
- System Requirement State: Draft
- Software Requirement State: Draft
- Primary Discipline: TBD
- Requirement Type: TBD

##### MS22029826-72466: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-72467: VCU10_100(0X30A): VCU10_100: DRIVE_EFFICIENCY (-100 TO 100)% (System Requirement)
- Variant: S237
- Stakeholder Requirement State: In Review
- System Requirement State: Draft
- Software Requirement State: Draft
- Primary Discipline: TBD
- Requirement Type: TBD

#### MS22029826-72459: Output Requirements (Heading)
- Variant: S237
- Stakeholder Requirement State: In Review
- System Requirement State: Draft
- Software Requirement State: Draft
- Primary Discipline: TBD
- Requirement Type: TBD

##### MS22029826-72468: Drive Efficiency Pointer Indication (System Requirement)
- Variant: S237
- Stakeholder Requirement State: In Review
- System Requirement State: Draft
- Software Requirement State: Draft
- Primary Discipline: TBD
- Requirement Type: TBD

#### MS22029826-72460: Performance Requirement (Heading)
- Variant: S237
- Stakeholder Requirement State: In Review
- System Requirement State: Draft
- Software Requirement State: Draft
- Primary Discipline: TBD
- Requirement Type: TBD

##### MS22029826-72469: Drive Efficiency Preconditions (System Requirement)
Drive Efficiency Preconditions
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- Variant: S237
- Stakeholder Requirement State: In Review
- System Requirement State: Draft
- Software Requirement State: Draft
- Primary Discipline: TBD
- Requirement Type: TBD

##### MS22029826-72470: Drive Efficiency Processing (System Requirement)
Drive Efficiency Processing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
- Variant: S237
- Stakeholder Requirement State: In Review
- System Requirement State: Draft
- Software Requirement State: Draft
- Primary Discipline: TBD
- Requirement Type: TBD

##### MS22029826-72471: S No Parameter Description (System Requirement)
| S No | Parameter | Description | Size (bytes) | Default | Min | Max | Unit |
| --- | --- | --- | --- | --- | --- | --- | --- |
| 1 | DRIVEEFAVGCNT | Moving Average Count for Drive Efficiency | 1 | 5 | 1 | 50 | No Unit |
| 2 | DRIVEEFFSLEW | Slew Rate for Drive Efficiency Bars | 1 | 4 | 1 | 50 | No Unit |
| 3 | DRIVEEFFIDLESLEW | Slew Rate for Drive Efficiency Bars When value is -100 to -1 | 1 | 2 1 | 1 | 50 | No Unit |
- Variant: S237
- Stakeholder Requirement State: In Review
- System Requirement State: Draft
- Software Requirement State: Draft
- Primary Discipline: TBD
- Requirement Type: TBD

##### MS22029826-72462: Table - Drive Efficiency Functional Logic (Heading)
- Variant: S237
- Stakeholder Requirement State: In Review
- System Requirement State: Draft
- Software Requirement State: Draft
- Primary Discipline: TBD
- Requirement Type: TBD

###### MS22029826-72472 (System Requirement)
IC shall indicate Drive Efficiency in bar form as per below table
| S.NO | Drive_Efficiency_Bar | Drive Efficiency% |  |
| --- | --- | --- | --- |
| S.NO | Drive_Efficiency_Bar | Increasing | Decreasing |
| 1 | 1 | 10 | 5 |
| 2 | 2 | 20 | 15 |
| 3 | 3 | 30 | 25 |
| 4 | 4 | 40 | 35 |
| 5 | 5 | 50 | 45 |
| 6 | 6 | 60 | 55 |
| 7 | 7 | 70 | 65 |
| 8 | 8 | 80 | 75 |
| 9 | 9 | 90 | 85 |
| 10 | 10 | 100 | 95 |
- Variant: S237
- Stakeholder Requirement State: In Review
- System Requirement State: Draft
- Software Requirement State: Draft
- Primary Discipline: TBD
- Requirement Type: TBD

#### MS22029826-72463: Fail safe requirements. (Heading)
- Variant: S237
- Stakeholder Requirement State: In Review
- System Requirement State: Draft
- Software Requirement State: Draft
- Primary Discipline: TBD
- Requirement Type: TBD

##### MS22029826-72473: When VAR_CODING_VEHICLE_CONTROL_UNIT is Disabled/ CAN message is missing / invalid: Drive Efficiency shall be Empty. (System Requirement)
- Variant: S237
- Stakeholder Requirement State: In Review
- System Requirement State: Draft
- Software Requirement State: Draft
- Primary Discipline: TBD
- Requirement Type: TBD

# Json2ReqIF Transformation

# Specification: SysFS24_Alerts
- JDA Snapshot Date: 2025-08-21 12:57:35

## MS22029826-32338: Vehicle Alerts (Heading)
- Stakeholder Requirement State: In Review
- System Requirement State: Draft
- Software Requirement State: Draft
- Primary Discipline: TBD
- Requirement Type: TBD

### MS22029826-32666: HU will provide visual & voice alerts based on CAN message information from different ECU. (Information)
- Stakeholder Requirement State: In Review
- System Requirement State: Draft
- Software Requirement State: Draft
- Primary Discipline: TBD
- Requirement Type: TBD

### MS22029826-32667: Voice messages will also be accompanied for the applicable alerts. (Information)
- Stakeholder Requirement State: In Review
- System Requirement State: Draft
- Software Requirement State: Draft
- Primary Discipline: TBD
- Requirement Type: TBD

### MS22029826-32668: Configuration (Heading)
- Stakeholder Requirement State: In Review
- System Requirement State: Draft
- Software Requirement State: Draft
- Primary Discipline: TBD
- Requirement Type: TBD

#### MS22029826-37633: Operational modes (Heading)
- Stakeholder Requirement State: In Review
- System Requirement State: Draft
- Software Requirement State: Draft
- Primary Discipline: TBD
- Requirement Type: TBD

##### MS22029826-47451: Full run mode (Information)
- Stakeholder Requirement State: In Review
- System Requirement State: Draft
- Software Requirement State: Draft
- Primary Discipline: TBD
- Requirement Type: TBD

##### MS22029826-47452: User off mode (Information)
- Stakeholder Requirement State: In Review
- System Requirement State: Draft
- Software Requirement State: Draft
- Primary Discipline: TBD
- Requirement Type: TBD

##### MS22029826-47455 (Information)
Note:When the alerts or VMS gets triggered while the radio is in user OFF mode, radio will display the alerts and play VMS if applicable without any audio source and then shall go to the USER OFF state again. If user acknowledgement is received before time out, then IS shall re-enter in to “User Off” mode immediately.
- Stakeholder Requirement State: In Review
- System Requirement State: Draft
- Software Requirement State: Draft
- Primary Discipline: TBD
- Requirement Type: TBD

##### MS22029826-47457: Alerts if displayed in Full run mode shall be closed on entry to One hour mode. (Information)
- Stakeholder Requirement State: In Review
- System Requirement State: Draft
- Software Requirement State: Draft
- Primary Discipline: TBD
- Requirement Type: TBD

#### MS22029826-37635: Input (Heading)
- Stakeholder Requirement State: In Review
- System Requirement State: Draft
- Software Requirement State: Draft
- Primary Discipline: TBD
- Requirement Type: TBD

##### MS22029826-47460: “Alert Info” tab selection in CarInfo (Information)
- Stakeholder Requirement State: In Review
- System Requirement State: Draft
- Software Requirement State: Draft
- Primary Discipline: TBD
- Requirement Type: TBD

##### MS22029826-47461: Automatic pop up of Alert based on CAN message. (Information)
- Stakeholder Requirement State: In Review
- System Requirement State: Draft
- Software Requirement State: Draft
- Primary Discipline: TBD
- Requirement Type: TBD

##### MS22029826-47463: User acknowledgement of alerts. (Information)
- Stakeholder Requirement State: In Review
- System Requirement State: Draft
- Software Requirement State: Draft
- Primary Discipline: TBD
- Requirement Type: TBD

##### MS22029826-47465: VMS – Shall be mapped to default UK English. This shall not be changed via HMI option. (Information)
- Stakeholder Requirement State: In Review
- System Requirement State: Draft
- Software Requirement State: Draft
- Primary Discipline: TBD
- Requirement Type: TBD

#### MS22029826-37637: Output (Heading)
- Stakeholder Requirement State: In Review
- System Requirement State: Draft
- Software Requirement State: Draft
- Primary Discipline: TBD
- Requirement Type: TBD

##### MS22029826-48232: Alert display in HU. (Information)
- Stakeholder Requirement State: In Review
- System Requirement State: Draft
- Software Requirement State: Draft
- Primary Discipline: TBD
- Requirement Type: TBD

##### MS22029826-48235: Voice output for applicable alerts. (Information)
- Stakeholder Requirement State: In Review
- System Requirement State: Draft
- Software Requirement State: Draft
- Primary Discipline: TBD
- Requirement Type: TBD

##### MS22029826-48237: Individual alerts shall be configured through $716 DID. Refer U321_Mahindra_Global_ID_IS.xlsx [REFERENCE_11] for details. (Information)
- Stakeholder Requirement State: In Review
- System Requirement State: Draft
- Software Requirement State: Draft
- Primary Discipline: TBD
- Requirement Type: TBD

##### MS22029826-48239: OLE Object (Information)
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OLE Object
- Stakeholder Requirement State: In Review
- System Requirement State: Draft
- Software Requirement State: Draft
- Primary Discipline: TBD
- Requirement Type: TBD

### MS22029826-32669: List of Alerts and Logic (Heading)
- Stakeholder Requirement State: In Review
- System Requirement State: Draft
- Software Requirement State: Draft
- Primary Discipline: TBD
- Requirement Type: TBD

#### MS22029826-37639: Embedded Object (Information)
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Embedded Object
- Stakeholder Requirement State: In Review
- System Requirement State: Draft
- Software Requirement State: Draft
- Primary Discipline: TBD
- Requirement Type: TBD

### MS22029826-32670: List of VMS (Heading)
- Stakeholder Requirement State: In Review
- System Requirement State: Draft
- Software Requirement State: Draft
- Primary Discipline: TBD
- Requirement Type: TBD

#### MS22029826-37641: OLE Object (Information)
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OLE Object
- Stakeholder Requirement State: In Review
- System Requirement State: Draft
- Software Requirement State: Draft
- Primary Discipline: TBD
- Requirement Type: TBD

### MS22029826-32671: CAN Input Signals (Heading)
- Stakeholder Requirement State: In Review
- System Requirement State: Draft
- Software Requirement State: Draft
- Primary Discipline: TBD
- Requirement Type: TBD

#### MS22029826-37643: OLE Object (Information)
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OLE Object
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OLE Object
- Stakeholder Requirement State: In Review
- System Requirement State: Draft
- Software Requirement State: Draft
- Primary Discipline: TBD
- Requirement Type: TBD

### MS22029826-32673: Functional Requirements (Heading)
- Stakeholder Requirement State: In Review
- System Requirement State: Draft
- Software Requirement State: Draft
- Primary Discipline: TBD
- Requirement Type: TBD

#### MS22029826-37645: Alerts shall have a display timing of 5seconds. For alerts to be played twice with a gap of 2 seconds, display timing is 12 seconds (5+2+5 seconds) (Information)
- Stakeholder Requirement State: In Review
- System Requirement State: Draft
- Software Requirement State: Draft
- Primary Discipline: TBD
- Requirement Type: TBD

#### MS22029826-37646: There shall always be a sync between alert displayed and TTS play back. (Information)
- Stakeholder Requirement State: In Review
- System Requirement State: Draft
- Software Requirement State: Draft
- Primary Discipline: TBD
- Requirement Type: TBD

#### MS22029826-37649: There shall be provision to close alert in HMI and Bezel/IR. (Information)
- Stakeholder Requirement State: In Review
- System Requirement State: Draft
- Software Requirement State: Draft
- Primary Discipline: TBD
- Requirement Type: TBD

#### MS22029826-37650: Whenever alert is closed, alert shall be logged in “Alerts Info” tab in CarInfo screen. (Information)
- Stakeholder Requirement State: In Review
- System Requirement State: Draft
- Software Requirement State: Draft
- Primary Discipline: TBD
- Requirement Type: TBD

#### MS22029826-37652: Date of occurrence of alert (in DD-MM-YYYY format) and time stamp of first occurrence (in HH:MM:SS format) shall be available in log along with alert information in CarInfo screen. (Information)
- Stakeholder Requirement State: In Review
- System Requirement State: Draft
- Software Requirement State: Draft
- Primary Discipline: TBD
- Requirement Type: TBD

#### MS22029826-37653: If the alert condition re-occurs in the same ignition cycle, alert & VMS will not be triggered again (if the alert is already registered in info page) (Information)
- Stakeholder Requirement State: In Review
- System Requirement State: Draft
- Software Requirement State: Draft
- Primary Discipline: TBD
- Requirement Type: TBD

#### MS22029826-37655: If the alert condition persists for next ignition cycle, the alert & VMS shall be triggered in next ignition. (Information)
- Stakeholder Requirement State: In Review
- System Requirement State: Draft
- Software Requirement State: Draft
- Primary Discipline: TBD
- Requirement Type: TBD

#### MS22029826-37657: Alerts shall get cleared automatically from info page once the alert gets dismissed. (Information)
- Stakeholder Requirement State: In Review
- System Requirement State: Draft
- Software Requirement State: Draft
- Primary Discipline: TBD
- Requirement Type: TBD

#### MS22029826-37659: OLE Object (Information)
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OLE Object
- Stakeholder Requirement State: In Review
- System Requirement State: Draft
- Software Requirement State: Draft
- Primary Discipline: TBD
- Requirement Type: TBD

#### MS22029826-37661: VMS will be mixed along with audio source. (Information)
- Stakeholder Requirement State: In Review
- System Requirement State: Draft
- Software Requirement State: Draft
- Primary Discipline: TBD
- Requirement Type: TBD

#### MS22029826-37663: VMS will be available only in front speakers. (Information)
- Stakeholder Requirement State: In Review
- System Requirement State: Draft
- Software Requirement State: Draft
- Primary Discipline: TBD
- Requirement Type: TBD

#### MS22029826-37665: If any alert comes during VR state, the alert will be displayed at the end of VR state, (Refer Audio management table [REFERENCE_13]) (Information)
- Stakeholder Requirement State: In Review
- System Requirement State: Draft
- Software Requirement State: Draft
- Primary Discipline: TBD
- Requirement Type: TBD

#### MS22029826-37666: In case of NAV and VMS, NAV will be provided with higher priority. (Refer Audio management table [REFERENCE_13]) (Information)
- Stakeholder Requirement State: In Review
- System Requirement State: Draft
- Software Requirement State: Draft
- Primary Discipline: TBD
- Requirement Type: TBD

#### MS22029826-37668: Until alert is dismissed, date and time stamp of alert occurred shall not get updated even if multiple times alert gets triggered due to change in signal value. (Information)
- Stakeholder Requirement State: In Review
- System Requirement State: Draft
- Software Requirement State: Draft
- Primary Discipline: TBD
- Requirement Type: TBD

#### MS22029826-37670: If multiple alerts are active at the same time, then system shall queue and play back the VMS. After completing the first VMS alert, system shall process the next alert prompt. (Information)
- Stakeholder Requirement State: In Review
- System Requirement State: Draft
- Software Requirement State: Draft
- Primary Discipline: TBD
- Requirement Type: TBD

#### MS22029826-37672: Refer Queue logic section [REQ_ALERTS_132] for multiple alerts handling. (Information)
- Stakeholder Requirement State: In Review
- System Requirement State: Draft
- Software Requirement State: Draft
- Primary Discipline: TBD
- Requirement Type: TBD

#### MS22029826-37674: Refer HMI SRD[REFERENCE_7] for HMI/SWC/IR/Bezel/Capsense interaction when alert is active. (Information)
- Stakeholder Requirement State: In Review
- System Requirement State: Draft
- Software Requirement State: Draft
- Primary Discipline: TBD
- Requirement Type: TBD

#### MS22029826-37676: Alerts shall not get erased automatically, if the user visits or scrolls the info page. (Information)
- Stakeholder Requirement State: In Review
- System Requirement State: Draft
- Software Requirement State: Draft
- Primary Discipline: TBD
- Requirement Type: TBD

#### MS22029826-37678: Alert icon shall be visible in HMI as long as an active alert is present in info page. (Information)
- Stakeholder Requirement State: In Review
- System Requirement State: Draft
- Software Requirement State: Draft
- Primary Discipline: TBD
- Requirement Type: TBD

#### MS22029826-37680: Alert icon shall be disabled in HMI only when there is no active alert in info page. (Information)
- Stakeholder Requirement State: In Review
- System Requirement State: Draft
- Software Requirement State: Draft
- Primary Discipline: TBD
- Requirement Type: TBD

#### MS22029826-37682: During ongoing alert, if the alert gets deactivated then immediately the ongoing alert shall be stopped. (Information)
- Stakeholder Requirement State: In Review
- System Requirement State: Draft
- Software Requirement State: Draft
- Primary Discipline: TBD
- Requirement Type: TBD

#### MS22029826-37683: There shall not be any delay seen when multiple alerts switching takes place. (Information)
- Stakeholder Requirement State: In Review
- System Requirement State: Draft
- Software Requirement State: Draft
- Primary Discipline: TBD
- Requirement Type: TBD

#### MS22029826-37685: In any ignition cycle: Sleep to wakeup, alert monitoring shall happen afresh. All alerts shall be erased from info page during sleep cycle. (Information)
- Stakeholder Requirement State: In Review
- System Requirement State: Draft
- Software Requirement State: Draft
- Primary Discipline: TBD
- Requirement Type: TBD

#### MS22029826-37687: If ignition cycle happens without allowing IVI to sleep, retain last active status. (Information)
- Stakeholder Requirement State: In Review
- System Requirement State: Draft
- Software Requirement State: Draft
- Primary Discipline: TBD
- Requirement Type: TBD

### MS22029826-32675: Interrupt handling (Heading)
- Stakeholder Requirement State: In Review
- System Requirement State: Draft
- Software Requirement State: Draft
- Primary Discipline: TBD
- Requirement Type: TBD

#### MS22029826-37689: OLE Object (Information)
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OLE Object
For audio handling of above interrupts, refer “IS_Interrupts_Audio management” tab of Audio management table [REFERENCE_13].
- Stakeholder Requirement State: In Review
- System Requirement State: Draft
- Software Requirement State: Draft
- Primary Discipline: TBD
- Requirement Type: TBD

### MS22029826-32678: Repetitive Alert Handling (Heading)
- Stakeholder Requirement State: In Review
- System Requirement State: Draft
- Software Requirement State: Draft
- Primary Discipline: TBD
- Requirement Type: TBD

#### MS22029826-37691: Door status, TPMS alert may occur more often with different signal status, System should be able to treat each “Door” and each “Tire” status as different alert and shall display the alert and play the prompt again in the same ignition cycle. (Information)
- Stakeholder Requirement State: In Review
- System Requirement State: Draft
- Software Requirement State: Draft
- Primary Discipline: TBD
- Requirement Type: TBD

#### MS22029826-37692 (Information)
Use case 1: System displayed “Door Open” alert based on “Driver door status” once and it is logged in to the info page. After the user has closed the door, alert will be deleted from the info page. In the same ignition cycle, if “Door open condition is satisfied for another door or for the same door again”, system shall again display the alert and play out the VMS.
- Stakeholder Requirement State: In Review
- System Requirement State: Draft
- Software Requirement State: Draft
- Primary Discipline: TBD
- Requirement Type: TBD

#### MS22029826-37694: Use case 2: System displayed the “FL – TPMS” alert and it is already available in the info page. Now if the alert conditions are satisfied for a different tyre (FR, RL, RR) then again the system shall prompt the alert to user. (Information)
- Stakeholder Requirement State: In Review
- System Requirement State: Draft
- Software Requirement State: Draft
- Primary Discipline: TBD
- Requirement Type: TBD

#### MS22029826-37696: Use case 3: System displayed the “FL – TPMS” alert and it is already available in the info page. Now if the same “FL” status is received in CAN message repeatedly, system shall not display or play the prompts again. (Information)
- Stakeholder Requirement State: In Review
- System Requirement State: Draft
- Software Requirement State: Draft
- Primary Discipline: TBD
- Requirement Type: TBD

### MS22029826-32680: Door Open alert (Heading)
- Stakeholder Requirement State: In Review
- System Requirement State: Draft
- Software Requirement State: Draft
- Primary Discipline: TBD
- Requirement Type: TBD

#### MS22029826-37698: Refer “List of alerts and logic” section for condition to trigger. (Information)
- Stakeholder Requirement State: In Review
- System Requirement State: Draft
- Software Requirement State: Draft
- Primary Discipline: TBD
- Requirement Type: TBD

#### MS22029826-37700: OLE Object (Information)
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OLE Object
- Stakeholder Requirement State: In Review
- System Requirement State: Draft
- Software Requirement State: Draft
- Primary Discipline: TBD
- Requirement Type: TBD

#### MS22029826-37702: Based on change in STS_DOOR signal value, respective door open alert shall be triggered. (Information)
- Stakeholder Requirement State: In Review
- System Requirement State: Draft
- Software Requirement State: Draft
- Primary Discipline: TBD
- Requirement Type: TBD

#### MS22029826-37704: Once triggered, condition to dismiss shall be STS_DOOR=0. (Information)
- Stakeholder Requirement State: In Review
- System Requirement State: Draft
- Software Requirement State: Draft
- Primary Discipline: TBD
- Requirement Type: TBD

### MS22029826-32683: Low Brake Fluid alert (Heading)
- Stakeholder Requirement State: In Review
- System Requirement State: Draft
- Software Requirement State: Draft
- Primary Discipline: TBD
- Requirement Type: TBD

#### MS22029826-37705: Refer “List of alerts and logic” section for condition to trigger. (Information)
- Stakeholder Requirement State: In Review
- System Requirement State: Draft
- Software Requirement State: Draft
- Primary Discipline: TBD
- Requirement Type: TBD

#### MS22029826-37706: Alert could be triggered when either one of three condition mentioned in “List of alerts and logic” gets satisfied. (Information)
- Stakeholder Requirement State: In Review
- System Requirement State: Draft
- Software Requirement State: Draft
- Primary Discipline: TBD
- Requirement Type: TBD

#### MS22029826-37708: Regarding Condition 3 in “List of alerts and logic” section: Distance covered shall be checked from the instance the low brake fluid is detected. (Information)
- Stakeholder Requirement State: In Review
- System Requirement State: Draft
- Software Requirement State: Draft
- Primary Discipline: TBD
- Requirement Type: TBD

#### MS22029826-37710: When alert is currently serviced due to one of the condition, if another condition gets satisfied before completion of current alert display, it need not be serviced again. (Information)
- Stakeholder Requirement State: In Review
- System Requirement State: Draft
- Software Requirement State: Draft
- Primary Discipline: TBD
- Requirement Type: TBD

#### MS22029826-38010: Once triggered, condition to dismiss shall be STS_BRAKE_FLUID_LVL =0. (Information)
- Stakeholder Requirement State: In Review
- System Requirement State: Draft
- Software Requirement State: Draft
- Primary Discipline: TBD
- Requirement Type: TBD

### MS22029826-32685: Seat belt warning (Heading)
- Stakeholder Requirement State: In Review
- System Requirement State: Draft
- Software Requirement State: Draft
- Primary Discipline: TBD
- Requirement Type: TBD

#### MS22029826-38012: Refer “List of alerts and logic” section for condition to trigger. (Information)
- Stakeholder Requirement State: In Review
- System Requirement State: Draft
- Software Requirement State: Draft
- Primary Discipline: TBD
- Requirement Type: TBD

#### MS22029826-38014: Once triggered, condition to dismiss shall be STS_SEAT_BLT_DRVR_SRS= Buckled or Buckle faulty or Reserved. (Information)
- Stakeholder Requirement State: In Review
- System Requirement State: Draft
- Software Requirement State: Draft
- Primary Discipline: TBD
- Requirement Type: TBD

### MS22029826-32687: High engine temperature alert (Heading)
- Stakeholder Requirement State: In Review
- System Requirement State: Draft
- Software Requirement State: Draft
- Primary Discipline: TBD
- Requirement Type: TBD

#### MS22029826-38016: Refer “List of alerts and logic” section for condition to trigger. (Information)
- Stakeholder Requirement State: In Review
- System Requirement State: Draft
- Software Requirement State: Draft
- Primary Discipline: TBD
- Requirement Type: TBD

#### MS22029826-38018: Once triggered, condition to dismiss shall be ENG_TEMP<110˚C. (Information)
- Stakeholder Requirement State: In Review
- System Requirement State: Draft
- Software Requirement State: Draft
- Primary Discipline: TBD
- Requirement Type: TBD

#### MS22029826-38019: When alert is currently serviced due to condition 1, if condition 2 gets satisfied before completion of current alert display, alert need not be serviced again. (Information)
- Stakeholder Requirement State: In Review
- System Requirement State: Draft
- Software Requirement State: Draft
- Primary Discipline: TBD
- Requirement Type: TBD

#### MS22029826-38022: When alert is currently serviced due to condition 2, if condition 1 gets satisfied before completion of current alert display, alert need not be serviced again. (Information)
- Stakeholder Requirement State: In Review
- System Requirement State: Draft
- Software Requirement State: Draft
- Primary Discipline: TBD
- Requirement Type: TBD

#### MS22029826-38024: Note: Engine temperature value is not EOL calibratable. (Information)
- Stakeholder Requirement State: In Review
- System Requirement State: Draft
- Software Requirement State: Draft
- Primary Discipline: TBD
- Requirement Type: TBD

### MS22029826-32689: Low Engine oil pressure alert (Heading)
- Stakeholder Requirement State: In Review
- System Requirement State: Draft
- Software Requirement State: Draft
- Primary Discipline: TBD
- Requirement Type: TBD

#### MS22029826-38026: Refer “List of alerts and logic” section for condition to trigger. (Information)
- Stakeholder Requirement State: In Review
- System Requirement State: Draft
- Software Requirement State: Draft
- Primary Discipline: TBD
- Requirement Type: TBD

#### MS22029826-38028: Once triggered, condition to dismiss shall be ENG_OIL_PRESSURE=0x0. (Information)
- Stakeholder Requirement State: In Review
- System Requirement State: Draft
- Software Requirement State: Draft
- Primary Discipline: TBD
- Requirement Type: TBD

#### MS22029826-38030: Debounce time shall be configurable through DID 713. Refer U321_Mahindra_Global_ID_IS.xlsx for details. (Information)
- Stakeholder Requirement State: In Review
- System Requirement State: Draft
- Software Requirement State: Draft
- Primary Discipline: TBD
- Requirement Type: TBD

### MS22029826-32692: Hand Brake engagement alert (Heading)
- Stakeholder Requirement State: In Review
- System Requirement State: Draft
- Software Requirement State: Draft
- Primary Discipline: TBD
- Requirement Type: TBD

#### MS22029826-38032: Refer “List of alerts and logic” section for condition to trigger. (Information)
- Stakeholder Requirement State: In Review
- System Requirement State: Draft
- Software Requirement State: Draft
- Primary Discipline: TBD
- Requirement Type: TBD

#### MS22029826-38034: Once triggered, condition to dismiss shall be STS_PARK_BRK=0x0. (Information)
- Stakeholder Requirement State: In Review
- System Requirement State: Draft
- Software Requirement State: Draft
- Primary Discipline: TBD
- Requirement Type: TBD

### MS22029826-32694: Reserve fuel warning (Heading)
- Stakeholder Requirement State: In Review
- System Requirement State: Draft
- Software Requirement State: Draft
- Primary Discipline: TBD
- Requirement Type: TBD

#### MS22029826-38036: Refer “List of alerts and logic” section for condition to trigger. (Information)
- Stakeholder Requirement State: In Review
- System Requirement State: Draft
- Software Requirement State: Draft
- Primary Discipline: TBD
- Requirement Type: TBD

#### MS22029826-38049: Alert shall be triggered when INDC_LOW_FUEL=0x1 and DIST_TO_EMPTY<=25km. (Information)
- Stakeholder Requirement State: In Review
- System Requirement State: Draft
- Software Requirement State: Draft
- Primary Discipline: TBD
- Requirement Type: TBD

#### MS22029826-38051: Once triggered, condition to dismiss shall be INDC_LOW_FUEL=0x0. (Information)
- Stakeholder Requirement State: In Review
- System Requirement State: Draft
- Software Requirement State: Draft
- Primary Discipline: TBD
- Requirement Type: TBD

#### MS22029826-38053: Note: DTE value is not calibratable. (Information)
- Stakeholder Requirement State: In Review
- System Requirement State: Draft
- Software Requirement State: Draft
- Primary Discipline: TBD
- Requirement Type: TBD

### MS22029826-32697: TPMS related alerts (Heading)
- Stakeholder Requirement State: In Review
- System Requirement State: Draft
- Software Requirement State: Draft
- Primary Discipline: TBD
- Requirement Type: TBD

#### MS22029826-38055: Low tyre pressure alert (Heading)
- Stakeholder Requirement State: In Review
- System Requirement State: Draft
- Software Requirement State: Draft
- Primary Discipline: TBD
- Requirement Type: TBD

##### MS22029826-48242: When LOW_TYRE_PRESSURE_ALERT!=0, alert shall be triggered for respective tyres. For every change in value, alert shall be triggered. (Information)
- Stakeholder Requirement State: In Review
- System Requirement State: Draft
- Software Requirement State: Draft
- Primary Discipline: TBD
- Requirement Type: TBD

#### MS22029826-38057: High tyre pressure alert (Heading)
- Stakeholder Requirement State: In Review
- System Requirement State: Draft
- Software Requirement State: Draft
- Primary Discipline: TBD
- Requirement Type: TBD

##### MS22029826-48244: When HIGH_TYRE_PRESSURE_ALERT!=0, alert shall be triggered for respective tyres. For every change in value, alert shall be triggered. (Information)
- Stakeholder Requirement State: In Review
- System Requirement State: Draft
- Software Requirement State: Draft
- Primary Discipline: TBD
- Requirement Type: TBD

#### MS22029826-38059: Air leakage alert (Heading)
- Stakeholder Requirement State: In Review
- System Requirement State: Draft
- Software Requirement State: Draft
- Primary Discipline: TBD
- Requirement Type: TBD

##### MS22029826-48246: When TPMS_LEAKAGE_ALERT!=0, alert shall be triggered for respective tyres. For every change in value, alert shall be triggered. (Information)
- Stakeholder Requirement State: In Review
- System Requirement State: Draft
- Software Requirement State: Draft
- Primary Discipline: TBD
- Requirement Type: TBD

##### MS22029826-48248: The following signals shall be ignored for that tyre (having the Air leakage) and user will not be alerted. (Information)
- Stakeholder Requirement State: In Review
- System Requirement State: Draft
- Software Requirement State: Draft
- Primary Discipline: TBD
- Requirement Type: TBD

##### MS22029826-48250: TPMS_ID_NOT_LEARNT (MBFM5_100): (this information need not be available in “Alert info” page) (Information)
- Stakeholder Requirement State: In Review
- System Requirement State: Draft
- Software Requirement State: Draft
- Primary Discipline: TBD
- Requirement Type: TBD

#### MS22029826-38061: TPMS signal error pop up (Heading)
- Stakeholder Requirement State: In Review
- System Requirement State: Draft
- Software Requirement State: Draft
- Primary Discipline: TBD
- Requirement Type: TBD

##### MS22029826-48253: When TPMS_SIGNAL_MISSING!=0, full screen pop up similar to alert shall be triggered for respective tyres. For every change in value, this shall be triggered. (Information)
- Stakeholder Requirement State: In Review
- System Requirement State: Draft
- Software Requirement State: Draft
- Primary Discipline: TBD
- Requirement Type: TBD

##### MS22029826-48255: This information need not be available as part of “Alerts Info” tab. (Information)
- Stakeholder Requirement State: In Review
- System Requirement State: Draft
- Software Requirement State: Draft
- Primary Discipline: TBD
- Requirement Type: TBD

##### MS22029826-48257: The following signals shall be ignored for that tyre (having the error) and user shall not be alerted. (Information)
- Stakeholder Requirement State: In Review
- System Requirement State: Draft
- Software Requirement State: Draft
- Primary Discipline: TBD
- Requirement Type: TBD

##### MS22029826-48259: LOW_TYRE_PRESSURE (MBFM5_100) (Information)
- Stakeholder Requirement State: In Review
- System Requirement State: Draft
- Software Requirement State: Draft
- Primary Discipline: TBD
- Requirement Type: TBD

##### MS22029826-48260: HIGH_TYRE_PRESSURE (MBFM5_100) (Information)
- Stakeholder Requirement State: In Review
- System Requirement State: Draft
- Software Requirement State: Draft
- Primary Discipline: TBD
- Requirement Type: TBD

##### MS22029826-48262: TPMS_LEAKAGE_ALERT (MBFM5_100) (Information)
- Stakeholder Requirement State: In Review
- System Requirement State: Draft
- Software Requirement State: Draft
- Primary Discipline: TBD
- Requirement Type: TBD

##### MS22029826-48264: TPMS_ID_NOT_LEARNT (MBFM5_100) (Information)
- Stakeholder Requirement State: In Review
- System Requirement State: Draft
- Software Requirement State: Draft
- Primary Discipline: TBD
- Requirement Type: TBD

#### MS22029826-38063: TPMS ID not learned alert (Heading)
- Stakeholder Requirement State: In Review
- System Requirement State: Draft
- Software Requirement State: Draft
- Primary Discipline: TBD
- Requirement Type: TBD

##### MS22029826-48267: When TPMS_ID_NOT_LEARNT!=0, full screen pop up similar to alert shall be triggered for respective tyres. For every change in value, this shall be triggered. (Information)
- Stakeholder Requirement State: In Review
- System Requirement State: Draft
- Software Requirement State: Draft
- Primary Discipline: TBD
- Requirement Type: TBD

##### MS22029826-48269: This information need not be available as part of “Alerts Info” tab. (Information)
- Stakeholder Requirement State: In Review
- System Requirement State: Draft
- Software Requirement State: Draft
- Primary Discipline: TBD
- Requirement Type: TBD

##### MS22029826-48271: The following signals shall be ignored for that tyre (TPMS not learnt) and user will not be alerted. But information shall be available in Alert Info tab. (Information)
- Stakeholder Requirement State: In Review
- System Requirement State: Draft
- Software Requirement State: Draft
- Primary Discipline: TBD
- Requirement Type: TBD

##### MS22029826-48273: LOW_TYRE_PRESSURE (MBFM5_100) (Information)
- Stakeholder Requirement State: In Review
- System Requirement State: Draft
- Software Requirement State: Draft
- Primary Discipline: TBD
- Requirement Type: TBD

##### MS22029826-48275: HIGH_TYRE_PRESSURE (MBFM5_100) (Information)
- Stakeholder Requirement State: In Review
- System Requirement State: Draft
- Software Requirement State: Draft
- Primary Discipline: TBD
- Requirement Type: TBD

#### MS22029826-38065: TPMS Multiple Alerts use cases (Heading)
- Stakeholder Requirement State: In Review
- System Requirement State: Draft
- Software Requirement State: Draft
- Primary Discipline: TBD
- Requirement Type: TBD

##### MS22029826-48278: For any tyre, use cases of multiple alerts as shown in the below table can be possible. (Information)
- Stakeholder Requirement State: In Review
- System Requirement State: Draft
- Software Requirement State: Draft
- Primary Discipline: TBD
- Requirement Type: TBD

##### MS22029826-48280: OLE Object (Information)
Link to embedded image
OLE Object
Case 1: If Low Pressure and Air Leakage triggers are present, both alerts shall be displayed.
- Stakeholder Requirement State: In Review
- System Requirement State: Draft
- Software Requirement State: Draft
- Primary Discipline: TBD
- Requirement Type: TBD

##### MS22029826-48282: Case 2: If High Pressure and Air Leakage triggers are present, both alerts shall be displayed. (Information)
- Stakeholder Requirement State: In Review
- System Requirement State: Draft
- Software Requirement State: Draft
- Primary Discipline: TBD
- Requirement Type: TBD

##### MS22029826-48284: Case 3: If High Pressure, Low pressure and Air Leakage triggers are present, High pressure and Air leakage alerts shall be displayed. (Information)
- Stakeholder Requirement State: In Review
- System Requirement State: Draft
- Software Requirement State: Draft
- Primary Discipline: TBD
- Requirement Type: TBD

### MS22029826-32699: Service due alert (Heading)
- Stakeholder Requirement State: In Review
- System Requirement State: Draft
- Software Requirement State: Draft
- Primary Discipline: TBD
- Requirement Type: TBD

#### MS22029826-38067: Refer “List of alerts and logic” section for condition to trigger. (Information)
- Stakeholder Requirement State: In Review
- System Requirement State: Draft
- Software Requirement State: Draft
- Primary Discipline: TBD
- Requirement Type: TBD

#### MS22029826-38069: Alert shall be triggered for every change in non-zero value of SERVICE_REMINDER signal. (Information)
- Stakeholder Requirement State: In Review
- System Requirement State: Draft
- Software Requirement State: Draft
- Primary Discipline: TBD
- Requirement Type: TBD

### MS22029826-32701: HHC cannot be activated alert (Heading)
- Stakeholder Requirement State: In Review
- System Requirement State: Draft
- Software Requirement State: Draft
- Primary Discipline: TBD
- Requirement Type: TBD

#### MS22029826-38071: Refer “List of alerts and logic” section for condition to trigger. Note: Vehicle speed check is not required. (Information)
- Stakeholder Requirement State: In Review
- System Requirement State: Draft
- Software Requirement State: Draft
- Primary Discipline: TBD
- Requirement Type: TBD

#### MS22029826-38074: Once Condition to trigger is met, debounce for 3 seconds before alerting the user. (Information)
- Stakeholder Requirement State: In Review
- System Requirement State: Draft
- Software Requirement State: Draft
- Primary Discipline: TBD
- Requirement Type: TBD

### MS22029826-32704: HDC cannot be activated alert (Heading)
- Stakeholder Requirement State: In Review
- System Requirement State: Draft
- Software Requirement State: Draft
- Primary Discipline: TBD
- Requirement Type: TBD

#### MS22029826-38076: Refer “List of alerts and logic” section for condition to trigger. Note: Vehicle speed check is not required. (Information)
- Stakeholder Requirement State: In Review
- System Requirement State: Draft
- Software Requirement State: Draft
- Primary Discipline: TBD
- Requirement Type: TBD

#### MS22029826-38089: Once Condition to trigger is met, debounce for 3 seconds before alerting the user. (Information)
- Stakeholder Requirement State: In Review
- System Requirement State: Draft
- Software Requirement State: Draft
- Primary Discipline: TBD
- Requirement Type: TBD

### MS22029826-32706: HDC activated / de-activated pop up (Heading)
- Stakeholder Requirement State: In Review
- System Requirement State: Draft
- Software Requirement State: Draft
- Primary Discipline: TBD
- Requirement Type: TBD

#### MS22029826-38091: Refer “List of alerts and logic” section for condition to trigger. Note: Engine speed check is not required. (Information)
- Stakeholder Requirement State: In Review
- System Requirement State: Draft
- Software Requirement State: Draft
- Primary Discipline: TBD
- Requirement Type: TBD

#### MS22029826-38093: For HDC_ACTIVE=0x3 retain previous state. (Information)
- Stakeholder Requirement State: In Review
- System Requirement State: Draft
- Software Requirement State: Draft
- Primary Discipline: TBD
- Requirement Type: TBD

### MS22029826-32708: Selective Catalytic Reduction (SCR) Alert Handling (NA for U321) (Heading)
- Stakeholder Requirement State: In Review
- System Requirement State: Draft
- Software Requirement State: Draft
- Primary Discipline: TBD
- Requirement Type: TBD

### MS22029826-32999: PKE Alert Handling (NA for U321) (Heading)
- Stakeholder Requirement State: In Review
- System Requirement State: Draft
- Software Requirement State: Draft
- Primary Discipline: TBD
- Requirement Type: TBD

### MS22029826-33001: Alert Queue Handling (Heading)
- Stakeholder Requirement State: In Review
- System Requirement State: Draft
- Software Requirement State: Draft
- Primary Discipline: TBD
- Requirement Type: TBD

#### MS22029826-38095: List of Queues (Heading)
- Stakeholder Requirement State: In Review
- System Requirement State: Draft
- Software Requirement State: Draft
- Primary Discipline: TBD
- Requirement Type: TBD

##### MS22029826-48286: System will maintain a queue with FIFO logic. (Information)
- Stakeholder Requirement State: In Review
- System Requirement State: Draft
- Software Requirement State: Draft
- Primary Discipline: TBD
- Requirement Type: TBD

##### MS22029826-48288: No priority will be maintained with in the queue. (Information)
- Stakeholder Requirement State: In Review
- System Requirement State: Draft
- Software Requirement State: Draft
- Primary Discipline: TBD
- Requirement Type: TBD

##### MS22029826-48291: Embedded Object (Information)
Link to embedded image
Embedded Object
- Stakeholder Requirement State: In Review
- System Requirement State: Draft
- Software Requirement State: Draft
- Primary Discipline: TBD
- Requirement Type: TBD

#### MS22029826-38097: Queue Maintenance (Heading)
- Stakeholder Requirement State: In Review
- System Requirement State: Draft
- Software Requirement State: Draft
- Primary Discipline: TBD
- Requirement Type: TBD

##### MS22029826-48293: Current playing alert will be shown for 5s (Voice prompt will be completed) and then only queue processing will be done. (Information)
- Stakeholder Requirement State: In Review
- System Requirement State: Draft
- Software Requirement State: Draft
- Primary Discipline: TBD
- Requirement Type: TBD

##### MS22029826-48295: Before processing the alert in queue if the alert is deactivated, then it will be deleted from the queue. (Information)
- Stakeholder Requirement State: In Review
- System Requirement State: Draft
- Software Requirement State: Draft
- Primary Discipline: TBD
- Requirement Type: TBD

##### MS22029826-48297: Before the completion of current alert if the ongoing alert gets deactivated then it shall be cancelled immediately and system shall process the next alert in queue. (Information)
- Stakeholder Requirement State: In Review
- System Requirement State: Draft
- Software Requirement State: Draft
- Primary Discipline: TBD
- Requirement Type: TBD

##### MS22029826-48299: Note: Subsequent sections cover the logical flow diagram and it is given only for clarification purpose. SW design shall not use the same flow for the development it shall be done according to the SW architecture. (Information)
- Stakeholder Requirement State: In Review
- System Requirement State: Draft
- Software Requirement State: Draft
- Primary Discipline: TBD
- Requirement Type: TBD

#### MS22029826-38099: Logical Flow Diagram for Queue Processing (Heading)
- Stakeholder Requirement State: In Review
- System Requirement State: Draft
- Software Requirement State: Draft
- Primary Discipline: TBD
- Requirement Type: TBD

##### MS22029826-48301: OLE Object (Information)
Link to embedded image
OLE Object
- Stakeholder Requirement State: In Review
- System Requirement State: Draft
- Software Requirement State: Draft
- Primary Discipline: TBD
- Requirement Type: TBD

#### MS22029826-38101: Logical Flow Diagram for De-Queue Processing (Heading)
- Stakeholder Requirement State: In Review
- System Requirement State: Draft
- Software Requirement State: Draft
- Primary Discipline: TBD
- Requirement Type: TBD

##### MS22029826-48302: OLE Object (Information)
Link to embedded image
OLE Object
- Stakeholder Requirement State: In Review
- System Requirement State: Draft
- Software Requirement State: Draft
- Primary Discipline: TBD
- Requirement Type: TBD

#### MS22029826-38103: Use Case 1: General Alert (Heading)
- Stakeholder Requirement State: In Review
- System Requirement State: Draft
- Software Requirement State: Draft
- Primary Discipline: TBD
- Requirement Type: TBD

##### MS22029826-48304: OLE Object (Information)
Link to embedded image
OLE Object
- Stakeholder Requirement State: In Review
- System Requirement State: Draft
- Software Requirement State: Draft
- Primary Discipline: TBD
- Requirement Type: TBD

#### MS22029826-38106: Use case 2: Alert Override by Diag commands (Heading)
- Stakeholder Requirement State: In Review
- System Requirement State: Draft
- Software Requirement State: Draft
- Primary Discipline: TBD
- Requirement Type: TBD

##### MS22029826-48307 (Information)
While the alerts are active, except acknowledge inputs, others are not functional. So user cannot enter into ETM mode. CAN Diag mode / EOL mode cannot override the alert screens. [Not possible in vehicle running condition, no specific SW check is maintained]
- Stakeholder Requirement State: In Review
- System Requirement State: Draft
- Software Requirement State: Draft
- Primary Discipline: TBD
- Requirement Type: TBD

#### MS22029826-38108: Use case 3: HMI Footer/Overlay update (Heading)
- Stakeholder Requirement State: In Review
- System Requirement State: Draft
- Software Requirement State: Draft
- Primary Discipline: TBD
- Requirement Type: TBD

##### MS22029826-48309: During alert if any volume update or error message like USB error, invalid file etc, it shall be shown over the Alert screen. (Information)
- Stakeholder Requirement State: In Review
- System Requirement State: Draft
- Software Requirement State: Draft
- Primary Discipline: TBD
- Requirement Type: TBD

#### MS22029826-38110: Use case 4: 4 general alerts in queue with 2 voice prompts and 2 non voice prompts (Heading)
- Stakeholder Requirement State: In Review
- System Requirement State: Draft
- Software Requirement State: Draft
- Primary Discipline: TBD
- Requirement Type: TBD

##### MS22029826-48311 (Information)
Whenever voice prompt alerts are playing, it will get mixed with the entertainment audio. If there is no voice prompt then only entertainment audio will be heard. If the voice prompt alerts are interleaved between the other alerts, then entertainment audio volume will be reduced whenever there is mixing and returns to normal whenever there is no voice prompt.
- Stakeholder Requirement State: In Review
- System Requirement State: Draft
- Software Requirement State: Draft
- Primary Discipline: TBD
- Requirement Type: TBD

#### MS22029826-38112: Use case 5: Multi Level alert processing in queue (Heading)
- Stakeholder Requirement State: In Review
- System Requirement State: Draft
- Software Requirement State: Draft
- Primary Discipline: TBD
- Requirement Type: TBD

##### MS22029826-48313: If any alert has a multi-level processing (Say, Engine temperature and Low brake fluid) then each level shall be processed as a separate alert based on the pre-condition. (Information)
- Stakeholder Requirement State: In Review
- System Requirement State: Draft
- Software Requirement State: Draft
- Primary Discipline: TBD
- Requirement Type: TBD

### MS22029826-33003: Error Handling (Heading)
- Stakeholder Requirement State: In Review
- System Requirement State: Draft
- Software Requirement State: Draft
- Primary Discipline: TBD
- Requirement Type: TBD

#### MS22029826-38114: LVI/HVI: As long as system is active and alert is in queue, system should keep playing the alert. On returning to normal state from LVI/HVI, check for alerts from beginning. (Information)
- Stakeholder Requirement State: In Review
- System Requirement State: Draft
- Software Requirement State: Draft
- Primary Discipline: TBD
- Requirement Type: TBD

#### MS22029826-38116: In case of CAN message missing, alert shall not get cleared/dismissed; it shall retain the last active state. (Information)
- Stakeholder Requirement State: In Review
- System Requirement State: Draft
- Software Requirement State: Draft
- Primary Discipline: TBD
- Requirement Type: TBD

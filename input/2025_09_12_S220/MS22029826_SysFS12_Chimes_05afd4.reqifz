# Json2ReqIF Transformation

# Specification: SysFS12_Chimes
- JDA Snapshot Date: 2025-08-22 15:09:45

## MS22029826-37159: Chimes (Heading)
- Variant: S220, S237, W502
- Stakeholder Requirement State: In Review
- System Requirement State: Draft
- Software Requirement State: Draft
- Primary Discipline: TBD
- Requirement Type: TBD

### MS22029826-44131: Table of Revision (Information)
- Variant: S220, S237, W502
- Stakeholder Requirement State: In Review
- System Requirement State: Draft
- Software Requirement State: Draft
- Primary Discipline: TBD
- Requirement Type: TBD

#### MS22029826-52385: Table of Revision-W502 & S220 (Information)
| Revision | DATE | Author | Modifications |
| --- | --- | --- | --- |
| BL23 | 16-10-2020 | cmathyam | 1. F004 - AEB & OSW Chime Update (Req-Id: 2578779) 2. F023 Need to provide user setting to disable LDW chime (Req Id- 2667296) |
| BL24 | 01-12-2020 | mmuthura | Req ID: 2725276- Added ACC info chimes for signal ACC_SYS_INFO=0x1, 0x2, 0x8~0xD. 3653305 Added for jury feedback F023 |
|  | 28-12-2020 | cmathyam | 3687781 -Req updated based on impediment 517443 -AEB Priority is modified 2725313 -Req updated based on Customer Feedback. |
| BL24 | 22-01-2020 | cmathyam | 2322989 - While playing overspeed Chime-n need to hold channel. Note:No need to hold channel while playing level 2 chime |
| BL25 | 1-3-2021 | cmathyam | Level 9 chimes modified from Infinite to 2 cycles as IGN off alerts cyclic behavior is removed Prewelcome chime is removed |
| BL26 | 8-3-2021 | cmathyam | 1.Tick tock wav files modified 1. Rear Seat belt trigger condition modified from 3F to 2F |
| BL27 | 30-Mar-2021 | bsathyak | 2578779 - Summary Table updated for New WAV file changes 2579116 - Updated WAV duration details 2667316 - Updated volume details 2667296 - Updated WAV names 2322988 - Updated duration of WAV 3897512 - Added requirement for Part1 & 2 triggers |
| BL28 | 07-05-201 | nsathyan | KPI Update - Chimes - Updated requirement - 1934436 SysTask Reference: 585370 |
| BL29 | 28-5-2021 | cmathyam | Sunroof chime added driver open status |
| BL31 | 23-5-2021 | cmathyam | DPF chime new feature is added. Req ID:1934255 -DDD, KeyFob store , KeyFob |
| BL31 |  |  | Recall, message notification updated in Summary table -standalone. |
| BL32 | 19//11/2021 | cmathyam | Req ID :1934255 updated for standalone cluster based on 1517327: Alert - Alert cyclic to 5sec timeout and chimes - SysFS11_Alert - PB DCR |
| BL33 | 16/12/2021 | ssenth12 | Req ID: 2627876 - Updated flow chart for DDD chime snooze behavior Req ID: 3897512 - Applied W601 Low, Z101 Low, Z101 Mid variants for Seat Belt Reminder Req ID: 1934255 - Splittedup Seat Belt Reminder chime into Part1 & Part2. Priority of other chimes shifted. Req ID: 4266694 - Pattern 3 for Seat Belt chime pattern added WP:1517328 - to be delinked after PR 3897512 - Removed W601 Low, Z101 Low, Z101 Mid variants. 1934255 - Removed the split up (reverted same as BL32) 4266694 - Removed this artifact (Remove Pattern3) |
| BL36 | 10/8/2022 | cmathyam | Req ID :1934255 Updated for chimes summary table for frequencies |
| BL37 | 31/08/2022 | bsathyak | ReqID: 1934255, 2578779, 2579116, 3897512, 3911810 Updated SBR Chime requirements for NCAP comments |
| BL38 | 25/1/2022 | cmathyam | Req ID: 3897512,3911810,2578779,2579116 Updated req for W601 HIGH. NCAP changes applicable only for z101 variants |
| BL39 | 11/05/2023 | Kaamesh K | Section 0-1.0-14 (ID: 2311951) and section 0- 1.0-15 (ID: 2312537) old seatbelt chime requirement is struck, Section 0-1.0-16 (ID: 5132343) new seatbelt chime requirements are added as per new SOW. Chime summary table is updated for seatbelt chimes (ID: 1934255, 2578779) |
| BL40 | 2/8/2023 | Chandana Mathyam | Req ID: 5134008 update on Seatbelt chime Req ID: 2578779 update on Removal of PART-1 , PART-2 chime for W601 High |
| BL40 | 24/10/2024 | Kaamesh K | FVSA Chime added MS22029826-105380: [S220/W502/S237]: Chime: FVSA Chime -Application Implementation |
| BL06 | 24/10/2024 | Kaamesh K | IACC Chime added MS22029826-105373: [S220/W502/S237]: Chime: IACC Chime -Application Implementation |
- Variant: S220, W502
- Stakeholder Requirement State: In Review
- System Requirement State: Draft
- Software Requirement State: Draft
- Primary Discipline: TBD
- Requirement Type: TBD

#### MS22029826-71328: Table of Revision-S237 (Information)
| Revision | Section | Remarks | Date | Author |
| --- | --- | --- | --- | --- |
| 1.1 | Chime | 1.Gear Shift Error Chime | 6/16/2023 | bmohan1 |
| 1.1 | Chime | 2.Shift Not Possible Chime | 6/16/2023 | bmohan1 |
| 1.1 | Chime | 3.Shift to P not Allowed Chime | 6/16/2023 | bmohan1 |
| 1.1 | Chime | 4.Press Brake to Shift Chime | 6/16/2023 | bmohan1 |
| 1.1 | Chime | 5.Press Shift unlock Switch Chime | 6/16/2023 | bmohan1 |
| 1.1 | Chime | 6.Park Switch Struck Chime | 6/16/2023 | bmohan1 |
| 1.1 | Chime | 7.Shift Unlock Switch Struck Chime | 6/16/2023 | bmohan1 |
| 1.1 | Chime | 8.Charge Fault Chime | 6/16/2023 | bmohan1 |
| 1.1 | Chime | 9.Charge Complete Chime | 6/16/2023 | bmohan1 |
| 1.1 | Chime | 10.Charge Terminate Chime | 6/16/2023 | bmohan1 |
| 1.1 | Chime | 11.Go Slow Chime | 6/16/2023 | bmohan1 |
| 1.1 | Chime | 12.Stop Car Status Alert | 6/16/2023 | bmohan1 |
| 1.1 | Chime | 13.Safe Mode Chime | 6/16/2023 | bmohan1 |
| 1.1 | Chime | 14.Drive Fault Alert | 6/16/2023 | bmohan1 |
| 1.1 | Chime | 15.Restart Alert | 6/16/2023 | bmohan1 |
| 1.1 | Chime | 16.EV Service Due Alert | 6/16/2023 | bmohan1 |
| 1.1 | Chime | 17.Stopping Alert | 6/16/2023 | bmohan1 |
| 1.1 | Chime | 18.Insert Plug Full Alert | 6/16/2023 | bmohan1 |
| 1.1 | Chime | 19.Power Save Mode Alert | 6/16/2023 | bmohan1 |
| 1.1 | Chime | 20.Shift Gear to N Alert | 6/16/2023 | bmohan1 |
| 1.1 | Chime | 21.Release Throttle Alert | 6/16/2023 | bmohan1 |
| 1.1 | Chime | 22.Unplug CAR Alert are added | 6/16/2023 | bmohan1 |
| 1.1 | Chime | 23.Chimes Summary table modified | 6/16/2023 | bmohan1 |
| 1.2 | Chime | 1.Turn On Mains Chime | 6/21/2023 | bmohan1 |
| 1.2 | Chime | 2.Charge Car Chime | 6/21/2023 | bmohan1 |
| 1.2 | Chime | 3.Activate Revive Chime | 6/21/2023 | bmohan1 |
| 1.2 | Chime | 4.Revive Chime | 6/21/2023 | bmohan1 |
| 1.2 | Chime | 5.Revive Mode Chime | 6/21/2023 | bmohan1 |
| 1.2 | Chime | 6.Revive Unsuccessful Chime | 6/21/2023 | bmohan1 |
| 1.2 | Chime | 7.Isolation Fault Chime | 6/21/2023 | bmohan1 |
| 1.2 | Chime | 8.Go Slow (Flash) Chime | 6/21/2023 | bmohan1 |
| 1.2 | Chime | 9.Hill Hold Deactivate Chime | 6/21/2023 | bmohan1 |
| 1.2 | Chime | 10.EPT High Temp Chime | 6/21/2023 | bmohan1 |
| 1.2 | Chime | 11.HV Battery High Temperature Chime /Thermal | 6/21/2023 | bmohan1 |
| 1.2 | Chime | Runaway | 6/21/2023 | bmohan1 |
| 1.2 | Chime | 12.Charging Chime | 6/21/2023 | bmohan1 |
| 1.2 | Chime | 13.Engage Park Chime | 6/21/2023 | bmohan1 |
| 1.2 | Chime | 14.Turn Ign Key to start vehicle Chime | 6/21/2023 | bmohan1 |
| 1.2 | Chime | 15.Press Start stop switch to start Chime | 6/21/2023 | bmohan1 |
| 1.2 | Chime | 16.Press Brake Chime | 6/21/2023 | bmohan1 |
| 1.2 | Chime | 17.Park Motor Failure Chime | 6/21/2023 | bmohan1 |
| 1.2 | Chime | 18.Stay In Park Chime | 6/21/2023 | bmohan1 |
| 1.2 | Chime | 19.Battery Low Temp Chime | 6/21/2023 | bmohan1 |
| 1.2 | Chime | 20.Coolant Leakage Park & Leave Vehicle Chime | 6/21/2023 | bmohan1 |
| 1.2 | Chime | 21.Coolant Low Temp Chime are added | 6/21/2023 | bmohan1 |
| 1.2 | Chime | 22.Seatbelt Chime modified | 6/21/2023 | bmohan1 |
| 1.5 | Chime | 1.Summary Table updated with Coolant Leakage Park & | 7/18/2023 | bmohan1 |
| 1.5 | Chime | Leave Vehicle Chime | 7/18/2023 | bmohan1 |
| 1.5 | Chime | 2.Preconditioning Chime & HVIL FAULT Chime added | 7/18/2023 | bmohan1 |
| 1.5 | Chime | 3.Engine running st updated in seat belt chime | 7/18/2023 | bmohan1 |
| 2 (V3) | Chime | 1.Low brake fluid chime added & Engine Running St Updated | 18-08-23 | bmohan1 |
| V4 | Chime | 1.Charge flap alert added part of message notification. 2.Notiifcation alert for S237 Modified to ON/OFF ignition cycle | 16-04-24 | cmathyam |
| BL06 | Chime | FVSA chime added MS22029826-105380: [S220/W502/S237]: Chime: FVSA Chime -Application Implementation | 24/10/2024 | kkumara5 |
| BL06 | Chime | IACC Chime added MS22029826-105373: [S220/W502/S237]: Chime: IACC Chime -Application Implementation | 24/10/2024 | kkumara5 |
| V5 | Chime | Added FVSA Chimes, IACC Failure Chimes to Chimes Summary for S237 | 04/10/24 | myunus |
| V6 | Chime | Seat Belt: MS22029826-114483: Added feature code to select MBFM and SBRM signal MS22029826-114490: Updated functional logic table by adding SBRM signal | 7/1/24 | pkumar47 |
- Variant: S237
- Stakeholder Requirement State: In Review
- System Requirement State: Draft
- Software Requirement State: Draft
- Primary Discipline: TBD
- Requirement Type: TBD

#### MS22029826-103826: Table of Revision-S220_SB_ADP_W601 (Information)
| Revision | Section | Remarks | Date | Author |
| --- | --- | --- | --- | --- |
| 1.1 | Chime | 1.Seatbelt Chime - Silver Box Adaptation (MS22029826-103748) added | 4/10/2024 | amore1 |
| 1.1 | Chime | FVSA chime added | 10/10/2024 | kkumara5 |
| 1.1 | Chime | IACC Chime added | 14/10/2024 | amore1 |
| 1.1 | Chime | FVSA and IACC chimes removed for SB_ADP | 29/11/2024 | kkumara5 |
- Variant: S220_SB_ADP_W601-V1, S220_SB_ADP_W601-V2
- Stakeholder Requirement State: In Review
- System Requirement State: Draft
- Software Requirement State: Draft
- Primary Discipline: TBD
- Requirement Type: TBD

#### MS22029826-122243: Revision History Table for Z112_SB_ADP_Z101 Variants (Information)
| Date | Author | Modifications |
| --- | --- | --- |
| 18/04/2025 | Manikandan G | Added Z112_SB_ADP_Z101-V5,Z112_SB_ADP_Z101-V6,Z112_SB_ADP_Z101-V7 variants in following section 1. FVSA Chime 2. IACC Chime |
| 09/05/2025 | Manikandan G | MS22029826-103748: Added Z112 Variant for Seatbelt Chime - Silver Box Adaptation section |
- Variant: Z112_SB_ADP_Z101-V5, Z112_SB_ADP_Z101-V6, Z112_SB_ADP_Z101-V7
- Stakeholder Requirement State: In Review
- System Requirement State: Draft
- Software Requirement State: Draft
- Primary Discipline: TBD
- Requirement Type: TBD

### MS22029826-44134: Generic (Heading)
- Variant: S220, S237, W502
- Stakeholder Requirement State: In Review
- System Requirement State: Draft
- Software Requirement State: Draft
- Primary Discipline: TBD
- Requirement Type: TBD

#### MS22029826-52388: Figure - Chime Types (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60628: Chime Types (System Requirement)
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- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60630: ChimeTypes (System Requirement)
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- Variant: S237
- Stakeholder Requirement State: In Review
- System Requirement State: Draft
- Software Requirement State: Draft
- Primary Discipline: SW
- Requirement Type: Functional

#### MS22029826-52389: Table - Chime Types (System Requirement)
- Variant: S220, S237, W502
- Stakeholder Requirement State: In Review
- System Requirement State: Draft
- Software Requirement State: Draft
- Primary Discipline: SW
- Requirement Type: Functional

##### MS22029826-60632: TYPE (System Requirement)
| TYPE | Description | Parameter | Example |
| --- | --- | --- | --- |
| A | Play Once Stop when complete No Pre-emption | N\A |  |
| B | Play continuously Stop immediately if condition recovered Pre-emption possible | Period T |  |
| C | Play for pre-defined number of cycles Stop only when complete Pre-emption possible | Period T, Cycles N |  |
| D | Play for pre-defined number of cycles Stop with current cycle if condition recovered Pre-emption possible | Period T, Cycles N |  |
| E | Play Once Stop with current cycle if condition recovered No Pre-emption | N\A |  |
- Variant: S237
- Stakeholder Requirement State: In Review
- System Requirement State: Draft
- Software Requirement State: Draft
- Primary Discipline: SW
- Requirement Type: Functional

##### MS22029826-60634: Type (System Requirement)
| Type | Description |
| --- | --- |
| Type A | Played once (1 cycle). It shall be not be repeated. Stopped only when the duration is complete, even though the condition goes inactive prior to it. It shall not be pre-empted (on higher priority chime) until the duration is completed. |
| Type B | Played continuously. When the condition goes inactive, Stopped immediately. It shall be pre-empted (on higher priority chime) provided at least 1 cycle is played. |
| Type C | Played N Number of Cycles Stopped when the N number of cycles is completed or condition goes inactive whichever is earlier. It shall be pre-empted (on higher priority chime) provided at least 1 cycle is played. |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52390: Table - Chime Summary (Heading)
- Variant: S220, S220_SB_ADP_W601-V1, S220_SB_ADP_W601-V2, S237, W502
- Stakeholder Requirement State: In Review
- System Requirement State: Draft
- Software Requirement State: Draft
- Primary Discipline: TBD
- Requirement Type: TBD

##### MS22029826-60643: W502 ,S220 & S220_SB_ADP_W601 (Information)
- Variant: S220, S220_SB_ADP_W601-V1, S220_SB_ADP_W601-V2, W502
- Stakeholder Requirement State: In Review
- System Requirement State: Draft
- Software Requirement State: Draft
- Primary Discipline: SW
- Requirement Type: Functional

###### MS22029826-60636: Priority (System Requirement)
| Group | Priority | Sound name | WAV File | Type | Period (ms) | On Time (ms) | Off Time (ms) | Cycles | Volume | User configurable (Tone and volume) | IGN |
| --- | --- | --- | --- | --- | --- | --- | --- | --- | --- | --- | --- |
| 1 | 1 | WELCOME | 1_Welcome | A | N/A | N/A | N/A | 1 | 90% | -- | On |
| 1 | 2 | GOODBYE | 3_Goodbye | A | N/A | N/A | N/A | 1 | 90% | -- | On |
| 2 | 1 | Seat Belt warning / Rear Passenger Seat Belt | S-15_V3_16kHz X 16Bit mono_mod | C | 1000 | 1000 | 0 | 95 (Calibration/Period) -Front(Drv/Psgr) | 40% | -- | On |
| 2 | 1 | Seat Belt warning / Rear Passenger Seat Belt | S-15_V3_16kHz X 16Bit mono_mod | C | 1000 | 1000 | 0 | 35(Calibration/Period -Rear) | 40% | -- | On |
| 2 | 2 | AEB Collision Warning 3 | 12_rec_RSST_nSndID_AEB | B | 100 | 100 | 0 | Infinite | 40% | -- | On |
| 2 | 3 | AEB Collision Warning2 | 12_rec_RSST_nSndID_AEB | C | 200 | 100 | 100 | 8 | 40% | -- | On |
| 2 | 4 | AEB Collision Warning 1 | 12_rec_RSST_nSndID_AEB | C | 400 | 100 | 300 | 4 | 40% | -- | On |
| 2 | 5 | OVERSPEED Level 2 Warning | S-16_V2_Volume Increase_16kHz X 16Bit_mod | B | 2000 | 2000 | (calibration interval - WAV duration) | Infinite | 40% | -- | On |
| 2 | 5 | OVERSPEED Level 2 Warning | S-16_V2_Volume Increase_16kHz X 16Bit_mod | B | (calibration interval) | 2000 | (calibration interval - WAV duration) | Infinite | 40% | -- | On |
| 2 | 6 | OVERSPEED Level 1 Warning | S-16_V2_Volume Increase_16kHz X 16Bit_mod | B | 60000 | 2000 | (calibration interval - WAV duration) | Infinite | 40% | -- | On |
| 2 | 6 | OVERSPEED Level 1 Warning | S-16_V2_Volume Increase_16kHz X 16Bit_mod | B | (calibration interval) | 2000 | (calibration interval - WAV duration) | Infinite | 40% | -- | On |
| 3 | 1 | Reverse | P4Cont_mono_16_mod | C | 100 | 100 | 0 | 5 | 40% | -- | On |
| 3 | 2 | RPAS Self Check | P4Cont_mono_16_mod | C | 100 | 100 | 0 | 5 | 40% | -- | On |
| 3 | 3 | RPAS Sensor Fail warning | P4Cont_mono_16_mod | C | 100 | 100 | 0 | 30 | 40% | -- | On |
| 3 | 4 | RR PAS Lv1, Warning | P4Cont_mono_16_mod | B | 100 | 100 | 0 | Infinite | 40% | -- | On |
| 3 | 5 | RR PAS Lv2, Warning | P4_mono_16_mod | B | 150 | 150 | 0 | Infinite | 40% | -- | On |
| 3 | 6 | RR PAS Lv3, Warning | P4_mono_16_mod | B | 300 | 150 | 150 | Infinite | 40% | -- | On |
| 3 | 7 | RR PAS Lv4, Warning | P4_mono_16_mod | B | 600 | 150 | 450 | Infinite | 40% | -- | On |
| 3 | 8 | APA RPAS Self Check | P4Cont_mono_16_mod | C | 100 | 100 | 0 | 5 | 40% | -- | On |
| 3 | 9 | APA RPAS Sensor Fail warning | P4Cont_mono_16_mod | C | 100 | 100 | 0 | 30 | 40% | -- | On |
| 3 | 10 | APA RR PAS Lv1, Warning | P4Cont_mono_16_mod | B | 100 | 100 | 0 | Infinite | 40% | -- | On |
| 3 | 11 | APA RR PAS Lv2, Warning | P4_mono_16_mod | B | 150 | 150 | 0 | Infinite | 40% | -- | On |
| 3 | 12 | APA RR PAS Lv3, Warning | P4_mono_16_mod | B | 300 | 150 | 150 | Infinite | 40% | -- | On |
| 3 | 13 | APA RR PAS Lv4, Warning | P4_mono_16_mod | B | 600 | 150 | 450 | Infinite | 40% | -- | On |
| 4 | 1 | APA SPAS Lv1, Warning | 5_RPAS_Type2_St1_St2_cont_update | B | 150 | 150 | 0 | Infinite | 40% | -- | On |
| 4 | 2 | APA SPAS Lv2, Warning | 6_RPAS_Type2_St1_St2_300ms_update | B | 150 | 150 | 0 | Infinite | 40% | -- | On |
| 4 | 3 | APA SPAS Lv3, Warning | 6_RPAS_Type2_St1_St2_300ms_update | B | 300 | 150 | 150 | Infinite | 40% | -- | On |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-60639: Priority (Information)
| Group | Priority | Sound name | WAV File | Type | Period (ms) | On Time (ms) | Off Time (ms) | Cycles | Volume | User configurable (Tone and volume) | IGN |
| --- | --- | --- | --- | --- | --- | --- | --- | --- | --- | --- | --- |
| 5 | 1 | FR PAS Lv1, Warning | 9_RPAS_Type4_St1_St2_cont_update | B | 150 | 150 | 0 | Infinite | 40% | -- | On |
| 5 | 2 | FR PAS Lv2, Warning | 10_RPAS_Type4_St1_St2_300ms_update | B | 150 | 150 | 0 | Infinite | 40% | -- | On |
| 5 | 3 | FR PAS Lv3, Warning | 10_RPAS_Type4_St1_St2_300ms_update | B | 300 | 150 | 150 | Infinite | 40% | -- | On |
| 5 | 4 | FR PAS Lv4, Warning | 10_RPAS_Type4_St1_St2_300ms_update | B | 600 | 150 | 450 | Infinite | 40% | -- | On |
| 5 | 5 | APA FR PAS Lv1, Warning | 9_RPAS_Type4_St1_St2_cont_update | B | 150 | 150 | 0 | Infinite | 40% | -- | On |
| 5 | 6 | APA FR PAS Lv2, Warning | 10_RPAS_Type4_St1_St2_300ms_update | B | 150 | 150 | 0 | Infinite | 40% | -- | On |
| 5 | 7 | APA FR PAS Lv3, Warning | 10_RPAS_Type4_St1_St2_300ms_update | B | 300 | 150 | 150 | Infinite | 40% | -- | On |
| 5 | 8 | APA FR PAS Lv4, Warning | 10_RPAS_Type4_St1_St2_300ms_update | B | 600 | 150 | 450 | Infinite | 40% | -- | On |
| 6 | 1 | AMT buzzer | 11_rec_RSST_nSndID_RPAS_St3 | C | Refer Pattern 1 |  |  | 4 | 40% | -- | On |
| 6 | 2 | High Temp Warning | 11_rec_RSST_nSndID_RPAS_St3 | C | Refer Pattern 2 |  |  | 4 | 40% | -- | On |
| 6 | 3 | Low Engine Oil Pressure | 11_rec_RSST_nSndID_RPAS_St3 | C | Refer Pattern 2 |  |  | 4 | 40% | -- | On |
| 6 | 4 | Low Brake Fluid | 11_rec_RSST_nSndID_RPAS_St3 | C | Refer Pattern 2 |  |  | 4 | 40% | -- | On |
| 6 | 5 | WIF | 11_rec_RSST_nSndID_RPAS_St3 | C | Refer Pattern 2 |  |  | 4 | 40% | -- | On |
| 7 | 1 | TJA Hands-Off Level2 | 13_LDWS Type2 | B | 500 | 500 | 0 | Infinite | 40% | -- | On |
| 7 | 2 | TJA Released Steering control | 14_LDWS Type4 | B | 500 | 500 | 0 | Infinite | 40% | -- | On |
| 7 | 3 | LKA Hands-Off | 13_LDWS Type2 | B | 500 | 500 | 0 | Infinite | 40% | -- | On |
| 7 | 4 | ACC Info | 15_BSD_LCA_RCTA_updated | C | 1000 | 1000 | 0 | 1 | 40% | -- | On |
| 7 | 5 | FVSA | 15_BSD_LCA_RCTA_updated | C | 1000 | 1000 | 0 | 1 | 40% | -- | On |
| 7 | 6 | Lane Departure | 16_LDWS Type1 or | B | 500 | 500 | 0 | Infinite | 25% | Yes | On |
| 7 | 6 | Lane Departure | 17_LDWS Type5 or | B | 500 | 500 | 0 | Infinite | 25% | Yes | On |
| 7 | 6 | Lane Departure | 18_LDWS Type3 | B | 500 | 500 | 0 | Infinite | 25% | Yes | On |
- Variant: S220, S220_SB_ADP_W601-V1, S220_SB_ADP_W601-V2, W502
- Stakeholder Requirement State: In Review
- System Requirement State: Draft
- Software Requirement State: Draft
- Primary Discipline: SW
- Requirement Type: Functional

###### MS22029826-60641: Priority (Information)
| Group | Priority | Sound name | WAV File | Type | Period (ms) | On Time (ms) | Off Time (ms) | Cycles | Volume | User configurable (Tone and volume) | IGN |
| --- | --- | --- | --- | --- | --- | --- | --- | --- | --- | --- | --- |
| 8 | 1 | Door Open | 19_rec_RSST_nSndID_Message | C | 1000 | 1000 | 0 | 4 | 50% | -- | On |
| 8 | 2 | Parking brake | 19_rec_RSST_nSndID_Message | C | 1000 | 1000 | 0 | 4 | 50% | -- | On |
| 8 | 3 | Message Notification | M15_Mono_16 | A | 1000 | 1000 | 4000 | 1 | 50% | Yes | On |
| 8 | 3 | Message Notification | M25.2 | A | 1000 | 1000 | 4000 | 1 | 50% | Yes | On |
| 8 | 3 | Message Notification | M26 | A | 1000 | 1000 | 4000 | 1 | 50% | Yes | On |
| 8 | 4 | IACC Chime | M15_Mono_16 | A | 1000 | 1000 | 4000 | 1 | 50% | Yes | On |
| 8 | 5 | Low Fuel | 19_rec_RSST_nSndID_Message | C | 1000 | 1000 | 0 | 4 | 50% | -- | On |
| 8 | 6 | Key Fob Memory Store | 22_SMART_AUTO_LOCK_SET | A | 600 | 600 | 0 | 1 | 50% | -- | On |
| 8 | 7 | Key Fob Memory Recall | 23_SMART_AUTO_LOCK_RELEASE | A | 1000 | 1000 | 0 | 1 | 50% | -- | On |
| 8 | 8 | DDD | 19_rec_RSST_nSndID_Message | B | 1000 | 1000 | 0 | Infinite | 40% | -- | On |
| 9 | 1 | PKE Key out | T-12 Key Out Alert16 | C | 1000 | 900 | 100 | 5 | 50% | -- | Off/On |
| 9 | 2 | PKE Fob key reminder | T-12 Key Out Alert16 | C | 1000 | 900 | 100 | 5 | 50% | -- | Off/On |
| 9 | 3 | Wireless Charging Forgotten | T-12 Key Out Alert16 | C | 1000 | 900 | 100 | 5 | 50% | -- | Off |
| 9 | 4 | External Light Warning | T-12 Key Out Alert16 | C | 1000 | 900 | 100 | 5 | 50% | -- | Off |
| 9 | 5 | Sunroof Open Warning | T-12 Key Out Alert16 | C | 1000 | 900 | 100 | 5 | 50% | -- | Off |
| 9 | 6 | Key In Reminder | T-12 Key Out Alert16 | C | 1000 | 900 | 100 | 5 | 50% | -- | Off |
| 9 | 7 | AMT Engage Park Brake Chime | T-12 Key Out Alert16 | C | 1000 | 900 | 100 | 5 | 50% | -- | Off |
| 9 | 8 | DPF Chime | DPF Filter Chime_D3_16khz x 16 bit | C | 1000 | 10Cycles X 1000 | 3 min | Infinite | 50% | -- | On |
| 9 | 8 | DPF Chime | DPF Filter Chime_D3_16khz x 16 bit | C | 1000 | 10Cycles X 1000 | 3 min | (Chime shall be repeated for every 3 min for Complete Ignition Cycle until condition is True) | 50% | -- | On |
| 10 | 1 | Turn signal Tick | T13_Tok_16kHz_450ms | A | 450 | 450 | 0 | 1 | 40% | Yes | Off/On |
| 10 | 1 | Turn signal Tick | T-14 Tok_16kHz_450ms | A | 450 | 450 | 0 | 1 | 40% | Yes | Off/On |
| 10 | 1 | Turn signal Tick | Alturas_16kHz_750ms_mod | A | 450 | 450 | 0 | 1 | 40% | Yes | Off/On |
| 10 | 2 | Turn signal Tock | T13_Tik_16kHz_300ms | A | 300 | 300 | 0 | 1 | 40% | Yes | Off/On |
| 10 | 2 | Turn signal Tock | T-14 Tik_16kHz_300ms | A | 300 | 300 | 0 | 1 | 40% | Yes | Off/On |
| 10 | 2 | Turn signal Tock | Tok_Silence | A | 300 | 300 | 0 | 1 | 40% | Yes | Off/On |
- Variant: S220, W502
- Stakeholder Requirement State: In Review
- System Requirement State: Draft
- Software Requirement State: Draft
- Primary Discipline: SW
- Requirement Type: Functional

##### MS22029826-60645: S237 (Information)
- Stakeholder Requirement State: In Review
- System Requirement State: Draft
- Software Requirement State: Draft
- Primary Discipline: SW
- Requirement Type: Functional

###### MS22029826-60647: Group (Information)
| Group | Priority | Sound name | WAV File | Type | Period (ms) | On Time (ms) | Off Time (ms) | Cycles | Volume | User configurable (Tone and volume) | IGN |
| --- | --- | --- | --- | --- | --- | --- | --- | --- | --- | --- | --- |
| 1 | 1 | WELCOME | 1_Welcome | A | N/A | N/A | N/A | 1 | 90% | -- | On |
| 1 | 2 | GOODBYE | 3_Goodbye | A | N/A | N/A | N/A | 1 | 90% | -- | On |
| 2 | 1 | Seat Belt warning / Rear Passenger Seat Belt | S-15_V3_16kHz X 16Bit mono_mod | C | 1000 | 1000 | 0 | 95 (Calibration/Period) -Front(Drv/Psgr) | 40% | -- | On |
| 2 | 1 | Seat Belt warning / Rear Passenger Seat Belt | S-15_V3_16kHz X 16Bit mono_mod | C | 1000 | 1000 | 0 | 35(Calibration/Period -Rear) | 40% | -- | On |
| 2 | 2 | Ready to Drive Chime | M25.2 | A | 1000 | 1000 | 0 | 1 | 50% | -- | On |
| 2 | 3 | AEB Collision Warning 3 | 12_rec_RSST_nSndID_AEB | B | 100 | 100 | 0 | Infinite | 40% | -- | On |
| 2 | 3 | AEB Collision Warning2 | 12_rec_RSST_nSndID_AEB | C | 200 | 100 | 100 | 8 | 40% | -- | On |
| 2 | 4 | AEB Collision Warning 1 | 12_rec_RSST_nSndID_AEB | C | 400 | 100 | 300 | 4 | 40% | -- | On |
| 2 | 5 | OVERSPEED Level 2 Warning | S-16_V2_Volume Increase_16kHz X 16Bit_mod | B | 2000 (calibration interval) | 2000 | (calibration interval - WAV duration) | Infinite | 40% | -- | On |
| 2 | 6 | OVERSPEED Level 1 Warning | S-16_V2_Volume Increase_16kHz X 16Bit_mod | B | 60000 (calibration interval) | 2000 | (calibration interval - WAV duration) | Infinite | 40% | -- | On |
| 2 | 7 | Coolant Leakage Park & Leave Vehicle Chime | T-12 Key Out Alert16 | D | 1000 | 1000 | 0 | Infinite | 40% | -- | Off/On |
| 3 | 1 | Reverse | P4Cont_mono_16_mod | C | 100 | 100 | 0 | 5 | 40% | -- | On |
| 3 | 2 | RPAS Self Check | P4Cont_mono_16_mod | C | 100 | 100 | 0 | 5 | 40% | -- | On |
| 3 | 3 | RPAS Sensor Fail warning | P4Cont_mono_16_mod | C | 100 | 100 | 0 | 30 | 40% | -- | On |
| 3 | 4 | RR PAS Lv1, Warning | P4Cont_mono_16_mod | B | 100 | 100 | 0 | Infinite | 40% | -- | On |
| 3 | 5 | RR PAS Lv2, Warning | P4_mono_16_mod | B | 150 | 150 | 0 | Infinite | 40% | -- | On |
| 3 | 6 | RR PAS Lv3, Warning | P4_mono_16_mod | B | 300 | 150 | 150 | Infinite | 40% | -- | On |
| 3 | 7 | RR PAS Lv4, Warning | P4_mono_16_mod | B | 600 | 150 | 450 | Infinite | 40% | -- | On |
| 3 | 8 | APA RPAS Self Check | P4Cont_mono_16_mod | C | 100 | 100 | 0 | 5 | 40% | -- | On |
| 3 | 9 | APA RPAS Sensor Fail warning | P4Cont_mono_16_mod | C | 100 | 100 | 0 | 30 | 40% | -- | On |
| 3 | 10 | APA RR PAS Lv1, Warning | P4Cont_mono_16_mod | B | 100 | 100 | 0 | Infinite | 40% | -- | On |
| 3 | 11 | APA RR PAS Lv2, Warning | P4_mono_16_mod | B | 150 | 150 | 0 | Infinite | 40% | -- | On |
| 3 | 12 | APA RR PAS Lv3, Warning | P4_mono_16_mod | B | 300 | 150 | 150 | Infinite | 40% | -- | On |
| 3 | 13 | APA RR PAS Lv4, Warning | P4_mono_16_mod | B | 600 | 150 | 450 | Infinite | 40% | -- | On |
- Variant: S237
- Stakeholder Requirement State: In Review
- System Requirement State: Draft
- Software Requirement State: Draft
- Primary Discipline: SW
- Requirement Type: Functional

###### MS22029826-60649: Group (Information)
| Group | Priority | Sound name | WAV File | Type | Period (ms) | On Time (ms) | Off Time (ms) | Cycles | Volume | User configurable (Tone and volume) | IGN |
| --- | --- | --- | --- | --- | --- | --- | --- | --- | --- | --- | --- |
| 4 | 1 | APA SPAS Lv1, Warning | 5_RPAS_Type2_St1_St2_cont_update | B | 150 | 150 | 0 | Infinite | 40% | -- | On |
| 4 | 2 | APA SPAS Lv2, Warning | 6_RPAS_Type2_St1_St2_300ms_update | B | 150 | 150 | 0 | Infinite | 40% | -- | On |
| 4 | 3 | APA SPAS Lv3, Warning | 6_RPAS_Type2_St1_St2_300ms_update | B | 300 | 150 | 150 | Infinite | 40% | -- | On |
| 5 | 1 | FR PAS Lv1, Warning | 9_RPAS_Type4_St1_St2_cont_update | B | 150 | 150 | 0 | Infinite | 40% | -- | On |
| 5 | 2 | FR PAS Lv2, Warning | 10_RPAS_Type4_St1_St2_300ms_update | B | 150 | 150 | 0 | Infinite | 40% | -- | On |
| 5 | 3 | FR PAS Lv3, Warning | 10_RPAS_Type4_St1_St2_300ms_update | B | 300 | 150 | 150 | Infinite | 40% | -- | On |
| 5 | 4 | FR PAS Lv4, Warning | 10_RPAS_Type4_St1_St2_300ms_update | B | 600 | 150 | 450 | Infinite | 40% | -- | On |
| 5 | 5 | APA FR PAS Lv1, Warning | 9_RPAS_Type4_St1_St2_cont_update | B | 150 | 150 | 0 | Infinite | 40% | -- | On |
| 5 | 6 | APA FR PAS Lv2, Warning | 10_RPAS_Type4_St1_St2_300ms_update | B | 150 | 150 | 0 | Infinite | 40% | -- | On |
| 5 | 7 | APA FR PAS Lv3, Warning | 10_RPAS_Type4_St1_St2_300ms_update | B | 300 | 150 | 150 | Infinite | 40% | -- | On |
| 5 | 8 | APA FR PAS Lv4, Warning | 10_RPAS_Type4_St1_St2_300ms_update | B | 600 | 150 | 450 | Infinite | 40% | -- | On |
| 6 | 1 | SBW Chimes | 6_rec_RSST_nSndID_RPAS_St3_16k | C | Refer Pattern 2 |  |  | 4 | 40% | -- | On |
| 6 | 2 | AMT buzzer | 11_rec_RSST_nSndID_RPAS_St3 | C | Refer Pattern 1 |  |  | 4 | 40% | -- | On |
| 6 | 3 | High Temp Warning | 11_rec_RSST_nSndID_RPAS_St3 | C | Refer Pattern 2 |  |  | 4 | 40% | -- | On |
| 6 | 4 | Low Engine Oil Pressure | 11_rec_RSST_nSndID_RPAS_St3 | C | Refer Pattern 2 |  |  | 4 | 40% | -- | On |
| 6 | 5 | Low Brake Fluid | 11_rec_RSST_nSndID_RPAS_St3 | C | Refer Pattern 2 |  |  | 4 | 40% | -- | On |
| 6 | 6 | WIF | 11_rec_RSST_nSndID_RPAS_St3 | C | Refer Pattern 2 |  |  | 4 | 40% | -- | On |
| 7 | 1 | TJA Hands-Off Level2 | 13_LDWS Type2 | B | 500 | 500 | 0 | Infinite | 40% | -- | On |
| 7 | 2 | TJA Released Steering control | 14_LDWS Type4 | B | 500 | 500 | 0 | Infinite | 40% | -- | On |
| 7 | 3 | LKA Hands-Off | 13_LDWS Type2 | B | 500 | 500 | 0 | Infinite | 40% | -- | On |
| 7 | 4 | ACC Info | 15_BSD_LCA_RCTA_updated | C | 1000 | 1000 | 0 | 1 | 40% | -- | On |
| 7 | 5 | FVSA | 15_BSD_LCA_RCTA_updated | C | 1000 | 1000 | 0 | 1 | 40% | -- | On |
| 7 | 6 | Lane Departure | 16_LDWS Type1 or | B | 500 | 500 | 0 | Infinite | 25% | Yes | On |
| 7 | 6 | Lane Departure | 17_LDWS Type5 or | B | 500 | 500 | 0 | Infinite | 25% | Yes | On |
| 7 | 6 | Lane Departure | 18_LDWS Type3 | B | 500 | 500 | 0 | Infinite | 25% | Yes | On |
- Variant: S237
- Stakeholder Requirement State: In Review
- System Requirement State: Draft
- Software Requirement State: Draft
- Primary Discipline: SW
- Requirement Type: Functional

###### MS22029826-60652: Group (Information)
| Group | Priority | Sound name | WAV File | Type | Period (ms) | On Time (ms) | Off Time (ms) | Cycles | Volume | User configurable (Tone and volume) | IGN |
| --- | --- | --- | --- | --- | --- | --- | --- | --- | --- | --- | --- |
| 8 | 1 | Limp Home Mode | 7_rec_RSST_nSndID_Message | C | 1000 | 1000 | 0 | 4 | 50% | -- | On |
| 8 | 2 | Door Open | 19_rec_RSST_nSndID_Message | C | 1000 | 1000 | 0 | 4 | 50% | -- | On |
| 8 | 3 | Parking brake (Park Brake Engaged) | 19_rec_RSST_nSndID_Message | C | 1000 | 1000 | 0 | 4 | 50% | -- | On |
| 8 | 4 | Message Notification | M15_Mono_16 | A | 1000 | 1000 | 4000 | 1 | 50% | Yes | On/Off |
| 8 | 4 | Message Notification | M25.2 | A | 1000 | 1000 | 4000 | 1 | 50% | Yes | On/Off |
| 8 | 4 | Message Notification | M26 | A | 1000 | 1000 | 4000 | 1 | 50% | Yes | On/Off |
| 8 | 5 | IACC Chime | M15_Mono_16 | A | 1000 | 1000 | 4000 | 1 | 50% | Yes | On |
| 8 | 6 | Low Fuel | 19_rec_RSST_nSndID_Message | C | 1000 | 1000 | 0 | 4 | 50% | -- | On |
| 8 | 7 | Key Fob Memory Store | 22_SMART_AUTO_LOCK_SET | A | 600 | 600 | 0 | 1 | 50% | -- | On |
| 8 | 8 | Key Fob Memory Recall | 23_SMART_AUTO_LOCK_RELEASE | A | 1000 | 1000 | 0 | 1 | 50% | -- | On |
| 8 | 9 | DDD | 19_rec_RSST_nSndID_Message | B | 1000 | 1000 | 0 | Infinite | 40% | -- | On |
| 9 | 1 | PKE Key out | T-12 Key Out Alert16 | C | 1000 | 900 | 100 | 5 | 50% | -- | Off/On |
| 9 | 2 | PKE Fob key reminder | T-12 Key Out Alert16 | C | 1000 | 900 | 100 | 5 | 50% | -- | Off/On |
| 9 | 3 | Wireless Charging Forgotten | T-12 Key Out Alert16 | C | 1000 | 900 | 100 | 5 | 50% | -- | Off |
| 9 | 4 | External Light Warning | T-12 Key Out Alert16 | C | 1000 | 900 | 100 | 5 | 50% | -- | Off |
| 9 | 5 | Sunroof Open Warning | T-12 Key Out Alert16 | C | 1000 | 900 | 100 | 5 | 50% | -- | Off |
| 9 | 6 | Key In Reminder / RKE Alarms | T-12 Key Out Alert16 | C | 1000 | 900 | 100 | 5 | 50% | -- | Off |
| 9 | 7 | AMT Engage Park Brake Chime | T-12 Key Out Alert16 | C | 1000 | 900 | 100 | 5 | 50% | -- | Off |
| 9 | 8 | DPF Chime | DPF Filter Chime_D3_16khz x 16 bit | C | 1000 | 10Cycles X 1000 | 3 min | Infinite | 50% | -- | On |
| 9 | 8 | DPF Chime | DPF Filter Chime_D3_16khz x 16 bit | C | 1000 | 10Cycles X 1000 | 3 min | (Chime shall be repeated for every 3 min for Complete Ignition Cycle until condition is True) | 50% | -- | On |
| 9 | 9 | EV Alert | T-12 Key Out Alert16 | C | 1000 | 900 | 100 | 5 | 50% | -- | Off/On |
| 10 | 1 | Turn signal Tick | T13_Tok_16kHz_450ms | A | 450 | 450 | 0 | 1 | 40% | Yes | Off/On |
| 10 | 1 | Turn signal Tick | T-14 Tok_16kHz_450ms | A | 450 | 450 | 0 | 1 | 40% | Yes | Off/On |
| 10 | 1 | Turn signal Tick | Alturas_16kHz_750ms_mod | A | 450 | 450 | 0 | 1 | 40% | Yes | Off/On |
| 10 | 2 | Turn signal Tock | T13_Tik_16kHz_300ms | A | 300 | 300 | 0 | 1 | 40% | Yes | Off/On |
| 10 | 2 | Turn signal Tock | T-14 Tik_16kHz_300ms | A | 300 | 300 | 0 | 1 | 40% | Yes | Off/On |
| 10 | 2 | Turn signal Tock | Tok_Silence | A | 300 | 300 | 0 | 1 | 40% | Yes | Off/On |
- Variant: S237
- Stakeholder Requirement State: In Review
- System Requirement State: Draft
- Software Requirement State: Draft
- Primary Discipline: SW
- Requirement Type: Functional

#### MS22029826-52391: Table – Chime Sound Profile (Heading)
- Variant: S220, S220_SB_ADP_W601-V1, S220_SB_ADP_W601-V2, S237, W502
- Stakeholder Requirement State: In Review
- System Requirement State: Draft
- Software Requirement State: Draft
- Primary Discipline: TBD
- Requirement Type: TBD

##### MS22029826-60654: Table – Chime Sound Profile-W502 & S220 (System Requirement)
| Chimes Data |  |  |
| --- | --- | --- |
| WAV | Frequency | Duration (Sec) |
| 1_WELCOME | N/A | 4 |
| 2_PRE WELCOME | N/A | 0 |
| 3_GOOD BYE | N/A | 4 |
| W601 High: S-15_V3_16kHz X 16Bit mono - Part1_mod Z101 High+,Z101 High S-15_V3_16kHz X 16Bit mono_mod | N/A | 3 1 |
| W601 High: S-15_V3_16kHz X 16Bit mono - Part2_mod | N/A | 8 |
| 5_RPAS_Type2_St1_St2_cont_update | A5(892.840) | 0.15 |
| 6_RPAS_Type2_St1_St2_300ms_update | A5(892.840) | 0.15 |
| P4Cont_mono_16_mod | E5 (666.67) | 0.1 |
| P4_mono_16_mod | E5 (666.67) | 0.15 |
| 9_RPAS_Type4_St1_St2_cont_update | F5(708.603) | 0.15 |
| 10_RPAS_Type4_St1_St2_300ms_update | F5(708.603) | 0.15 |
| 11_rec_RSST_nSndID_RPAS_St3 | F#/Gb6(1454.545) | 0.071 |
| 12_rec_RSST_nSndID_AEB | D4(297.613) | 0.1 |
| 13_LDWS Type2 | A#/Bb4(455.531) | 0.5 |
| 14_LDWS Type4 | C#/Db8(4464.200) | 0.5 |
| 15_BSD_LCA_RCTA_updated | A5(892.850) | 0.5 |
| 16_LDWS Type1 | G5(769.690) | 0.5 |
| 17_LDWS Type5 | C#/Db5(558.025) | 0.5 |
| 18_LDWS Type3 | A#/Bb5(949.830) | 0.5 |
| M15_Mono_16 | N/A | 1 |
| M25.2 | G6 (1600) | 1 |
| M26 | A6 (1777) | 1 |
| 22_SMART_AUTO_LOCK_SET | B4(501.596) | 0.6 |
| 23_SMART_AUTO_LOCK_RELEASE | D5(603.270) | 1 |
| T-12 Key Out Alert16 | N/A | 0.9 |
| T13_Tik_16kHz_300ms | G6 (1600) | 0.3 |
| T13_Tok_16kHz_450ms | A6 (1777.778 Hz) | 0.45 |
| T-14 Tik_16kHz_300ms | A4 (444 Hz) | 0.3 |
| T-14 Tok_16kHz_450ms | D4 (296.296 Hz) | 0.45 |
| Alturas_16kHz_750ms_mod | N/A | 0.45 |
| S-16_V2_Volume Increase_16kHz X 16Bit_mod | N/A | 2 |
| DPF Filter Chime_D3_16khz x 16 bit | E4(326.531) | 1 |
|  |  | 33.471 |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-71807: Table – Chime Sound Profile-S237 (System Requirement)
|  |  | Chimes Data |  |
| --- | --- | --- | --- |
| WAV |  | Frequency | Duration (Sec) |
| 1_WELCOME |  | N/A | 4 |
| 3_GOOD BYE |  | N/A | 4 |
| S-15_V3_16kHz X 16Bit mono_mod |  | N/A | 1 |
| 5_RPAS_Type2_St1_St2_cont_upd ate |  | A5(892.840) | 0.15 |
| 6_RPAS_Type2_St1_St2_300ms_u pdate |  | A5(892.840) | 0.15 |
| P4Cont_mono_16_mod |  | E5 (666.67) | 0.1 |
| P4_mono_16_mod |  | E5 (666.67) | 0.15 |
| 9_RPAS_Type4_St1_St2_cont_upd ate |  | F5(708.603) | 0.15 |
| 10_RPAS_Type4_St1_St2_300ms_ update |  | F5(708.603) | 0.15 |
| 11_rec_RSST_nSndID_RPAS_St3 |  | F#/Gb6(1454.545) | 0.071 |
| 12_rec_RSST_nSndID_AEB |  | D4(297.613) | 0.1 |
| 13_LDWS Type2 |  | A#/Bb4(455.531) | 0.5 |
| 14_LDWS Type4 |  | C#/Db8(4464.200) | 0.5 |
| 15_BSD_LCA_RCTA_updated |  | A5(892.850) | 0.5 |
| 16_LDWS Type1 |  | G5(769.690) | 0.5 |
| 17_LDWS Type5 |  | C#/Db5(558.025) | 0.5 |
| 18_LDWS Type3 |  | A#/Bb5(949.830) | 0.5 |
| M15_Mono_16 |  | N/A | 1 |
| M25.2 |  | G6 (1600) | 1 |
| M26 |  | A6 (1777) | 1 |
| 22_SMART_AUTO_LOCK_SET |  | B4(501.596) | 0.6 |
| 23_SMART_AUTO_LOCK_RELEASE |  | D5(603.270) | 1 |
| T-12 Key Out Alert16 |  | N/A | 0.9 |
| T13_Tik_16kHz_300ms |  | G6 (1600) | 0.3 |
| T13_Tok_16kHz_450ms |  | A6 (1777.778 Hz) | 0.45 |
| T-14 Tik_16kHz_300ms |  | A4 (444 Hz) | 0.3 |
| T-14 Tok_16kHz_450ms |  | D4 (296.296 Hz) | 0.45 |
| Alturas_16kHz_750ms_mod |  | N/A | 0.45 |
| S-16_V2_Volume Increase_16kHz X 16Bit_mod |  | N/A | 2 |
| DPF Filter Chime_D3_16khz x 16 bit |  | E4(326.531) | 1 |
|  |  |  | 23.471 |
- Variant: S237
- Stakeholder Requirement State: In Review
- System Requirement State: Draft
- Software Requirement State: Draft
- Primary Discipline: SW
- Requirement Type: Functional

#### MS22029826-52392: Configurable Chimes (Heading)
- Variant: S220, S237, W502
- Stakeholder Requirement State: In Review
- System Requirement State: Draft
- Software Requirement State: Draft
- Primary Discipline: TBD
- Requirement Type: TBD

##### MS22029826-60656 (System Requirement)
The below chimes shall be configurable based on the user setting
Each chime shall have Default WAV( Option 1) that is configured, They shall be modified using the setting chime configuration option:
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60659: Configurable Chimes – Tone (System Requirement)
| Configurabl e Chimes – Tone | Option -1 WAV File 1 | Option 2 -Wav File 2 | Option 3 -Wav File 3 | Optio n 4 | Battery reconne ct value |
| --- | --- | --- | --- | --- | --- |
| Turn Indication | T13_Tok_16kHz_450 ms | T-14 Tok_16kHz_450 ms | Alturas_16kHz_750ms_m od | NA | Option1 |
| Turn Indication | T13_Tik_16kHz_300 ms | T-14 Tik_16kHz_300 ms | Alturas_16kHz_750ms_m od | NA | Option1 |
| Message Notification | M15_Mono_16 | M25.2 | M26 | NA | Option1 |
| Lane Departure | 16_LDWS Type1 | 17_LDWS Type5 | 18_LDWS Type3 | OFF | Option1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60661: WAV files need to be restricted to particular chime group (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60663: WAV files reserved for each configurable chime shall NOT be used anywhere else (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60665: The above chimes can be configured for 3 different levels (High/Medium/Low) based on the user settings (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60668: Configurable Chimes –Volume (System Requirement)
| Configurable Chimes – Volume | High | Mid | Low | Battery reconnect value |
| --- | --- | --- | --- | --- |
| Turn Indication | 90% | 60% | 30% | Mid |
| Message Notification | 90% | 60% | 30% | Mid |
| Lane Departure | 90% | 60% | 30% | Mid |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60670: Audibility of low value shall be decided based on the vehicle trials (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52395: Figure - Chime Patterns (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60672: Pattern 1 (System Requirement)
Pattern 1
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- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60674: Pattern 2 (System Requirement)
Pattern 2
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- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52397: Functional Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60676 (System Requirement)
Every chime shall have the following attributes associated to it:
Priority – Priority of the chime
Type – Type of chime (details below)
Frequency – Frequency of sound output for buzzer
Period – Period of each cycle (incl. On/Off time)
On Time – Duration of valid sound output in 1 cycle
Off Time – Duration of silence in 1 cycle
Cycles – No. of cycles to repeat
- Variant: S237
- Stakeholder Requirement State: In Review
- System Requirement State: Draft
- Software Requirement State: Draft
- Primary Discipline: SW
- Requirement Type: Functional

##### MS22029826-60679 (System Requirement)
Every chime shall have the following attributes associated to it:
Priority – Priority of the chime
Type – Type of chime (details below)
WAV file – WAV file to play for sound output in speaker
Period – Period of each cycle (incl. On/Off time)
Volume – Volume level
Cycles – No. of cycles to repeat
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60681: There shall not be any abnormal sound output during start, stop or loop of any chime. (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60683: Chimes may be required to play in IGN Off or On based on individual requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60685: The chime shall be triggered (not necessarily played) within -100ms- 200ms from input condition active (System Requirement)
The chime shall be triggered (not necessarily played) within 100ms 200ms from input condition active
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60688: Once a chime is played, it shall not be played again even if the condition remains active. It may however be played again of the active condition goes inactive and again to active (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60690: Upto 2 chimes can be played simultaneously, 1 in each channel, provided certain conditions are met. (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60692: Only 1 chime of a particular group shall be played at any given time. In case another chime of the same group is triggered when one is currently being played, the new one shall be queued. (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60694: Every group has a priority associated to it, with 0 being the highest priority and N being the lowest. (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60697: Every chime of a group has a priority associated to it, with 0 being the highest and N being the lowest. (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60699: A chime shall be played independent to its message center warning display (if any) even though the condition to trigger is the same, due to difference in priority arbitration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60701: There shall be an inter-chime delay of 50ms and inter-repetition delay of 50ms (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60703: It shall be possible to enable/disable (configuration, via Diag) every individual chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60053: If a chime is pre-empted by a higher priority chime, it shall be queued. When the higher priority chime is completed, the pre-empted chime shall be played again from start. (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60055 (System Requirement)
Chime behavior for each type shall be as follows:
1. Type A –
a. It shall be played once (1 cycle).
b. It shall be not be repeated.
c. It shall be stopped only when the duration is completed, even though the condition goes inactive prior to it.
d. It shall not be pre-empted(on higher priority chime) until the duration is completed.
2. Type B –
a. It shall be played continuously for multiple cycles of T period each until the condition is active.
b. It shall be repeated.
c. It shall be stopped immediately when the condition goes inactive.
d. It shall be pre-empted(on higher priority chime) provided atleast 1 cycle has been played.
3. Type C –
a. It shall be played N times with each cycle of T period.
b. It shall be repeated.
c. It shall be stopped only when the duration is completed, even though the condition goes inactive prior to it.
d. It shall be pre-empted(on higher priority chime) provided atleast 1 cycle has been played.
4. Type D –
a. It shall be played N times with each cycle of T period.
b. It shall be repeated.
c. It shall be stopped when the condition goes inactive provided the current cycle is allowed to complete.
d. It shall be pre-empted(on higher priority chime) provided atleast 1 cycle has been played.
5
a. It shall be played once (1 cycle).
b. It shall not repeated.
c. It shall be stopped when the condition goes inactive provided the current cycle is allowed to complete.
d. It shall not be pre-empted(on higher priority chime) until the duration is completed.
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44136: Engine High Temperature Chime (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52399: Input Requirements (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60057: IgnMode (Value: Off, On) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60058: LVSD/HVSD Flag (Value: Not Set, Set) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60060: VAR_CODING_ENGINE_MANAGEMENT_SYSTEM (Value: 0-Not Present, 1-Present) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60062: Diag RW HighTemp Chime Enable (Value: 0-Disabled, 1-Enabled) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60064: IC1_100: ENG_COOLANT_TEMP (Value: 0-Normal, 1-High Temp) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60065: Engine Running St (Value: Yes, No) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52401: Output Requirements (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60067: Engine High Temp Chime Functional Logic (Value: Off, On) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Secondary Disciplines: FV
- Software Requirement State: Draft
- Primary Discipline: SW
- Requirement Type: Functional

#### MS22029826-52403: Performance Requirements (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60069: Table - Engine Temperature High Chime Configuration (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-63974: VAR_CODING_ENGINE_MANAGEMENT_SYSTEM (System Requirement)
| VAR_CODING_ENGINE_MANAGEMENT_SYSTEM | Diag RW HighTemp Chime Enable | Engine HighTemp Chime Configuration |
| --- | --- | --- |
| 1 | 1 | 1 |
| 0 | 1 | 0 |
| 1 | 0 | 0 |
| 0 | 0 | 0 |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60070: Table - Engine Temperature High Chime Functional Logic (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-63976: IgnMode (System Requirement)
|  | IgnMode | LVSD/HVSD Flag | HighTemp Chime Config | CAN Missing or Never Received | IC1_100: ENG_COOLANT_TEMP | Engine Running St | Engine High Temp Chime Functional Logic |
| --- | --- | --- | --- | --- | --- | --- | --- |
| 1 | Off | X | X | X | X | X | Off |
| 2 | On | 1 | X | X | X | X | Off |
| 3 | On | 0 | 0 | X | X | X | Off |
| 4 | On | 0 | 1 | 1 | X | X | Off |
| 5 | On | 0 | 1 | 0 | 0 | X | Off |
| 6 | On | 0 | 1 | 0 | 1 | No | Off |
| 7 | On | 0 | 1 | 0 | 1 | Yes (<5 sec) | Off |
| 8 | On | 0 | 1 | 0 | 1 | Yes (>=5 sec) | On |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44138: Low Engine Oil Pressure Chime (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52406: Input Requirements (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60071: IgnMode (Value: On, Off) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60073: LVSD/HVSD Flag (Value: Set, Not Set) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60074: VAR_CODING_ENGINE_MANAGEMENT_SYSTEM (Value: 0-Not Present, 1-Present) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60076: EMS4_20:ENG_OIL_PRESSURE (Value: 0-Normal/Default, 1-Low pressure) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60077: Diag RW LowOilPressure Chime Enable (Value: 0-Disable, 1-Enable) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60079: Engine Running St (Value: Yes, No) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52408: Output Requirements (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60081: Engine Low Oil Pressure Functional Logic (Value: Off, On) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52410: Performance Requirements (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60083: Table- Engine Low Oil Pressure Chime Configuration (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-63978: VAR_CODING_ENGINE_MANAGEMENT_SYSTEM (System Requirement)
| VAR_CODING_ENGINE_MANAGEMENT_SYSTEM | Diag RW LowOilPressure Chime Enable | Engine Low Oil Pressure Chime Configuration |
| --- | --- | --- |
| 0 | X | 0 |
| 1 | 0 | 0 |
| 1 | 1 | 1 |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60084: Table-Engine Low Oil Pressure Chime Functional Logic (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64170: IgnMode (System Requirement)
| IgnMode | LVSD/HVSD Flag | LowOilPressure Chime Configuration | CAN Signal Missing / Never received | EMS4_20:ENG_OIL_PRESSURE | Engine Running St | Engine Low Oil Pressure Chime Functional Logic |
| --- | --- | --- | --- | --- | --- | --- |
| Off | X | X | X | X | X | Off |
| On | Set | X | X | X | X | Off |
| On | Not Set | 0 | X | X | X | Off |
| On | Not Set | 1 | 1 | X | X | Off |
| On | Not Set | 1 | 0 | 0 | X | Off |
| On | Not Set | 1 | 0 | 1 (t <= 7 sec) | X | Off |
| On | Not Set | 1 | 0 | 1 (t > 7 sec) | No | Off |
| On | Not Set | 1 | 0 | 1 (t > 7 sec) | Yes(<7 sec) | Off |
| On | Not Set | 1 | 0 | 1 (t > 7 sec) | Yes (>=7 sec) | On |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44140: Low Brake Fluid (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52413: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60086: IgnMode (Value: On, Off) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60088: LVSD/HVSD Flag (Value: Set, Not Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60090: LowBrakeFluidSt Hw Input (AL) (Value: 0-Active, 1-Not Active) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60092: Engine Running St (Value: Yes, No) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-71822: Engine Running St (Value: Yes, No) (System Requirement)
Engine Running St (Value: Yes, No)
*(Engine running St from VCU10_100: INDC_DRIVE_ENABLE-Refer Artifact 5227913 from gauges Section)
- Variant: S237
- Stakeholder Requirement State: In Review
- System Requirement State: Draft
- Software Requirement State: Draft
- Primary Discipline: TBD
- Requirement Type: TBD

##### MS22029826-60094: Diag RW LowBrakeFluid Chime Enable (Value:0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52415: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60095: LowBrakeFluid Chime Functional Logic (Value: On,Off) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52417: Performance Requirement (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60097: Table-LowBrakeFluid Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64173: Diag RW LowBrakeFluid Chime Enable (System Requirement)
| Diag RW LowBrakeFluid Chime Enable | LowBrakeFluid Chime Configuration |
| --- | --- |
| 0 | 0 |
| 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60099: Table-LowBrakeFluid Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64175: IgnMode (System Requirement)
| IgnMode | LVSD/HVSD Flag | LowBrakeFluid Chime Configuration | LowBrakeFluidSt Hw Input(AL) | Engine Running St | LowBrakeFluid Chime Functional Logic |
| --- | --- | --- | --- | --- | --- |
| Off | X | X | X | X | Off |
| On | Set | X | X | X | Off |
| On | Not Set | 0 | X | X | Off |
| On | Not Set | 1 | 1 | X | Off |
| On | Not Set | 1 | 0 (t<=3 sec) | X | Off |
| On | Not Set | 1 | 0 (t>3 sec) | No | Off |
| On | Not Set | 1 | 0 (t>3 sec) | Yes(<5 sec) | Off |
| On | Not Set | 1 | 0 (t>3 sec) | Yes(>=5 sec) | On |
*(Engine running St from VCU10_100: INDC_DRIVE_ENABLE-Refer Artifact 5227913 from gauges Section) For S237 variant alone.
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-71824: Ready to Drive Chime (Heading)
- Variant: S237
- Stakeholder Requirement State: In Review
- System Requirement State: Draft
- Software Requirement State: Draft
- Primary Discipline: TBD
- Requirement Type: TBD

#### MS22029826-71825: Input Requirements (Heading)
- Variant: S237
- Stakeholder Requirement State: In Review
- System Requirement State: Draft
- Software Requirement State: Draft
- Primary Discipline: TBD
- Requirement Type: TBD

##### MS22029826-71828: IgnMode (Value: On, Off) (System Requirement)
- Variant: S237
- Stakeholder Requirement State: In Review
- System Requirement State: Draft
- Software Requirement State: Draft
- Primary Discipline: TBD
- Requirement Type: TBD

##### MS22029826-71831: LVSD/HVSD Flag (Value: Not Set, Set) (System Requirement)
- Variant: S237
- Stakeholder Requirement State: In Review
- System Requirement State: Draft
- Software Requirement State: Draft
- Primary Discipline: TBD
- Requirement Type: TBD

##### MS22029826-71832: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-71833: VCU10_100(0X30A):INDC_DRIVE_ENABLE (System Requirement)
VCU10_100(0X30A):INDC_DRIVE_ENABLE (0X0 - Default value/Vehicle Not Enabled, 0x1-
Drive Enabled/Activate Vehicle ,0x2~0x3-Reserved)
- Variant: S237
- Stakeholder Requirement State: In Review
- System Requirement State: Draft
- Software Requirement State: Draft
- Primary Discipline: TBD
- Requirement Type: TBD

##### MS22029826-71834: Diag RW Ready to Drive Chime Enable (Value: 0-Disable, 1-Enable) (System Requirement)
- Variant: S237
- Stakeholder Requirement State: In Review
- System Requirement State: Draft
- Software Requirement State: Draft
- Primary Discipline: TBD
- Requirement Type: TBD

#### MS22029826-71826: Output Requirements (Heading)
- Variant: S237
- Stakeholder Requirement State: In Review
- System Requirement State: Draft
- Software Requirement State: Draft
- Primary Discipline: TBD
- Requirement Type: TBD

##### MS22029826-71829: Ready to Drive Chime Functional Logic (Value: Off, On) (System Requirement)
- Variant: S237
- Stakeholder Requirement State: In Review
- System Requirement State: Draft
- Software Requirement State: Draft
- Primary Discipline: TBD
- Requirement Type: TBD

#### MS22029826-71827: Performance Requirements (Heading)
- Variant: S237
- Stakeholder Requirement State: In Review
- System Requirement State: Draft
- Software Requirement State: Draft
- Primary Discipline: TBD
- Requirement Type: TBD

##### MS22029826-71830 (System Requirement)
Table - Ready to Drive Chime Functional Logic
| Ign Mode | LVSD/HVSD Flag | VAR_CODING_VEHICLE_CONTROL_UNIT | Diag RW Ready to Drive Chime Enable | CAN Signal Missing or Never Received | VCU10_100(0X30A): INDC_DRIVE_ENABLE | Ready to Drive Chime Functional Logic |
| --- | --- | --- | --- | --- | --- | --- |
| Off | X | X | X | X | X | Off |
| On | Set | X | X | X | X | Off |
| On | Not Set | 0 | X | X | X | Off |
| On | Not Set | 1 | 0 | X | X | Off |
| On | Not Set | 1 | 1 | 1 | X | Off |
| On | Not Set | 1 | 1 | 0 | !=0x1 | Off |
| On | Not Set | 1 | 1 | 0 | =0x1 | On |
- Variant: S237
- Stakeholder Requirement State: In Review
- System Requirement State: Draft
- Software Requirement State: Draft
- Primary Discipline: TBD
- Requirement Type: TBD

### MS22029826-71835: Limp Home Mode Chime (Heading)
- Variant: S237
- Stakeholder Requirement State: In Review
- System Requirement State: Draft
- Software Requirement State: Draft
- Primary Discipline: TBD
- Requirement Type: TBD

#### MS22029826-71836: Input Requirements (Heading)
- Variant: S237
- Stakeholder Requirement State: In Review
- System Requirement State: Draft
- Software Requirement State: Draft
- Primary Discipline: TBD
- Requirement Type: TBD

##### MS22029826-71840: IgnMode (Value: On, Off) (System Requirement)
- Variant: S237
- Stakeholder Requirement State: In Review
- System Requirement State: Draft
- Software Requirement State: Draft
- Primary Discipline: TBD
- Requirement Type: TBD

##### MS22029826-71842: LVSD/HVSD Flag (Value: Not Set, Set) (System Requirement)
- Variant: S237
- Stakeholder Requirement State: In Review
- System Requirement State: Draft
- Software Requirement State: Draft
- Primary Discipline: TBD
- Requirement Type: TBD

##### MS22029826-71843: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-71844: VCU3_10(0X118): STS_VEHICLE_LIMP_HOME (0X0 -Inactive/Default value, 0x1 - Active) (System Requirement)
- Variant: S237
- Stakeholder Requirement State: In Review
- System Requirement State: Draft
- Software Requirement State: Draft
- Primary Discipline: TBD
- Requirement Type: TBD

##### MS22029826-71845: Diag RW Limp Home Chime Enable (Value: 0-Disable, 1-Enable) (System Requirement)
- Variant: S237
- Stakeholder Requirement State: In Review
- System Requirement State: Draft
- Software Requirement State: Draft
- Primary Discipline: TBD
- Requirement Type: TBD

#### MS22029826-71837: Output Requirements (Heading)
- Variant: S237
- Stakeholder Requirement State: In Review
- System Requirement State: Draft
- Software Requirement State: Draft
- Primary Discipline: TBD
- Requirement Type: TBD

##### MS22029826-71839: Limp Home Chime Functional Logic (Value: Off, On) (System Requirement)
- Variant: S237
- Stakeholder Requirement State: In Review
- System Requirement State: Draft
- Software Requirement State: Draft
- Primary Discipline: TBD
- Requirement Type: TBD

#### MS22029826-71838: Performance Requirements (Heading)
- Variant: S237
- Stakeholder Requirement State: In Review
- System Requirement State: Draft
- Software Requirement State: Draft
- Primary Discipline: TBD
- Requirement Type: TBD

##### MS22029826-71841: Table - Limp Home Chime Functional Logic (System Requirement)
Table - Limp Home Chime Functional Logic
| Ign Mode | LVSD/HVSD Flag | VAR_CODING_VEHICLE_CONTROL_UNIT | Diag RW Limp Home Chime Enable | CAN Signal Missing or Never Received | VCU3_10(0X118): STS_VEHICLE_LIMP_HOME | Limp Home Chime Functional Logic |
| --- | --- | --- | --- | --- | --- | --- |
| Off | X | X | X | X | X | Off |
| On | Set | X | X | X | X | Off |
| On | Not Set | 0 | X | X | X | Off |
| On | Not Set | 1 | 0 | X | X | Off |
| On | Not Set | 1 | 1 | 1 | X | Off |
| On | Not Set | 1 | 1 | 0 | 0x0 | Off |
| On | Not Set | 1 | 1 | 0 | 0x1 | On |
- Variant: S237
- Stakeholder Requirement State: In Review
- System Requirement State: Draft
- Software Requirement State: Draft
- Primary Discipline: TBD
- Requirement Type: TBD

### MS22029826-44142: Turn Signal Left/Right Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52419: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60101: IgnMode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60103: LVSD/HVSD Flag (Value: Not Set, Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60106: VAR_CODING_MAHINDRA_BODY_FUNCTION_MODULE (Value: 0-Not Present, 1-Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60108: FEATURE_CODE_TURN_INDC_TT_TYPE(Value: 0-CAN, 1-HW) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60110: MBFM1_100: INDC_TURN_FLSHR(Value: 0-Lamp Off/Default Value, 1-Left Turn, 2-Right Turn, 3 -Hazard) (System Requirement)
MBFM1_100: INDC_TURN_FLSHR (Value: 0-Lamp Off/Default Value, 1-Left Turn, 2-Right Turn, 3 -Hazard)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60111: Diag RW TurnSignal L/R IGN ON Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60113: Diag RW TurnSignal L/R IGN OFF Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60115: TurnLeftTTSt Hw Input(Value : 0-OFF,1 -ON) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60117: TurnRightTTSt Hw Input(Value : 0-OFF,1 -ON) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52421: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60118: TurnSignal L/R IGN ON Chime Functional Logic (Value: Tick, Tock, No chime) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60121: TurnSignal L/R IGN OFF Chime Functional Logic (Value: Tick, Tock, No chime) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52423: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60122: Table-TurnSignal L/R IGN ON Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64176: VAR_CODING_MAHINDRA_BODY_FUNCTION_MODULE (System Requirement)
| VAR_CODING_MAHINDRA_BODY_FUNCTION_MODULE | FEATURE_CODE_TURN_INDC_TT_TYPE | Diag RW TurnSignal L/R IGN ON Chime Enable | TurnSignal L/R IGN ON Chime Configuration |
| --- | --- | --- | --- |
| X | X | 0 | 0 |
| 0 | 0 | X | 0 |
| 1 | 0 | 1 | CAN |
| X | 1 | 1 | HW |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60124: Table-TurnSignal L/R IGN OFF Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64178: VAR_CODING_MAHINDRA_BODY_FUNCTION_MODULE (System Requirement)
| VAR_CODING_MAHINDRA_BODY_FUNCTION_MODULE | FEATURE_CODE_TURN_INDC_TT_TYPE | Diag RW TurnSignal L/R IGN OFF Chime Enable | TurnSignal L/R IGN OFF Chime Configuration |
| --- | --- | --- | --- |
| X | X | 0 | 0 |
| 0 | 0 | X | 0 |
| 1 | 0 | 1 | CAN |
| X | 1 | 1 | HW |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60126: Table-TurnSignal L/R IGN ON Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64180: IgnMode (System Requirement)
|  | IgnMode | LVSD/HVSD Flag | TurnSignal L/R IGN ON Chime Configuration | TurnLeft/RightTT St Hw Input | CAN Signal Missing / Never Received | MBFM1_100: INDC_TURN_FLSHR | TurnSignal L/R IGN ON Chime Functional logic |
| --- | --- | --- | --- | --- | --- | --- | --- |
| 1 | Off | X | X | X | X | X | No Chime |
| 2 | On | Set | X | X | X | X | No Chime |
| 3 | On | Not Set | 0 | X | X | X | No Chime |
| 4 | On | Not set | HW | 0->1 | X | X | Tick |
| 5 | On | Not set | HW | 1->0 | X | X | Tock |
| 6 | On | Not set | HW | Other | X | X | No Chime |
| 7 | On | Not Set | CAN | X | 1 | X | No Chime |
| 8 | On | Not Set | CAN | X | 0 | 0x0->0x1, 0x0->0x2, 0x0->0x3 | Tick |
| 9 | On | Not Set | CAN | X | 0 | 0x1->0x0, 0x2->0x0, 0x3->0x0 | Tock |
| 10 | On | Not Set | CAN | X | 0 | Other | No chime |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60128: Table-Turn Signal L/R IGN OFF Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64181: IgnMode (System Requirement)
|  | IgnMode | LVSD/HVSD Flag | TurnSignal L/R IGN OFF Chime Configuration | TurnLeft/RightTT St Hw Input | CAN Signal Missing / Never Received | MBFM1_100: INDC_TURN_FLSHR | TurnSignal L/R IGN OFF Chime Functional logic |
| --- | --- | --- | --- | --- | --- | --- | --- |
| 1 | On | X | X | X | X | X | No Chime |
| 2 | Off | Set | X | X | X | X | No Chime |
| 3 | Off | Not Set | 0 | X | X | X | No Chime |
| 4 | Off | Not set | HW | 0->1 | X | X | Tick |
| 5 | Off | Not set | HW | 1->0 | X | X | Tock |
| 6 | Off | Not set | HW | Other | X | X | No Chime |
| 7 | Off | Not Set | CAN | X | 1 | X | No Chime |
| 8 | Off | Not Set | CAN | X | 0 | 0x0->0x3 | Tick |
| 9 | Off | Not Set | CAN | X | 0 | 0x3->0x0 | Tock |
| 10 | Off | Not Set | CAN | X | 0 | Other | No chime |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44144: Reverse Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52424: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60129: IgnMode (Value: On, Off) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60131: LVSD/HVSD Flag (Value: Set, Not Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60133: VAR_CODING_ENGINE_MANAGEMENT_SYSTEM (Value: 0-Not Present, 1-Present) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-71847: VAR_CODING_VEHICLE_CONTROL_UNIT(Value: 0-Not Present, 1-Present) (Value: 0-Not Present, 1-Present) (System Requirement)
- Variant: S237
- Stakeholder Requirement State: In Review
- System Requirement State: Draft
- Software Requirement State: Draft
- Primary Discipline: SW
- Requirement Type: Functional

##### MS22029826-60135: VAR_CODING_TRANSMISSION_CONTROL_UNIT(Value :0-Not Present, 1-Present) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60136: VAR_CODING_AUTOMATED_MANUAL_TRANSMISSION (Value: 0-Not Present, 1-Present) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60138: EMS1_10:CURRENT_GEAR_MT (Value: 0-Neutral, 1-1st gear, 2-2nd gear, 3-3rd gear, 4-4th gear,5-5th gear, 6-6th gear, 7-Reverse, 8~0xE-Reserved,0xF-Invalid) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60140: TCU6_20: TGS_LEVER (Value: Value: 0~5-Reserved,0x6-Drive, 0x7-Neutral 0x8-Reverse 0x7-Neutral 0x8-Reverse, 0x9-Park, 0x9-Park, 0xA-Trip+,0xB-Trip- 0xC-M-forward drive 0xD-Default Value ,0xE-Middle position,0xF-Signal Invalid) (System Requirement)
TCU6_20: TGS_LEVER (Value: Value: 0~5-Reserved,0x6-Drive, 0x7-Neutral 0x8-Reverse 0x7-Neutral 0x8-Reverse, 0x9-Park, 0x9-Park, 0xA-Trip+,0xB-Trip- 0xC-M-forward drive 0xD -Default Value ,0xE-Middle position,0xF-Signal Invalid)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60395: Diag RW Reverse Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-71848: AMT5_20: GEAR_ACTUAL_AMT (Value: 0x0-Neutral, 0x1-1st gear, 0x2-2nd gear, 0x3-3rd gear, 0x4-4th gear, 0x5-5th gear,0x6~0x9-Reserved, 0xB~0XE-Reserved, 0xA-Reverse,, 0xF-Invalid) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-71849 (System Requirement)
VCU10_100: GEAR_ACTUAL_VCU (Values: 0x0=neutral/default, 0x1=Forward mode,
0x2=Reverse Mode, 0x3=Low mode, 0x4=Reserved, 0x5= Park Mode, 0x6= Reserved,
0x7= Signal invalid)
- Variant: S237
- Stakeholder Requirement State: In Review
- System Requirement State: Draft
- Software Requirement State: Draft
- Primary Discipline: TBD
- Requirement Type: TBD

#### MS22029826-52426: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60397: Reverse Chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52427: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60399: Table-Reverse Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64183: W502 & S220 (System Requirement)
| VAR_CODING_AUTOMATED_MANUAL_TRANSMISSION | VAR_CODING_TRANSMISSION_CONTROL_UNIT | VAR_CODING_ENGINE_MANAGEMENT_SYSTEM | Diag RW Reverse Chime Enable | Reverse Chime Configuration |
| --- | --- | --- | --- | --- |
| X | X | X | 0 | 0 |
| X | 0 | 0 | 1 | 0 |
| 1 | 1 | X | 1 | 0 (log DTC) |
| 0 | 0 | 1 | 1 | MT |
| 1 | 0 | X | 1 | AMT |
| 0 | 1 | X | 1 | AT |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-71851: S237 (System Requirement)
| VAR_CODING_VEHICLE_CONTROL_UNIT | Diag RW Reverse Chime Enable | Reverse Chime Configuration |
| --- | --- | --- |
| 0 | X | 0 |
| 1 | 0 | 0 |
| 1 | 1 | 1 |
- Stakeholder Requirement State: In Review
- System Requirement State: Draft
- Software Requirement State: Draft
- Primary Discipline: TBD
- Requirement Type: TBD

##### MS22029826-60401: Table-Reverse Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64185: For MT Variant: (System Requirement)
For MT Variant:
| IgnMode | LVSD/HVSD Flag | Reverse Chime Configuration | CAN Signal Missing / Never received | EMS1_10:CURRENT_GEAR_MT | Reverse Chime Functional Logic |
| --- | --- | --- | --- | --- | --- |
| Off | X | X | X | X | Off |
| On | Set | X | X | X | Off |
| On | Not Set | 0 | X | X | Off |
| On | Not Set | 1 | 1 | X | Off |
| On | Not Set | 1 | 0 | 0x7( Reverse) | On |
| On | Not Set | 1 | 0 | != 0X7 | Off |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64187: For AT Variant: (System Requirement)
For AT Variant:
| IgnMode | LVSD/HVSD Flag | Reverse Chime Configuration | CAN Signal Missing / Never received | TCU6_20: TGS_LEVER | Reverse Chime Functional Logic |
| --- | --- | --- | --- | --- | --- |
| Off | X | X | X | X | Off |
| On | Set | X | X | X | Off |
| On | Not Set | 0 | X | X | Off |
| On | Not Set | 1 | 1 | X | Off |
| On | Not Set | 1 | 0 | 0x8 (Reverse) | On |
| On | Not Set | 1 | 0 | != 0x8 | Off |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-71850: For AMT Variant (System Requirement)
For AMT Variant
| IgnMode | LVSD/HVSD Flag | Reverse Chime Configuration | CAN Signal Missing / Never received | AMT5_20: GEAR_ACTUAL_AMT | Reverse Chime Functional Logic |
| --- | --- | --- | --- | --- | --- |
| Off | X | X | X | X | Off |
| On | Set | X | X | X | Off |
| On | Not Set | 0 | X | X | Off |
| On | Not Set | 1 | 1 | X | Off |
| On | Not Set | 1 | 0 | 0xA (Reverse) | On |
| On | Not Set | 1 | 0 | != 0xA | Off |
- Variant: S220, S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-71852: For S237 (System Requirement)
| IgnMo de | LVSD/HVSD Flag | Reverse Chime Configuratio n | CAN Signal Missing /Never received | VCU10_100: GEAR_ACTUAL_VCU | Reverse Chime Functional Logic |
| --- | --- | --- | --- | --- | --- |
| Off | X | X | X | X | Off |
| On | Set | X | X | X | Off |
| On | Not Set | 0 | X | X | Off |
| On | Not Set | 1 | 1 | X | Off |
| On | Not Set | 1 | 0 | 0x2 | On |
| On | Not Set | 1 | 0 | !=0x2 | Off |
- Variant: S237
- Stakeholder Requirement State: In Review
- System Requirement State: Draft
- Software Requirement State: Draft
- Primary Discipline: TBD
- Requirement Type: TBD

### MS22029826-44146: Door Open Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52429: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60403: IgnMode (Value: On, Off) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60405: LVSD/HVSD Flag (Value: Not Set, Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60407: VAR_CODING_MAHINDRA_BODY_FUNCTION_MODULE (Value: 0-Not Present, 1-Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60409: Diag RW DoorOpen Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60412: MBFM1_100:STS_DOOR:Bit0 -Tailgate (Value:0-Close, 1-Open) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60414: MBFM1_100:STS_DOOR: Bit1 -Hood (Value:0-Close, 1-Open) (System Requirement)
MBFM1_100:STS_DOOR:Bit1 -Hood (Value:0-Close, 1-Open)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60416: MBFM1_100:STS_DOOR:Bit2 - Co-driver -FL (Value:0-Close, 1-Open) (System Requirement)
MBFM1_100:STS_DOOR: Bit2 - Co-driver -FL (Value:0-Close, 1-Open)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60418: MBFM1_100:STS_DOOR: Bit3 - Driver -FR (Value:0-Close, 1-Open) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60421: MBFM1_100:STS_DOOR:Bit4 - Rear Left (Value:0-Close, 1-Open) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60423: MBFM1_100:STS_DOOR:Bit5 - Rear Right (Value:0-Close, 1-Open) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60424: Vehicle Moving St (Value: Yes, No) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-72021: FEATURE_CODE_DOOR_SEL (0-2 Door, 1-4 Door)) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52431: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60426: DoorOpen Chime Functional Logic (Value: On, Off) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52433: Performance Requirement (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60427: Table-DoorOpen Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64189: VAR_CODING_MAHINDRA_BODY_FUNCTION _SYSTEM (System Requirement)
|  | VAR_CODING_MAHINDRA_BODY_FUNCTION _SYSTEM | Diag RW DoorOpen Chime Configuration | DoorOpen Chime Configuration |
| --- | --- | --- | --- |
| 1 | 0 | X | 0 |
| 2 | 1 | 0 | 0 |
| 3 | 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60430: Table-Door Status (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64191: MBFM1_100: STS_DOOR (System Requirement)
FEATURE_CODE_DOOR_SEL=0
|  | MBFM1_100:STS_DOOR |  |  |  |  |  | Door Status |
| --- | --- | --- | --- | --- | --- | --- | --- |
|  | RR Door | RL Door | FR Door | FL Door | Hood | Tailgate | Door Status |
|  | Bit=5 | Bit=4 | Bit=3 | Bit=2 | Bit=1 | Bit=0 | Door Status |
| 1 | 0 | 0 | 0 | 0 | 0 | 0 | Close |
| 2 | X | X | X | 1 | X | X | Open |
| 3 | X | X | 1 | X | X | X | Open |
| 4 | X | X | X | X | 1 | X | Open |
| 5 | X | X | X | X | X | 1 | Open |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-72028: MBFM1_100: STS_DOOR (System Requirement)
FEATURE_CODE_DOOR_SEL=1
|  | MBFM1_100:STS_DOOR |  |  |  |  |  | Door Status |
| --- | --- | --- | --- | --- | --- | --- | --- |
|  | RR Door | RL Door | FR Door | FL Door | Hood | Tailgate | Door Status |
|  | Bit=5 | Bit=4 | Bit=3 | Bit=2 | Bit=1 | Bit=0 | Door Status |
| 1 | 0 | 0 | 0 | 0 | 0 | 0 | Close |
| 2 | X | X | X | X | X | 1 | Open |
| 3 | X | X | X | X | 1 | X | Open |
| 4 | X | X | X | 1 | X | X | Open |
| 5 | X | X | 1 | X | X | X | Open |
| 6 | X | 1 | X | X | X | X | Open |
| 7 | 1 | X | X | X | X | X | Open |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-72192: MBFM1_100: STS_DOOR (System Requirement)
| MBFM1_100: STS_DOOR |  |  |  |  |  | Door Status |
| --- | --- | --- | --- | --- | --- | --- |
| Bit5: Rear Right | Bit4: Rear Left | Bit3: Driver | Bit2: Co-Driver | Bit1: Hood | Bit0: Tail Gate | Door Status |
| 0 | 0 | 0 | 0 | 0 | 0 | Close |
| 1 | X | X | X | X | X | Open |
| X | 1 | X | X | X | X | Open |
| X | X | 1 | X | X | X | Open |
| X | X | X | 1 | X | X | Open |
| X | X | X | X | 1 | X | Open |
| X | X | X | X | X | 1 | Open |
- Variant: S237
- Stakeholder Requirement State: In Review
- System Requirement State: Draft
- Software Requirement State: Draft
- Primary Discipline: SW
- Requirement Type: Functional

##### MS22029826-60432: Table-DoorOpen Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64193: IgnMode (System Requirement)
|  | IgnMode | LVSD/HVSD Flag | DoorOpen Chime Configuration | CAN Signal Missing/ Never Received | Door Status | Vehicle Moving St | DoorOpen Chime Functional Logic |
| --- | --- | --- | --- | --- | --- | --- | --- |
|  | Off | X | X | X | X | X | Off |
| 1 | On | Set | X | X | X | X | Off |
| 2 | On | X | 0 | X | X | X | Off |
| 3 | On | Not Set | 1 | 1 | X | X | Off |
| 4 | On | Not Set | 1 | 0 | Close | X | Off |
| 5 | On | Not Set | 1 | 0 | Open | No | Off |
| 6 | On | Not Set | 1 | 0 | Open | Yes | On |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44148: PAS Chime (Heading)
- Variant: S220, S237, W502
- Stakeholder Requirement State: In Review
- System Requirement State: Draft
- Software Requirement State: Draft
- Primary Discipline: TBD
- Requirement Type: TBD

#### MS22029826-52435: Input Requirements (Heading)
- Variant: S220, S237, W502
- Stakeholder Requirement State: In Review
- System Requirement State: Draft
- Software Requirement State: Draft
- Primary Discipline: TBD
- Requirement Type: TBD

##### MS22029826-60434: IgnMode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60436: LVSD/HVSD Flag (Value: Not Set, Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60438: RPAS Activation St (Refer PAS Alert) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60440: FPAS Activation St (Refer PAS Alert) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60442: Message (System Requirement)
| Message ID | Message name | Signal name | Range | Value Description |
| --- | --- | --- | --- | --- |
| 0x326 | MBFM_PAS1_50 | RPAS_ERROR | 0 to 0x10 | 0x0 - No Error 0x1 - RL Sensor Fault 0x2 - RLC Sensor Fault 0x4 - RRC Sensor Fault 0x8 - RR Sensor Fault 0x10 - ECU Fault |
| 0x326 | MBFM_PAS1_50 | BAR_ZONE_RL | 0x0 to 0xF | Bar Zone On/Off for RL sensor |
| 0x326 | MBFM_PAS1_50 | BAR_ZONE_RLC | 0x0 to 0xF | Bar Zone On/Off for RLC sensor |
| 0x326 | MBFM_PAS1_50 | BAR_ZONE_RRC | 0x0 to 0xF | Bar Zone On/Off for RRC sensor |
| 0x326 | MBFM_PAS1_50 | BAR_ZONE_RR | 0x0 to 0xF | Bar Zone On/Off for RR sensor |
| 0x326 | MBFM_PAS1_50 | FPAS_ERROR | 0 to 0x10 | 0x0 - No Error 0x1 - FL Sensor Fault 0x2 - FLC Sensor Fault 0x4 - FRC Sensor Fault 0x8 - FR Sensor Fault 0x10 - ECU Fault |
| 0x326 | MBFM_PAS1_50 | BAR_ZONE_FL | 0x0 to 0xF | Bar Zone On/Off for FL sensor |
| 0x326 | MBFM_PAS1_50 | BAR_ZONE_FLC | 0x0 to 0xF | Bar Zone On/Off for FLC sensor |
| 0x326 | MBFM_PAS1_50 | BAR_ZONE_FRC | 0x0 to 0xF | Bar Zone On/Off for FRC sensor |
| 0x326 | MBFM_PAS1_50 | BAR_ZONE_FR | 0x0 to 0xF | Bar Zone On/Off for FR sensor |
|  |  | FPAS_SWT_STS | 0x0 | 0x0 – Off/Default 0x1 - On |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60444: Trailer Status:MBFM1_100 -STS_TRAILER ( Value: 0x0x -Trailer not connected / Default Value, 0x1 -Trailer Connected) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60447: Diag RW RPAS Sector Zone Calibration (Value -0x0 to 0xF) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60449: Diag RW FPAS Sector Zone Calibration (Value -0x0 to 0xF) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60451: Diag RW RPAS Fail Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60454: Diag RW PAS Status Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60456: Diag RW RPAS Self Check Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60458: Diag RW RPAS Self Check time (configurable –Default- 500ms) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60461: Diag RW RPAS Error Check time (configurable –Default- 3sec) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52437: OutputRequirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60464: RPAS Fail Chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60466: RPAS Self Check Chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60468: RPAS Status Chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60470: FPAS Status Chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52439: Performance Requirements (Heading)
- Variant: S220, S237, W502
- Stakeholder Requirement State: In Review
- System Requirement State: Draft
- Software Requirement State: Draft
- Primary Discipline: TBD
- Requirement Type: TBD

##### MS22029826-60472: Table-RPAS Fail Chime Configuration (Heading)
- Variant: S220, S237, W502
- Stakeholder Requirement State: In Review
- System Requirement State: Draft
- Software Requirement State: Draft
- Primary Discipline: TBD
- Requirement Type: TBD

###### MS22029826-64195: VAR_CODING_MAHINDRA_BODY_FUNCTION_MODULE (System Requirement)
| VAR_CODING_MAHINDRA_BODY_FUNCTION_MODULE | FEATURE_CODE_RPAS_IND | Diag RW RPAS Fail Chime Enable | RPAS Fail Chime Configuration |
| --- | --- | --- | --- |
| 0 | X | X | 0 |
| 1 | 0 | X | 0 |
| 1 | 1 | 0 | 0 |
| 1 | 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60474: Table-RPAS Fail Chime Functional Logic (Heading)
- Variant: S220, S237, W502
- Stakeholder Requirement State: In Review
- System Requirement State: Draft
- Software Requirement State: Draft
- Primary Discipline: TBD
- Requirement Type: TBD

###### MS22029826-64197: Ign Mode (System Requirement)
| Ign Mode | LVSD/HVSD Flag | RPAS Fail Chime Configuration | RPAS Activation St | MBFM1_100-STS_TRAILER | CAN Signal Missing/Never Received | MBFM_PAS1_50: RPAS_ERROR | RPAS Fail Chime Functional Logic |
| --- | --- | --- | --- | --- | --- | --- | --- |
| Off | X | X | X | X | X | X | Off |
| On | Set | X | X | X | X | X | Off |
| On | Not Set | 0 | X | X | X | X | Off |
| On | Not Set | 1 | False | X | X | X | Off |
| On | Not Set | 1 | True | 1 | 1 | X | Off |
| On | Not Set | 1 | True | 0 | 1 | X | Error-Tone On For t= #Diag RW RPAS Error Check time |
| On | Not Set | 1 | True | X | 0 | 0x0 | Off |
| On | Not Set | 1 | True | 1 | 0 | !=0x0 | Off |
| On | Not Set | 1 | True | 0 | 0 | !=0x0 | Error-Tone On For t= #Diag RW RPAS Error Check time |
# Diag RW RPAS Error Check time Parameter not applicable for smart core
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60476: Ign Mode (Heading)
| Ign Mode | LVSD/HVSD Flag | RPAS Fail Chime Configuration | RPAS Activation St | MBFM1_100-STS_TRAILER | CAN Signal Missing/Never Received | MBFM_PAS1_50:RPAS_ERROR | RPAS Fail Chime Functional Logic |
| --- | --- | --- | --- | --- | --- | --- | --- |
| Off | X | X | X | X | X | X | Off |
| On | Set | X | X | X | X | X | Off |
| On | Not Set | 0 | X | X | X | X | Off |
| On | Not Set | 1 | FALSE | X | X | X | Off |
| On | Not Set | 1 | TRUE | 1 | 1 | X | Off |
| On | Not Set | 1 | TRUE | 0 | 1 | X | Error-Tone On For t= ^#Diag RW RPAS Error Check time |
| On | Not Set | 1 | TRUE | X | 0 | 0x0 | Off |
| On | Not Set | 1 | TRUE | 1 | 0 | !=0x0 | Off |
| On | Not Set | 1 | TRUE | 0 | 0 | !=0x0 | Error-Tone On For t= ^#Diag RW RPAS Error Check time |
# Diag RW RPAS Error Check time Parameter not applicable for smart core
- Variant: S220, S237, W502
- Stakeholder Requirement State: In Review
- System Requirement State: Draft
- Software Requirement State: Draft
- Primary Discipline: TBD
- Requirement Type: TBD

##### MS22029826-60478: Table-PAS Status Chime Configuration (Heading)
- Variant: S220, S237, W502
- Stakeholder Requirement State: In Review
- System Requirement State: Draft
- Software Requirement State: Draft
- Primary Discipline: TBD
- Requirement Type: TBD

###### MS22029826-64198: VAR_CODING_MAHINDRA_BODY_FUNCTION_MODULE (System Requirement)
| VAR_CODING_MAHINDRA_BODY_FUNCTION_MODULE | Diag RW PAS Status Chime Enable | FEATURE_CODE_RPAS_IND | FEATURE_CODE_FPAS_IND | PAS Status Chime Configuration |
| --- | --- | --- | --- | --- |
| 0 | X | X | X | 0 |
| 1 | 0 | X | X | 0 |
| 1 | 1 | 0 | 0 | 0 |
| 1 | 1 | 1 | 0 | RPAS Only |
| 1 | 1 | 0 | 1 | FPAS Only |
| 1 | 1 | 1 | 1 | RPAS and FPAS |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60480: Table-RPAS Status Chime Precondition (Heading)
- Variant: S220, S237, W502
- Stakeholder Requirement State: In Review
- System Requirement State: Draft
- Software Requirement State: Draft
- Primary Discipline: TBD
- Requirement Type: TBD

###### MS22029826-64200: Ign Mode (System Requirement)
| Ign Mode | LVSD/HVSD Flag | MBFM1_100 STS_TRAILER | CAN Signal Missing/ Never Received | MBFM_PAS1_50: RPAS_ERROR | RPAS chime Precondition Logic |
| --- | --- | --- | --- | --- | --- |
| Off | X | X | X | X | False |
| On | Set | X | X | X | False |
| On | Not Set | 1 | X | X | False |
| On | Not Set | 0 | 1 | X | False |
| On | Not Set | 0 | 0 | !=0x0 | False |
| On | Not Set | 0 | 0 | =0x0 | True |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60482: Table- RPAS status Chime -3 zone (Heading)
- Variant: S220, S237, W502
- Stakeholder Requirement State: In Review
- System Requirement State: Draft
- Software Requirement State: Draft
- Primary Discipline: TBD
- Requirement Type: TBD

###### MS22029826-64203: Diag RW PAS Status Chime Enable (System Requirement)
| Diag RW PAS Status Chime Enable | RPAS Activation St | RPAS chime Precondition Logic | MBFM_PAS1_50: BAR_ZONE_XX | RPAS Status Chime Functional Logic |
| --- | --- | --- | --- | --- |
| 0 | X | X | X | Off |
| FPAS Only | X | X | X | Off |
| RPAS Only | False | X | X | Off |
| RPAS Only | True | False | X | Off |
| RPAS Only | True | True | 0x1 | Level1 On |
| RPAS Only | True | True | 0x2 | Level2 On |
| RPAS Only | True | True | 0x3 | Level3 On |
| RPAS Only | True | True | 0x0, 0x4 to 0xF | Off |
| RPAS and FPAS | False | X | X | Off |
| RPAS and FPAS | True | False | X | Off |
| RPAS and FPAS | True | True | 0x1 | Level1 On |
| RPAS and FPAS | True | True | 0x2 | Level2 On |
| RPAS and FPAS | True | True | 0x3 | Level3 On |
| RPAS and FPAS | True | True | 0x0, 0x4 to 0xF | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64205 (System Requirement)
The above table is applicable for 3 zone APPLICABLE scenario:
CASE 1: Diag RW RPAS Sector Zone Calibration (value :0x1)
XX Represents: RLC, RRC
CASE 3: Diag RW RPAS Sector Zone Calibration (value :0x3)
XX Represents: RL, RR,RLC
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60484: Table- RPAS Status Chime -4 Zone (Heading)
- Variant: S220, S237, W502
- Stakeholder Requirement State: In Review
- System Requirement State: Draft
- Software Requirement State: Draft
- Primary Discipline: TBD
- Requirement Type: TBD

###### MS22029826-64207: Diag RW PAS Status Chime Enable (System Requirement)
| Diag RW PAS Status Chime Enable | RPAS Activation St | RPAS chime Precondition Logic | MBFM_PAS1_50: BAR_ZONE_XX | RPAS Status Chime Functional Logic |
| --- | --- | --- | --- | --- |
| 0 | X | X | X | Off |
| FPAS Only | X | X | X | Off |
| RPAS Only | False | X | X | Off |
| RPAS Only | True | False | X | Off |
| RPAS Only | True | True | 0x1 | Level1 On |
| RPAS Only | True | True | 0x2 | Level2 On |
| RPAS Only | True | True | 0x3 | Level3 On |
| RPAS Only | True | True | 0x4 | Level4 On |
| RPAS Only | True | True | 0x0, 0x5 to 0xF | Off |
| RPAS and FPAS | False | X | X | Off |
| RPAS and FPAS | True | False | X | Off |
| RPAS and FPAS | True | True | 0x1 | Level1 On |
| RPAS and FPAS | True | True | 0x2 | Level2 On |
| RPAS and FPAS | True | True | 0x3 | Level3 On |
| RPAS and FPAS | True | True | 0x4 | Level4 On |
| RPAS and FPAS | True | True | 0x0, 0x5 to 0xF | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64209 (System Requirement)
The above table is applicable for 4 zone APPLICABLE scenario:
CASE 2: Diag RW RPAS Sector Zone Calibration (value :0x2)
XX Represents: RLC, RRC
CASE 4: Diag RW RPAS Sector Zone Calibration (value :0x4)
XX Represents: RL, RR,RLC
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64211 (System Requirement)
The above table is applicable for 4 zone APPLICABLE scenario:
CASE 5: Diag RW RPAS Sector Zone Calibration (value :0x5)
XX Represents: RLC, RRC,RR,RLC
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60486: Table- RPAS Status Chime -12 Zone (Heading)
- Variant: S220, S237, W502
- Stakeholder Requirement State: In Review
- System Requirement State: Draft
- Software Requirement State: Draft
- Primary Discipline: TBD
- Requirement Type: TBD

###### MS22029826-64213: Diag RW PAS Status Chime Enable (System Requirement)
| Diag RW PAS Status Chime Enable | RPAS Activation St | RPAS chime Precondition Logic | MBFM_PAS1_50: BAR_ZONE_XX | RPAS Status Chime Functional Logic |
| --- | --- | --- | --- | --- |
| 0 | X | X | X | Off |
| FPAS Only | X | X | X | Off |
| RPAS Only | False | X | X | Off |
| RPAS Only | True | False | X | Off |
| RPAS Only | True | True | 0x1~0x3 | Level1 On |
| RPAS Only | True | True | 0x4~0x6 | Level2 On |
| RPAS Only | True | True | 0x7~0x9 | Level3 On |
| RPAS Only | True | True | 0x9~0xC | Level4 On |
| RPAS Only | True | True | 0x0, 0xD to 0xF | Off |
| RPAS and FPAS | False | X | X | Off |
| RPAS and FPAS | True | False | X | Off |
| RPAS and FPAS | True | True | 0x1~0x3 | Level1 On |
| RPAS and FPAS | True | True | 0x4~0x6 | Level2 On |
| RPAS and FPAS | True | True | 0x7~0x9 | Level3 On |
| RPAS and FPAS | True | True | 0xA~0xC | Level4 On |
| RPAS and FPAS | True | True | 0x0, 0xD to 0xF | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64215 (System Requirement)
The above table is applicable for 12 zone APPLICABLE scenario:
CASE 6: Diag RW RPAS Sector Zone Calibration (value :0x6)
XX Represents: RLC,RRC
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60488: RPAS Status Chime - 8 Zone (Heading)
- Variant: S220, S237, W502
- Stakeholder Requirement State: In Review
- System Requirement State: Draft
- Software Requirement State: Draft
- Primary Discipline: TBD
- Requirement Type: TBD

###### MS22029826-64217: Diag RW PAS Status Chime Enable (System Requirement)
| Diag RW PAS Status Chime Enable | RPAS Activation St | RPAS chime Precondition Logic | MBFM_PAS1_50: BAR_ZONE_XX | RPAS Status Chime Functional Logic |
| --- | --- | --- | --- | --- |
| 0 | X | X | X | Off |
| FPAS Only | X | X | X | Off |
| RPAS Only | False | X | X | Off |
| RPAS Only | True | False | X | Off |
| RPAS Only | True | True | 0x1~0x3 | Level1 On |
| RPAS Only | True | True | 0x4~0x6 | Level2 On |
| RPAS Only | True | True | 0x7~0x8 | Level3 On |
| RPAS Only | True | True | 0x0, 0x9 to 0xF | Off |
| RPAS and FPAS | False | X | X | Off |
| RPAS and FPAS | True | False | X | Off |
| RPAS and FPAS | True | True | 0x1~0x3 | Level1 On |
| RPAS and FPAS | True | True | 0x4~0x6 | Level2 On |
| RPAS and FPAS | True | True | 0x7~0x8 | Level3 On |
| RPAS and FPAS | True | True | 0x0, 0x9 to 0xF | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64219 (System Requirement)
The above table is applicable for 8 zone APPLICABLE scenario:
CASE 6: Diag RW RPAS Sector Zone Calibration (value :0x6)
XX Represents: RL,RR
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60491: Table: FPAS status chime Precondidtions (Heading)
- Variant: S220, S237, W502
- Stakeholder Requirement State: In Review
- System Requirement State: Draft
- Software Requirement State: Draft
- Primary Discipline: TBD
- Requirement Type: TBD

###### MS22029826-64221: Ign Mode (System Requirement)
| Ign Mode | LVSD/HVSD Flag | MBFM_PAS1_100: FPAS_SWT_STS | CAN Signal Missing/ Never Received | MBFM_PAS1_100: FPAS_ERROR | FPAS chime Precondition Logic |
| --- | --- | --- | --- | --- | --- |
| Off | X | X | X | X | Off |
| On | Set | X | X | X | Off |
| On | Not Set | 1 | X | X | Off |
| On | Not Set | 0 | 1 | X | Off |
| On | Not Set | 0 | 0 | !=0x0 | Off |
| On | Not Set | 0 | 0 | =0x0 | On |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60493: Table- FPAS status Chime -3 zone (Heading)
- Variant: S220, S237, W502
- Stakeholder Requirement State: In Review
- System Requirement State: Draft
- Software Requirement State: Draft
- Primary Discipline: TBD
- Requirement Type: TBD

###### MS22029826-64222: Diag RW PAS Status Chime Enable (System Requirement)
| Diag RW PAS Status Chime Enable | RPAS Activation St | FPAS Activation St | FPAS chime Precondition Logic | MBFM_PAS1_50: BAR_ZONE_XX | FPAS Status Chime Functional Logic |
| --- | --- | --- | --- | --- | --- |
| 0 | X | X | X | X | Off |
| RPAS Only | X | X | X | X | Off |
| FPAS Only | X | False | X | X | Off |
| FPAS Only | X | True | False | X | Off |
| FPAS Only | X | True | True | 0x1 | Level1 On |
| FPAS Only | X | True | True | 0x2 | Level2 On |
| FPAS Only | X | True | True | 0x3 | Level3 On |
| FPAS Only | X | True | True | 0x0, 0x4 to 0xF | Off |
| RPAS and FPAS | False | False | X | X | Off |
| RPAS and FPAS | RPAS Activation St =True OR FPAS Activation St=True |  | False | X | Off |
| RPAS and FPAS | RPAS Activation St =True OR FPAS Activation St=True |  | True | 0x1 | Level1 On |
| RPAS and FPAS | RPAS Activation St =True OR FPAS Activation St=True |  | True | 0x2 | Level2 On |
| RPAS and FPAS | RPAS Activation St =True OR FPAS Activation St=True |  | True | 0x3 | Level3 On |
| RPAS and FPAS | RPAS Activation St =True OR FPAS Activation St=True |  | True | 0x0, 0x4 to 0xF | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64224 (System Requirement)
The above table is applicable for 3 zone APPLICABLE scenario:
CASE 1: Diag RW FPAS Sector Zone Calibration (value :0x1)
XX Represents: FLC, FRC
CASE 3: Diag RW FPAS Sector Zone Calibration (value :0x3)
XX Represents: FL, FR,FLC
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60495: Table- FPAS Status Chime -4 Zone (Heading)
- Variant: S220, S237, W502
- Stakeholder Requirement State: In Review
- System Requirement State: Draft
- Software Requirement State: Draft
- Primary Discipline: TBD
- Requirement Type: TBD

###### MS22029826-64226: Diag RW PAS Status Chime Enable (System Requirement)
| Diag RW PAS Status Chime Enable | RPAS Activation St | FPAS Activation St | FPAS chime Precondition Logic | MBFM_PAS1_50: BAR_ZONE_XX | FPAS Status Chime Functional Logic |
| --- | --- | --- | --- | --- | --- |
| 0 | X | X | X | X | Off |
| RPAS Only | X | X | X | X | Off |
| FPAS Only | X | False | X | X | Off |
| FPAS Only | X | True | False | X | Off |
| FPAS Only | X | True | True | 0x1 | Level1 On |
| FPAS Only | X | True | True | 0x2 | Level2 On |
| FPAS Only | X | True | True | 0x3 | Level3 On |
| FPAS Only | X | True | True | 0x4 | Level4 On |
| FPAS Only | X | True | True | 0x0, 0x5 to 0xF | Off |
| RPAS and FPAS | False | False | X | X | Off |
| RPAS and FPAS | RPAS Activation St =True OR FPAS Activation St=True |  | False | X | Off |
| RPAS and FPAS | RPAS Activation St =True OR FPAS Activation St=True |  | True | 0x1 | Level1 On |
| RPAS and FPAS | RPAS Activation St =True OR FPAS Activation St=True |  | True | 0x2 | Level2 On |
| RPAS and FPAS | RPAS Activation St =True OR FPAS Activation St=True |  | True | 0x3 | Level3 On |
| RPAS and FPAS | RPAS Activation St =True OR FPAS Activation St=True |  | True | 0x4 | Level4 On |
| RPAS and FPAS | RPAS Activation St =True OR FPAS Activation St=True |  | True | 0x0, 0x5 to 0xF | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64228 (System Requirement)
The above table is applicable for 4 zone APPLICABLE scenario:
CASE 2: Diag RW FPAS Sector Zone Calibration (value :0x2)
XX Represents: FLC, FRC
CASE 4: Diag RW FPAS Sector Zone Calibration (value :0x4)
XX Represents: FL, FR,FLC
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64230 (System Requirement)
The above table is applicable for 4 zone APPLICABLE scenario:
CASE 5: Diag RW FPAS Sector Zone Calibration (value :0x5)
XX Represents: FLC, FRC,FR,FL
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60497: Table- FPAS Status Chime -12 Zone (Heading)
- Variant: S220, S237, W502
- Stakeholder Requirement State: In Review
- System Requirement State: Draft
- Software Requirement State: Draft
- Primary Discipline: TBD
- Requirement Type: TBD

###### MS22029826-64232: Diag RW PAS Status Chime Enable (System Requirement)
| Diag RW PAS Status Chime Enable | RPAS Activation St | FPAS Activation St | FPAS chime Precondition Logic | MBFM_PAS1_50: BAR_ZONE_XX | FPAS Status Chime Functional Logic |
| --- | --- | --- | --- | --- | --- |
| 0 | X | X | X | X | Off |
| RPAS Only | X | X | X | X | Off |
| FPAS Only | X | False | X | X | Off |
| FPAS Only | X | True | False | X | Off |
| FPAS Only | X | True | True | 0x1~0x3 | Level1 On |
| FPAS Only | X | True | True | 0x4~0x6 | Level2 On |
| FPAS Only | X | True | True | 0x7~0x9 | Level3 On |
| FPAS Only | X | True | True | 0x9~0xC | Level4 On |
| FPAS Only | X | True | True | 0x0, 0xD to 0xF | Off |
| RPAS and FPAS | False | False | X | X | Off |
| RPAS and FPAS | RPAS Activation St =True OR FPAS Activation St=True |  | False | X | Off |
| RPAS and FPAS | RPAS Activation St =True OR FPAS Activation St=True |  | True | 0x1~0x3 | Level1 On |
| RPAS and FPAS | RPAS Activation St =True OR FPAS Activation St=True |  | True | 0x4~0x6 | Level2 On |
| RPAS and FPAS | RPAS Activation St =True OR FPAS Activation St=True |  | True | 0x7~0x9 | Level3 On |
| RPAS and FPAS | RPAS Activation St =True OR FPAS Activation St=True |  | True | 0xA~0xC | Level4 On |
| RPAS and FPAS | RPAS Activation St =True OR FPAS Activation St=True |  | True | 0x0, 0xD to 0xF | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64234 (System Requirement)
The above table is applicable for 12 zone APPLICABLE scenario:
CASE 6: Diag RW FPAS Sector Zone Calibration (value :0x6)
XX Represents: FLC,FRC
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60500: FPAS Status Chime - 8 Zone (Heading)
- Variant: S220, S237, W502
- Stakeholder Requirement State: In Review
- System Requirement State: Draft
- Software Requirement State: Draft
- Primary Discipline: TBD
- Requirement Type: TBD

###### MS22029826-64236: Diag RW PAS Status Chime Enable (System Requirement)
| Diag RW PAS Status Chime Enable | RPAS Activation St | FPAS Activation St | FPAS chime Precondition Logic | MBFM_PAS1_50: BAR_ZONE_XX | FPAS Status Chime Functional Logic |
| --- | --- | --- | --- | --- | --- |
| 0 | X | X | X | X | Off |
| RPAS Only | X | X | X | X | Off |
| FPAS Only | X | False | X | X | Off |
| FPAS Only | X | True | False | X | Off |
| FPAS Only | X | True | True | 0x1~0x3 | Level1 On |
| FPAS Only | X | True | True | 0x4~0x6 | Level2 On |
| FPAS Only | X | True | True | 0x7~0x8 | Level3 On |
| FPAS Only | X | True | True | 0x0, 0x9 to 0xF | Off |
| RPAS and FPAS | False | False | X | X | Off |
| RPAS and FPAS | RPAS Activation St =True OR FPAS Activation St=True |  | False | X | Off |
| RPAS and FPAS | RPAS Activation St =True OR FPAS Activation St=True |  | True | 0x1~0x3 | Level1 On |
| RPAS and FPAS | RPAS Activation St =True OR FPAS Activation St=True |  | True | 0x4~0x6 | Level2 On |
| RPAS and FPAS | RPAS Activation St =True OR FPAS Activation St=True |  | True | 0x7~0x8 | Level3 On |
| RPAS and FPAS | RPAS Activation St =True OR FPAS Activation St=True |  | True | 0x0, 0x9 to 0xF | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64238 (System Requirement)
The above table is applicable for 8 zone APPLICABLE scenario:
CASE 6: Diag RW FPAS Sector Zone Calibration (value :0x6)
XX Represents: FL,FR
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64240: RPAS: (System Requirement)
RPAS:
Chime shall play considering Min value of the sensors as highest priority ignoring the BAR_ZONE of other sensor based on Diag RW RPAS Sensor Zone Calibration
FPAS
Chime shall play considering Min value of the sensors as highest priority ignoring the BAR_ZONE of other sensor based on Diag RW RPAS Sensor Zone Calibration
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60143: Table-RPAS Self Check Chime Functional Logic (Heading)
- Variant: S220, S237, W502
- Stakeholder Requirement State: In Review
- System Requirement State: Draft
- Software Requirement State: Draft
- Primary Discipline: TBD
- Requirement Type: TBD

###### MS22029826-64242: Diag RW RPAS Self Check Chime Enable (System Requirement)
| VAR_CODING_MAHINDRA_BODY_ FUNCTION_MODULE | FEATURE_CODE_ RPAS_IND | Dia g RW RP AS Self Che ck Chi me Ena ble | RPAS Activa tion St | MBFM1_ 100 STS_TR AILER | CAN Signa l Missi ng/ Neve r Recei ved | MBFM_PA S1_50: RPAS_ER ROR | RPAS Self Check Chime Functi onal Logic |  |
| --- | --- | --- | --- | --- | --- | --- | --- | --- |
| 0 | X | X | X | X | X | X | Off |  |
| 1 | 0 | X | X | X | X | X | Off |  |
| 1 | 1 | 0 | X | X | X | X | Off |  |
| 1 | 1 | 1 | False | X | X | X | Off |  |
| 1 | 1 | 1 | False- >True | X | 1 | X | Off |  |
| 1 | 1 | 1 | False- >True | X | 0 | !=0x0 | Off |  |
| 1 | 1 | 1 | False- >True | 1 | 0 | 0x0 | Off |  |
| 1 | 1 | 1 | False- >True | 0 | 0 | 0x0 | On SelfTone For t= Diag RW RPAS Self Check time |  |
|  |  |  |  |  |  |  | (Diag RW RPAS Self Check |  |
|  |  |  |  |  |  |  | time Not Applica ble for smart |  |
|  |  |  |  |  |  |  | core) |  |
| 1 | 1 | 1 | True | X | 0 | 0x0 | Off |  |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44150: Overspeed Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52440: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60145: IgnMode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60147: LVSD/HVSD Flag (Value: Set, Not Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60149: VSpd Ind (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60151: Speedometer Preconditions (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60153: DiagRWOverSpeedLevel1Val (Default: 80kmph) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60154: DiagRWOverSpeedLevel2Val (Default: 120kmph). (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60156: DiagRWOverSpeedLevel1Type (Value: 0-Off, 1- Play Once, 2-Play & Repeat every N seconds (as defined by next parameter)) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60158: DiagRWOverSpeedLevel1RepetitionInterval (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60160: DiagRWOverSpeedLevel2Type (Value: 0-Off, 1- Play Once, 2-Play & Repeat every N seconds (as defined by next parameter)) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60162: DiagRWOverSpeedLevel2RepetitionInterval (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60164: DiagRWOverSpeedHysteresis(Default: 5%) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60166: Diag RW OverSpeed Chime Enable ( Value:0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52442: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60168: OverSpeed Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52444: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60169: Table - Overspeed Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64244: Speedometer Preconditions (System Requirement)
| Speedometer Preconditions | Diag RW OverSpeed Chime Enable | OverSpeed Chime Configuration |
| --- | --- | --- |
| 0 | X | 0 |
| 1 | 0 | 0 |
| 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60171: Table - Overspeed Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64246: IgnMode (System Requirement)
| IgnMode | LVSD/HVSD Flag | OverSpeed Chime Configuration | CAN Missing or Never Received | VSpd Ind | OverSpeed Chime Functional Logic |
| --- | --- | --- | --- | --- | --- |
| Off | X | X | X | X | Off |
| On | Set | X | X | X | Off |
| On | Not Set | 0 | X | X | Off |
| On | Not Set | 1 | 1 | X | Off |
| On | Not Set | 1 | 0 | >=DiagRWOverSpeedLevel1Val (increasing Trend) | Level1 chime ON, Level2 chime Off |
| On | Not Set | 1 | 0 | >DiagRWOverSpeedLevel1Val- DiagRWOverSpeedHysteresis AND <= DiagRWOverSpeedLevel2Val- DiagRWOverSpeedHysteresis (Decreasing Trend) | Level1 chime ON, Level2 chime Off |
| On | Not Set | 1 | 0 | >= DiagRWOverSpeedLevel2Val (Increasing Trend) | Level2 chime ON, Level1 chime Off |
| On | Not Set | 1 | 0 | <= DiagRWOverSpeedLevel1Val- DiagRWOverSpeedHysteresis (Decreasing Trend) | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64248: In case of Level 1 Chime: (System Requirement)
In case of Level 1 Chime:
- For every repetition, there shall be fixed OFF time of (5-2) sec where 2 sec is the WAV play duration. This shall reflect in the minimum calibratable repetition interval.
During the interval of 5<t<60 sec (calibratable), this chime shall not hold the channel so that other chimes shall be allowed to play as necessary
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64250: In case of Level 2 Chime, no other chimes (of lower priority) shall be allowed to play until this chime is compeleted. (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44152: WIF Chime (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52446: Input Requirements (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60173: IgnMode (Value: Off, On) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60175: LVSD/HVSD Flag (Value: Set, Not Set) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60177: Diag RW WIF Chime Enable (Value:0-Not Present, 1-Present) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60179: VAR_CODING_ENGINE_MANAGEMENT_SYSTEM (Value: 0-Not Present, 1-Present) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60180: FEATURE_CODE_FUEL_TYPE (Value: 0-Gasoline, 1-Diesel) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60182: EMS1_10: STS_WATER_IN_FUEL (Value: 0x0-No water in Fuel, 0x1-Water In Fuel) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60183: Engine Running st (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52448: Output Requirements (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60185: WIF Chime Functional Logic (Value: Off, On) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52450: Performance Requirements (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60187: Table - WIF Chime Configuration (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64252: VAR_CODING_ENGINE_MANAGEMENT_SYSTEM (System Requirement)
| VAR_CODING_ENGINE_MANAGEMENT_SYSTEM | FEATURE_CODE_FUEL_TYPE | Diag RW WIF Chime Enable | WIF Wrn Configuration |
| --- | --- | --- | --- |
| 0 | X | X | 0 |
| 1 | 0 | X | 0 |
| 1 | 1 | 0 | 0 |
| 1 | 1 | 1 | 1 |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60189: Table - WIF Chime Functional Logic (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64254: IgnMode (System Requirement)
| IgnMode | LVSD/HVSD Flag | WIF Chime Configuration | CAN Signal Missing or Never Received | EMS1_10: STS_WATER_IN_FUEL | Engine Running st | WIF Chime Functional Logic |
| --- | --- | --- | --- | --- | --- | --- |
| Off | X | X | X | X | X | Off |
| On | Set | X | X | X | X | Off |
| On | Not Set | 0 | X | X | X | Off |
| On | Not Set | 1 | 1 | X | X | Off |
| On | Not Set | 1 | 0 | 0 | X | Off |
| On | Not Set | 1 | 0 | 1 | No | Off |
| On | Not Set | 1 | 0 | 1 | Yes (<5secs) | Off |
| On | Not Set | 1 | 0 | 1 | Yes (>=5secs) | On |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44154: Key In Reminder (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52452: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60191: IgnMode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60193: LVSD/HVSD Flag (Value: Set, Not Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60195: MBFM1_100: KEY_IN_REMINDER (Value:1-Warning On ,0 -Warning Off ) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60197: VAR_CODING_MAHINDRA_BODY_FUNCTION_MODULE (Value: 0-Not Present, 1-Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60200: Diag RW KeyInReminder Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60202: FEATURE_CODE_KEY_IN_REMINDER_CONFIG (Values: 0-Disable, 1- Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52454: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60204: KeyInReminder Chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52456: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60206: Table - Key In Reminder Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64256: VAR_CODING_MAHINDRA_BODY_CONTROL_MODULE (System Requirement)
| VAR_CODING_MAHINDRA_BODY_CONTROL_MODULE | FEATURE_CODE_KEY_IN_REMINDER_CONFIG | Diag RW KeyInReminder Chime Enable | KeyInReminder Chime Configuration |
| --- | --- | --- | --- |
| 0 | X | X | 0 |
| 1 | 0 | X | 0 |
| 1 | 1 | 0 | 0 |
| 1 | 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60208: Table - Key In Reminder Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64258: IgnMode (System Requirement)
| IgnMode | LVSD/HVSD Flag | KeyInReminder Chime Configuration | CAN Signal Missing / Never received | MBFM1_100: KEY_IN_REMINDER | KeyInReminder Chime Functional Logic |
| --- | --- | --- | --- | --- | --- |
| On | X | X | X | X | Off |
| Off | Set | X | X | X | Off |
| Off | Not Set | 0 | X | X | Off |
| Off | Not Set | 1 | 1 | X | Off |
| Off | Not Set | 1 | 0 | 0x0 | Off |
| Off | Not Set | 1 | 0 | 0x1 | On |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44156: External Light Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52457: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60210: IgnMode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60212: LVSD/HVSD Flag (Value: Set, Not Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60214: MBFM1_100: PARK_LAMP_ON_REMINDER (Value: 0-Off,1- On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60216: VAR_CODING_MAHINDRA_BODY_FUNCTION_MODULE (Value: 0-Not Present, 1-Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60218: FEATURE_CODE_PARK_LAMP_ON_CONFIG (Value :0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60220: Diag RW ExtLamp Chime Enable (Value: 0-Disabled, 1-Enabled) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52459: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60222: ExtLamp Chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52461: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60224: Table - External Lamp Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64260: VAR_CODING_MAHINDRA_BODY_FUNCTION_MODULE (System Requirement)
|  | VAR_CODING_MAHINDRA_BODY_FUNCTION_MODULE | Diag RW ExtLamp Chime Enable | FEATURE_CODE_PARK_LAMP_ON_CONFIG | ExtLamp Chime Configuration |
| --- | --- | --- | --- | --- |
| 1 | 0 | X | X | 0 |
| 2 | 1 | 0 | X | 0 |
| 3 | 1 | 1 | 0 | 0 |
| 4 | 1 | 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60226: Table - External Lamp Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64262: IgnMode (System Requirement)
| IgnMode | LVSD/HVSD Flag | ExternalLight Chime Configuration | CAN Signal Missing/Never received | MBFM1_100: PARK_LAMP_ON_REMINDER | ExtLamp Chime Functional Logic |
| --- | --- | --- | --- | --- | --- |
| Off | Set | X | X | X | Off |
| Off | Not Set | 0 | X | X | Off |
| Off | Not Set | 1 | 1 | X | Off |
| Off | Not Set | 1 | 0 | 0 | Off |
| Off | Not Set | 1 | 0 | 1 | On |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44158: Low Fuel Chime (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52463: Input Requirements (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60228: IgnMode (Value: Off, On) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60230: LVSD/HVSD Flag (Value: Set, Not Set) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60232: Diag RW LowFuel Chime Enable (Value: 0-Disabled, 1-Enabled) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60234: Engine Running St (Value: Yes, No) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60235: IC1_100: . INDC_LOW_FUEL (Value: 0-Normal, 1-Low Fuel) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52465: Output Requirements (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60237: LowFuel Chime Functional Logic (Value: Off, On) (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52466: Performance Requirements (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-59961: Table - Low Fuel Chime Configuration (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64264: Diag RW LowFuel Chime Enable (System Requirement)
| Diag RW LowFuel Chime Enable | LowFuel Chime Configuration |
| --- | --- |
| 1 | 1 |
| 0 | 0 |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-59964: Table - Low Fuel Chime Functional Logic (System Requirement)
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64266: IgnMode (System Requirement)
|  | IgnMode | LVSD/HVSD Flag | LowFuel Chime Config | IC1_100: INDC_LOW_FUEL | Engine Running St | LowFuel Chime Functional Logic |
| --- | --- | --- | --- | --- | --- | --- |
| 1 | Off | X | X | X | X | Off |
| 2 | On | 1 | X | X | X | Off |
| 3 | On | 0 | 0 | X | X | Off |
| 5 | On | 0 | 1 | 0 | X | Off |
| 6 | On | 0 | 1 | 1 | No | Off |
| 7 | On | 0 | 1 | 1 | Yes (<5sec) | Off |
| 8 | On | 0 | 1 | 1 | Yes (>=5sec) | On |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44163: Seatbelt Chime (Information)
- Variant: S220, S237, W502
- Stakeholder Requirement State: In Review
- System Requirement State: Draft
- Software Requirement State: Draft
- Primary Discipline: TBD
- Requirement Type: TBD

#### MS22029826-52434: Input Requirements (Information)
- Variant: S220, S237, W502
- Stakeholder Requirement State: In Review
- System Requirement State: Draft
- Software Requirement State: Draft
- Primary Discipline: TBD
- Requirement Type: TBD

##### MS22029826-60051: IgnMode (Value: Off, On) (Information)
- Variant: S220, S237, W502
- Stakeholder Requirement State: In Review
- System Requirement State: Draft
- Software Requirement State: Draft
- Primary Discipline: SW
- Requirement Type: Functional

##### MS22029826-60052: LVSD/HVSD Flag (Value: Not Set, Set) (Information)
- Variant: S220, S237, W502
- Stakeholder Requirement State: In Review
- System Requirement State: Draft
- Software Requirement State: Draft
- Primary Discipline: SW
- Requirement Type: Functional

##### MS22029826-60054: VAR_CODING_SUPPLEMENTARY_RESTRAINT_SYSTEM(Value: 0-Not Present, 1-Present) (Information)
- Variant: S220, S237, W502
- Stakeholder Requirement State: In Review
- System Requirement State: Draft
- Software Requirement State: Draft
- Primary Discipline: SW
- Requirement Type: Functional

##### MS22029826-60056: VAR_CODING_MAHINDRA_BODY_FUNCTION_MODULE (Value: 0-Not Present, 1-Present) (Information)
- Variant: S220, S237, W502
- Stakeholder Requirement State: In Review
- System Requirement State: Draft
- Software Requirement State: Draft
- Primary Discipline: SW
- Requirement Type: Functional

##### MS22029826-60059: VAR_CODING_SEAT_BELT_REMINDER (Value: 0-Not Present, 1-Present) (Information)
- Variant: S220, S237, W502
- Stakeholder Requirement State: In Review
- System Requirement State: Draft
- Software Requirement State: Draft
- Primary Discipline: SW
- Requirement Type: Functional

##### MS22029826-60061: FEATURE_CODE_CODRIVER_SBR_CONFIG (Value: 0- Disabled, 1- Enabled) (Information)
- Variant: S220, S237, W502
- Stakeholder Requirement State: In Review
- System Requirement State: Draft
- Software Requirement State: Draft
- Primary Discipline: SW
- Requirement Type: Functional

##### MS22029826-60063: FEATURE_CODE_REARSEATBELT_INPUT_SEL (Value: 0 - SBRM 1- MBFM) (Information)
- Variant: S220, S237, W502
- Stakeholder Requirement State: In Review
- System Requirement State: Draft
- Software Requirement State: Draft
- Primary Discipline: SW
- Requirement Type: Functional

##### MS22029826-60066: FEATURE_CODE_REAR_SEAT_COMBINATION (Value: 0 ,1 - Option1, 2 - Option2, 3 - Option3) (Information)
- Variant: S220, S237, W502
- Stakeholder Requirement State: In Review
- System Requirement State: Draft
- Software Requirement State: Draft
- Primary Discipline: SW
- Requirement Type: Functional

##### MS22029826-60068 (Information)
SRS1_20: STS_SEAT_BLT_DRV (Value: 0x0-Not Buckled,0x1-Buckled, 0x2-Buckle Faulty,0x3-
Reserved)
- Variant: S220, S237, W502
- Stakeholder Requirement State: In Review
- System Requirement State: Draft
- Software Requirement State: Draft
- Primary Discipline: SW
- Requirement Type: Functional

##### MS22029826-60503: SRS1_20:SRS_CRC(Value:0x0 to 0xFF) (Information)
- Variant: S220, S237, W502
- Stakeholder Requirement State: In Review
- System Requirement State: Draft
- Software Requirement State: Draft
- Primary Discipline: SW
- Requirement Type: Functional

##### MS22029826-60506 (Information)
SRS1_20: STS_SEAT_BLT_PSGR (Value: 0x0-Not Buckled,0x1-Buckled, 0x2-Buckle Faulty,0x3-
Reserved)
- Variant: S220, S237, W502
- Stakeholder Requirement State: In Review
- System Requirement State: Draft
- Software Requirement State: Draft
- Primary Discipline: SW
- Requirement Type: Functional

##### MS22029826-60508 (Information)
EMS1_10: CURRENT GEAR_MT (Value: Value: 0-Neutral, 1-1st gear, 2-2nd gear, 3-3rd gear, 4-4th
gear,5-5th gear, 6-6th gear, 7-Reverse, 8~0xE-Reserved,0xF-Invalid)
- Variant: S220, W502
- Stakeholder Requirement State: In Review
- System Requirement State: Draft
- Software Requirement State: Draft
- Primary Discipline: SW
- Requirement Type: Functional

##### MS22029826-73339 (Information)
VCU10_100: GEAR_ACTUAL_VCU (Values: 0x0=neutral/default, 0x1=Forward mode,
0x2=Reverse Mode, 0x3=Low mode, 0x4=Reserved, 0x5= Park Mode, 0x6= Reserved,
0x7= Signal invalid)
- Variant: S237
- Stakeholder Requirement State: In Review
- System Requirement State: Draft
- Software Requirement State: Draft
- Primary Discipline: SW
- Requirement Type: Functional

##### MS22029826-60510 (Information)
TCU6_20: TGS_LEVER (Value: Value: 0~5-Reserved,0x6-Drive, 0x7-Neutral 0x8-Reverse 0x7-Neutral
0x8-Reverse, 0x9-Park, 0x9-Park, 0xA-Trip+,0xB-Trip-0xC-M-forward drive 0xD-Default Value ,0xE-Middle position,0xF-Signal Invalid)
- Variant: S220, W502
- Stakeholder Requirement State: In Review
- System Requirement State: Draft
- Software Requirement State: Draft
- Primary Discipline: SW
- Requirement Type: Functional

##### MS22029826-73346: AMT5_20: GEAR_ACTUAL_AMT (Value: 0x0-Neutral, 0x1-1st gear, 0x2-2nd gear, 0x3-3rd gear, 0x4-4th gear, 0x5-5th gear,0x6~0x9-Reserved, 0xB~0XE-Reserved, 0xA-Reverse,, 0xF-Invalid) (Information)
- Variant: S220
- Stakeholder Requirement State: In Review
- System Requirement State: Draft
- Software Requirement State: Draft
- Primary Discipline: SW
- Requirement Type: Functional

##### MS22029826-73357: MBFM1_100(0X348): STS_SEAT_BLT_DRVR(Value: 0x0-Not Buckled/Default, 0x1-Buckled, 0x2- Buckle Faulty, 0x3-Reserved) (Information)
- Variant: S220, W502
- Stakeholder Requirement State: In Review
- System Requirement State: Draft
- Software Requirement State: Draft
- Primary Discipline: SW
- Requirement Type: Functional

##### MS22029826-73359: MBFM1_100(0X348): STS_SEAT_BLT_PSGR(Value: 0x0-Not Buckled/Default, 0x1-Buckled, 0x2- Buckle Faulty, 0x3-Reserved) (Information)
- Variant: S220, W502
- Stakeholder Requirement State: In Review
- System Requirement State: Draft
- Software Requirement State: Draft
- Primary Discipline: SW
- Requirement Type: Functional

##### MS22029826-60512: Engine Running St (Value: Yes, No) (Information)
- Variant: S220, W502
- Stakeholder Requirement State: In Review
- System Requirement State: Draft
- Software Requirement State: Draft
- Primary Discipline: SW
- Requirement Type: Functional

##### MS22029826-73362: Engine Running St (Value: Yes, No) (Information)
Engine Running St (Value: Yes, No)
*(Engine running St from VCU10_100: INDC_DRIVE_ENABLE-Refer Artifact 5227913 from gauges Section)
- Variant: S237
- Stakeholder Requirement State: In Review
- System Requirement State: Draft
- Software Requirement State: Draft
- Primary Discipline: SW
- Requirement Type: Functional

##### MS22029826-60514: Vehicle Moving St (Value: Yes, No) (Information)
- Variant: S220, S237, W502
- Stakeholder Requirement State: In Review
- System Requirement State: Draft
- Software Requirement State: Draft
- Primary Discipline: SW
- Requirement Type: Functional

##### MS22029826-60516: VSpd Ind (Refer Speedometer) (Information)
- Variant: S220, S237, W502
- Stakeholder Requirement State: In Review
- System Requirement State: Draft
- Software Requirement State: Draft
- Primary Discipline: SW
- Requirement Type: Functional

##### MS22029826-60517: Odo Out (Refer odometer) (Information)
- Variant: S220, S237, W502
- Stakeholder Requirement State: In Review
- System Requirement State: Draft
- Software Requirement State: Draft
- Primary Discipline: SW
- Requirement Type: Functional

##### MS22029826-60519: Diag RW SeatBelt Chime Enable (Value: 0-Disable, 1-Enable) (Information)
- Variant: S220, S237, W502
- Stakeholder Requirement State: In Review
- System Requirement State: Draft
- Software Requirement State: Draft
- Primary Discipline: SW
- Requirement Type: Functional

##### MS22029826-60521: Diag RW Rear PSGR SeatBelt Chime Enable (Value: 0-Disable, 1-Enable) (Information)
- Variant: S220, S237, W502
- Stakeholder Requirement State: In Review
- System Requirement State: Draft
- Software Requirement State: Draft
- Primary Discipline: SW
- Requirement Type: Functional

##### MS22029826-60523: Diag RW Seatbelt FW Signal Resume (Default-10km/h) (Information)
- Variant: S220, S237, W502
- Stakeholder Requirement State: In Review
- System Requirement State: Draft
- Software Requirement State: Draft
- Primary Discipline: SW
- Requirement Type: Functional

##### MS22029826-60524 (Information)
MBFM9_500: PSGR_REAR_SEAT_BELT (Value:0x0-0x3F)
BIT 0:- Rear Left Passenger(0-Not Buckled,1-Buckled)
BIT 1:- Rear Middle Passenger(0-Not Buckled,1-Buckled)
BIT 2:- Rear Right Passenger(0-Not Buckled,1-Buckled)
BIT 3:- Rear 3rd RowLeft Passenger(0-Not Buckled,1-Buckled)
BIT 4:- Rear 3rd Row Middle Passenger(0-Not Buckled,1-Buckled)
BIT 5:- Rear 3rd Row Right Passenger(0-Not Buckled,1-Buckled)
- Variant: S220, S237, W502
- Stakeholder Requirement State: In Review
- System Requirement State: Draft
- Software Requirement State: Draft
- Primary Discipline: SW
- Requirement Type: Functional

##### MS22029826-60528: Configurable table for Front (Drv,Psgr) (Information)
|  | Engine RPM time check (Diag RW SBR Eng Running Time) | Forward motion time check. (Diag RW SBR Moving Time) | ODO distance (m) (Diag RW SBR Moving Distance) | Vehicle speed check for final trigger (Diag RW SBR Speed Threshold) | Chime duration (Diag RW SBR Final Chime Duration) |
| --- | --- | --- | --- | --- | --- |
| Final signal | 59 sec | 59 sec | 490 | >=24 kmph | 95 sec |
- Variant: S220, S237, W502
- Stakeholder Requirement State: In Review
- System Requirement State: Draft
- Software Requirement State: Draft
- Primary Discipline: SW
- Requirement Type: Functional

##### MS22029826-60530: Configurable table for Rear: (Information)
|  | Chime duration (Diag RW Rear SBR Final Chime Duration) |
| --- | --- |
| Final signal | 35 sec |
- Variant: S220, S237, W502
- Stakeholder Requirement State: In Review
- System Requirement State: Draft
- Software Requirement State: Draft
- Primary Discipline: SW
- Requirement Type: Functional

##### MS22029826-114483: FEATURE_CODE_REARSEATBELT_INPUT_SEL (Value: 0-SBRM , 1- MBFM) (Information)
- Variant: S237
- Stakeholder Requirement State: In Review
- System Requirement State: Draft
- Software Requirement State: Draft
- Primary Discipline: SW
- Requirement Type: Functional

##### MS22029826-114538 (Information)
SBRM1_100: PSGR_REAR_SEAT_BELT (Value:0x0-0x3F)
BIT 0:- Rear Left Passenger(0-Not Buckled,1-Buckled)
BIT 1:- Rear Middle Passenger(0-Not Buckled,1-Buckled)
BIT 2:- Rear Right Passenger(0-Not Buckled,1-Buckled)
BIT 3:- Rear 3rd RowLeft Passenger(0-Not Buckled,1-Buckled)
BIT 4:- Rear 3rd Row Middle Passenger(0-Not Buckled,1-Buckled)
BIT 5:- Rear 3rd Row Right Passenger(0-Not Buckled,1-Buckled)
- Variant: S237
- Stakeholder Requirement State: In Review
- System Requirement State: Draft
- Software Requirement State: Draft
- Primary Discipline: SW
- Requirement Type: Functional

#### MS22029826-52436: Output Requirements (Information)
- Variant: S220, S237, W502
- Stakeholder Requirement State: In Review
- System Requirement State: Draft
- Software Requirement State: Draft
- Primary Discipline: TBD
- Requirement Type: TBD

##### MS22029826-60532: SeatBelt Chime Functional Logic (Value: Off, On) (Information)
- Variant: S220, S237, W502
- Stakeholder Requirement State: In Review
- System Requirement State: Draft
- Software Requirement State: Draft
- Primary Discipline: SW
- Requirement Type: Functional

##### MS22029826-60534: Rear Seat Belt Final Condition St (Value: No, Yes) (Information)
- Variant: S220, S237, W502
- Stakeholder Requirement State: In Review
- System Requirement State: Draft
- Software Requirement State: Draft
- Primary Discipline: SW
- Requirement Type: Functional

##### MS22029826-60535: SeatBelt Final Condition St (Value: No, Yes) (Information)
- Variant: S220, S237, W502
- Stakeholder Requirement State: In Review
- System Requirement State: Draft
- Software Requirement State: Draft
- Primary Discipline: SW
- Requirement Type: Functional

##### MS22029826-60537: IC2_200:SEAT_BELT_REMAINDER_FL_REAR( Value: 0-Default, 1-Pattern 3, 2-Reserved, 3-Reserved) (Information)
- Variant: S220, S237, W502
- Stakeholder Requirement State: In Review
- System Requirement State: Draft
- Software Requirement State: Draft
- Primary Discipline: SW
- Requirement Type: Functional

#### MS22029826-52438: Performance Requirements (Information)
- Variant: S220, S237, W502
- Stakeholder Requirement State: In Review
- System Requirement State: Draft
- Software Requirement State: Draft
- Primary Discipline: TBD
- Requirement Type: TBD

##### MS22029826-60539: Table- Seat Belt Drv Chime Configuration (Information)
- Variant: S220, S237, W502
- Stakeholder Requirement State: In Review
- System Requirement State: Draft
- Software Requirement State: Draft
- Primary Discipline: TBD
- Requirement Type: TBD

###### MS22029826-64010: VAR_CODING_SUPPLIMENTARY_RESTRAINT_SYSTEM (Information)
|  | VAR_CODING_SUPPLIMENTARY_RESTRAINT_SYSTEM | Diag RW Seat Belt Drv Chime Enable | Drv SeatBelt Chime Configuration |
| --- | --- | --- | --- |
| 1 | X | 0 | 0 |
| 2 | 0 | 1 | 0 |
| 3 | 1 | 1 | 1 |
- Variant: S220, S237, W502
- Stakeholder Requirement State: In Review
- System Requirement State: Draft
- Software Requirement State: Draft
- Primary Discipline: SW
- Requirement Type: Functional

##### MS22029826-60541: Table- Psgr Seat Belt Chime Configuration (Information)
- Variant: S220, S237, W502
- Stakeholder Requirement State: In Review
- System Requirement State: Draft
- Software Requirement State: Draft
- Primary Discipline: TBD
- Requirement Type: TBD

###### MS22029826-64012: FEATURE_CODE_CODRIVER_SBR_CONFIG​ (Information)
|  | FEATURE_CODE_CODRIVER_SBR_CONFIG​ | VAR_CODING_SUPPLIMENTARY_RESTRAINT_SYSTEM | Diag RW Seat Belt Drv Chime Enable | Psgr SeatBelt Chime Configuration |
| --- | --- | --- | --- | --- |
| 1 | X | X | 0 | 0 |
| 2 | X | 0 | 1 | 0 |
| 3 | 0 | 1 | 1 | 0 |
| 4 | 1 | 1 | 1 | 1 |
- Variant: S220, S237, W502
- Stakeholder Requirement State: In Review
- System Requirement State: Draft
- Software Requirement State: Draft
- Primary Discipline: SW
- Requirement Type: Functional

##### MS22029826-73370: Table- Rear Seat Belt Chime Configuration (Information)
- Variant: S220, S237, W502
- Stakeholder Requirement State: In Review
- System Requirement State: Draft
- Software Requirement State: Draft
- Primary Discipline: TBD
- Requirement Type: TBD

###### MS22029826-73371: VAR_CODING_MAHINDRA_BODY_FUNCTION_MODULE (Information)
|  | VAR_CODING_MAHINDRA_BODY_FUNCTION_MODULE | Diag RW Rear PSGR SeatBelt Chime Enable | Rear SeatBelt Chime Configuration |
| --- | --- | --- | --- |
| 1 | 0 | 1 | 0 |
| 2 | 1 | 1 | 1 |
- Variant: S220, W502
- Stakeholder Requirement State: In Review
- System Requirement State: Draft
- Software Requirement State: Draft
- Primary Discipline: SW
- Requirement Type: Functional

##### MS22029826-60542: Table- Seat Belt Final Condition St (Information)
- Variant: S220, S237, W502
- Stakeholder Requirement State: In Review
- System Requirement State: Draft
- Software Requirement State: Draft
- Primary Discipline: TBD
- Requirement Type: TBD

###### MS22029826-64014 (Information)
After ignition ON and anyone of the seatbelt is not buckled and vehicle should achieve anyone of the below conditions to start the final signal (chime).
| 1.Engine Running St >= Diag RW SBR Eng Running RPM for Diag RW SBR Eng Running Time | 2.Vehicle Moving St >= Diag RW SBR Moving Threshold for Diag RW SBR Moving Time | 1. ODO Out >= Vehicle Covered Diag RW SBR Moving Distance in forward motion | 4.VSpd Ind >= Diag RW SBR Speed Threshold in forward motion | SeatBelt Final Condition St |
| --- | --- | --- | --- | --- |
| No | No | No | No | No |
| X | X | X | Yes | Yes |
| X | X | Yes | X | Yes |
| X | Yes | X | X | Yes |
| Yes | X | X | X | Yes |
Note: Point 1~3 Timer to be restarted to meet the final condition. Point 4 to be met while revaluating the final condition.
Once condition evaluated and met then all conditions to be restarted again from next buckle change
- Variant: S220, S237, W502
- Stakeholder Requirement State: In Review
- System Requirement State: Draft
- Software Requirement State: Draft
- Primary Discipline: SW
- Requirement Type: Functional

##### MS22029826-60544: Table-Rear Seat belt Final Condition St (Information)
- Variant: S220, S237, W502
- Stakeholder Requirement State: In Review
- System Requirement State: Draft
- Software Requirement State: Draft
- Primary Discipline: TBD
- Requirement Type: TBD

###### MS22029826-64016: VSpd Ind >= Diag RW SBR Speed Threshold in forward motion (Information)
| VSpd Ind >= Diag RW SBR Speed Threshold in forward motion | Rear Seat Belt Final Condition St |
| --- | --- |
| No | No |
| Yes | Yes |
- Variant: S220, S237, W502
- Stakeholder Requirement State: In Review
- System Requirement State: Draft
- Software Requirement State: Draft
- Primary Discipline: SW
- Requirement Type: Functional

##### MS22029826-60546: Table- Seat Belt Chime Driver St (Information)
- Variant: S220, S237, W502
- Stakeholder Requirement State: In Review
- System Requirement State: Draft
- Software Requirement State: Draft
- Primary Discipline: TBD
- Requirement Type: TBD

###### MS22029826-64018: Table- Seat Belt Chime Driver St (Information)
|  | Drv SeatBelt Chime Configuration | CAN Signal Missing/ Never | SRS1_20:SRS_CRC SRS1_20:STS_SEAT_BELT_DRV |  | Drv Chime SBR St |
| --- | --- | --- | --- | --- | --- |
| 1 2 3 4 5 6 7 |  | Received |  |  |  |
| 1 2 3 4 5 6 7 | 0 | X | X X Invalid Valid Valid Valid Valid | X | Off |
| 1 2 3 4 5 6 7 | 1 | 1 | X X Invalid Valid Valid Valid Valid | X | Off |
| 1 2 3 4 5 6 7 | 1 | 0 | X X Invalid Valid Valid Valid Valid | X | Off |
| 1 2 3 4 5 6 7 | 1 | 0 | X X Invalid Valid Valid Valid Valid | 0x0(Not Buckled/Default) | On |
| 1 2 3 4 5 6 7 | 1 | 0 | X X Invalid Valid Valid Valid Valid | 0x1(Buckled) | Off |
| 1 2 3 4 5 6 7 | 1 | 0 | X X Invalid Valid Valid Valid Valid | 0x2(Buckle faulty) | Off |
| 1 2 3 4 5 6 7 | 1 | 0 | X X Invalid Valid Valid Valid Valid | 0x3(reserved) | Off |
- Variant: S220, S237, W502
- Stakeholder Requirement State: In Review
- System Requirement State: Draft
- Software Requirement State: Draft
- Primary Discipline: SW
- Requirement Type: Functional

##### MS22029826-60548: Table- Seat Belt Chime Psgr St (Information)
- Variant: S220, S237, W502
- Stakeholder Requirement State: In Review
- System Requirement State: Draft
- Software Requirement State: Draft
- Primary Discipline: TBD
- Requirement Type: TBD

###### MS22029826-64020: PSGR SeatBelt Chime Configuration (Information)
|  | PSGR SeatBelt Chime Configuration | CAN Signal Missing/ Never Received | SRS1_20:SRS_CRC | SRS1_20: STS_SEAT_BELT_PSGR | Psgr Chime SBR St |
| --- | --- | --- | --- | --- | --- |
| 1 | 0 | X | X | X | Off |
| 2 | 1 | 1 | X | X | Off |
| 3 | 1 | 0 | Invalid | X | Off |
| 4 | 1 | 0 | Valid | 0x0(Not Buckled/Default) | On |
| 5 | 1 | 0 | Valid | 0x1(Buckled) | Off |
| 6 | 1 | 0 | Valid | 0x2(Buckle faulty) | Off |
| 7 | 1 | 0 | Valid | 0x3(reserved) | Off |
- Variant: S220, S237, W502
- Stakeholder Requirement State: In Review
- System Requirement State: Draft
- Software Requirement State: Draft
- Primary Discipline: SW
- Requirement Type: Functional

##### MS22029826-60550: Table- Rear Chime SeatBelt St (Information)
- Variant: S220, S237, W502
- Stakeholder Requirement State: In Review
- System Requirement State: Draft
- Software Requirement State: Draft
- Primary Discipline: TBD
- Requirement Type: TBD

###### MS22029826-64022: Rear Seatbelt Chime Configuration (Information)
| Rear Seatbelt Chime Configuration | CAN Signal Missing/ Never Received | MBFM9_500: PSGR_REAR_SEAT_BELT |  |  | Rear Chime SBR St |
| --- | --- | --- | --- | --- | --- |
| Rear Seatbelt Chime Configuration | CAN Signal Missing/ Never Received | Bit 2 | Bit 1 | Bit 0 | Rear Chime SBR St |
| X | X | X |  |  | Off |
| 0 | X | X |  |  | Off |
| 1 | 1 | X |  |  | Off |
| 1 | 0 | X | X | 0 | On |
| 1 | 0 | X | 0 | X | On |
| 1 | 0 | 0 | X | X | On |
| 1 | 0 | 1 | 1 | 1 | Off |
- Variant: S220, W502
- Stakeholder Requirement State: In Review
- System Requirement State: Draft
- Software Requirement State: Draft
- Primary Discipline: SW
- Requirement Type: Functional

###### MS22029826-114490: Table- Rear Chime SeatBelt St (Information)
| Diag RW Rear PSGR SeatBelt Chime Enable | CAN Signal Missing/ Never Received | FEATURE_CODE_REARSEATBELT_INPUT_SEL | VAR_CODING_MAHINDRA_BODY_FUNCTION_MODULE | MBFM9_500: PSGR_REAR_SEAT_BELT |  |  | SBRM1_100: PSGR_REAR_SEAT_BE LT |  |  | Rear SBR St |
| --- | --- | --- | --- | --- | --- | --- | --- | --- | --- | --- |
| Diag RW Rear PSGR SeatBelt Chime Enable | CAN Signal Missing/ Never Received | FEATURE_CODE_REARSEATBELT_INPUT_SEL | VAR_CODING_MAHINDRA_BODY_FUNCTION_MODULE | Bit 2 | Bit 1 | Bit 0 | Bit 2 | Bit 1 | Bit 0 | Rear SBR St |
| 0 | X | X | X | X |  |  | X |  |  | Off |
| 1 | 1 | X | X | X |  |  | X |  |  | Off |
| 1 | 0 | 1 | 0 | X |  |  | X |  |  | Off |
| 1 | 0 | 1 | 1 | X | X | 0 | X |  |  | On |
| 1 | 0 | 1 | 1 | X | 0 | X | X |  |  | On |
| 1 | 0 | 1 | 1 | 0 | X | X | X |  |  | On |
| 1 | 0 | 1 | 1 | 1 | 1 | 1 | X |  |  | Off |
| 1 | 0 | 0 | X | X |  |  | X | X | 0 | On |
| 1 | 0 | 0 | X | X |  |  | X | 0 | X | On |
| 1 | 0 | 0 | X | X |  |  | 0 | X | X | On |
| 1 | 0 | 0 | X | X |  |  | 1 | 1 | 1 | Off |
- Variant: S237
- Stakeholder Requirement State: In Review
- System Requirement State: Draft
- Software Requirement State: Draft
- Primary Discipline: SW
- Requirement Type: Functional

##### MS22029826-60552: Table- Seat Belt Chime Functional Logic (Information)
- Variant: S220, S237, W502
- Stakeholder Requirement State: In Review
- System Requirement State: Draft
- Software Requirement State: Draft
- Primary Discipline: TBD
- Requirement Type: TBD

###### MS22029826-64028: S220/W502 (Information)
Drv SeatBelt chime Logic:
|  | IgnMode | LVSD/HVSD Flag | Drv Chime SBR St | CAN Signal missing for #Gear Signal | CURRENT_GEAR_MT (or) TGS_LEVER (or) AMT5_20: GEAR_ACTUAL_AMT | SeatBelt Final Condition St | Drv SeatBelt Chime Logic |
| --- | --- | --- | --- | --- | --- | --- | --- |
| 1 | Off | X | X | X | X | X | Off |
| 2 | On | Set | X | X | X | X | Off |
| 3 | On | Not Set | Off | X | X | X | Off |
| 4 | On | Not Set | On | 1 | X | X | Off |
| 5 | On | Not Set | On | 0 | Reverse | X | Off |
| 6 | On | Not Set | On | 0 | ^#Not Reverse | No | Off |
| 7 | On | Not Set | On | 0 | ^#Not Reverse | Yes | On |
PSGR Seatbelt Chime Logic:
|  | IgnMode | LVSD/HVSD Flag | PSGR Chime SBR St | CAN Signal missing for #Gear Signal | CURRENT_GEAR_MT (or) TGS_LEVER (or) AMT5_20: GEAR_ACTUAL_AMT | SeatBelt Final Condition St | PSGR SeatBelt Chime Logic |
| --- | --- | --- | --- | --- | --- | --- | --- |
| 1 | Off | X | X | X | X | X | Off |
| 2 | On | Set | X | X | X | X | Off |
| 3 | On | Not Set | Off | X | X | X | Off |
| 4 | On | Not Set | On | 1 | X | X | Off |
| 5 | On | Not Set | On | 0 | Reverse | X | Off |
| 6 | On | Not Set | On | 0 | ^#Not Reverse | No | Off |
| 7 | On | Not Set | On | 0 | ^#Not Reverse | Yes | On |
Note:
1.Appropriate gear signal shall be used based on MT/AT/AMT
1. Reverse Usecase:
When Forward gear is re-selected and forward motion commences (>10 km/h (Diag RW Seatbelt FW Signal Resume), the Final Signal must resume again (Note: Only Elapsed duration chime shall Play)
1. Whenever there is a change in either or both ‘Driver SBR St = On’ or ‘PSGR SBR St = On’ or ‘from Off, the ‘SeatBelt Final Condition St’ shall be evaluated from start and the chime shall be retriggered when ‘SeatBelt Final Condition St=TRUE’.
- Variant: S220, W502
- Stakeholder Requirement State: In Review
- System Requirement State: Draft
- Software Requirement State: Draft
- Primary Discipline: SW
- Requirement Type: Functional

###### MS22029826-73378: S237 (Information)
Drv SeatBelt chime Logic:
|  | IgnMode | LVSD/HVSD Flag | Drv Chime SBR St | CAN Signal missing for #Gear Signal | VCU10_100: GEAR_ACTUAL_VC U | SeatBelt Final Condition St | Drv SeatBelt Chime Logic |
| --- | --- | --- | --- | --- | --- | --- | --- |
| 1 | Off | X | X | X | X | X | Off |
| 2 | On | Set | X | X | X | X | Off |
| 3 | On | Not Set | Off | X | X | X | Off |
| 4 | On | Not Set | On | 1 | X | X | Off |
| 5 | On | Not Set | On | 0 | Reverse | X | Off |
| 6 | On | Not Set | On | 0 | ^#^Not Reverse | No | Off |
| 7 | On | Not Set | On | 0 | ^#^Not Reverse | Yes | On |
PSGR Seatbelt Chime Logic:
|  | IgnMode | LVSD/HVSD Flag | PSGR Chime SBR St | CAN Signal missing for #Gear Signal | VCU10_100: GEAR_ACTUAL_VC U | SeatBelt Final Condition St | PSGR SeatBelt Chime Logic |
| --- | --- | --- | --- | --- | --- | --- | --- |
| 1 | Off | X | X | X | X | X | Off |
| 2 | On | Set | X | X | X | X | Off |
| 3 | On | Not Set | Off | X | X | X | Off |
| 4 | On | Not Set | On | 1 | X | X | Off |
| 5 | On | Not Set | On | 0 | Reverse | X | Off |
| 6 | On | Not Set | On | 0 | ^#^Not Reverse | No | Off |
| 7 | On | Not Set | On | 0 | ^#^Not Reverse | Yes | On |
Note:
1. Reverse Usecase:
When Forward gear is re-selected and forward motion commences (>10 km/h (Diag RW
Seatbelt FW Signal Resume), the Final Signal must resume again (Note: Only Elapsed duration chime shall Play)
2. Whenever there is a change in either or both ‘Driver SBR St = On’ or ‘PSGR SBR St = On’ or ‘from Off, the ‘SeatBelt Final Condition St’ shall be evaluated from start and the chime shall be retriggered when ‘SeatBelt Final Condition St=TRUE’.
- Stakeholder Requirement State: In Review
- System Requirement State: Draft
- Software Requirement State: Draft
- Primary Discipline: SW
- Requirement Type: Functional

##### MS22029826-60554: Table-Rear Seatbelt Chime Functional Logic (Information)
- Variant: S220, S237, W502
- Stakeholder Requirement State: In Review
- System Requirement State: Draft
- Software Requirement State: Draft
- Primary Discipline: TBD
- Requirement Type: TBD

###### MS22029826-64030: S220/W502 (Information)
| IgnMode | LVDS/HVSD Flag | Rear Chime SBR St | CAN Signal missing for ^#1Gear | CURRENT_GEAR_MT (or) TGS_LEVER (or) AMT5_20: GEAR_ACTUAL_AMT | Rear Seat Belt Final Condition St | Rear Chime Logic |
| --- | --- | --- | --- | --- | --- | --- |
| Off | X | X | X | X | X | Off |
| On | Set | X | X | X | X | Off |
| On | Not set | Off | X | X | X | Off |
| On | Not set | On | 1 | X | X | Off |
| On | Not Set | On | 0 | Reverse | X | Off |
| On | Not Set | On | 0 | ^#1Not Reverse | Not Met | Off |
| On | Not Set | On | 0 | ^#1Not Reverse | Met | On |
Note:
1.Appropriate gear signal shall be used based on MT/AT/AMT
1. Reverse Use case:
When Forward gear is re-selected and forward motion commences (>10 km/h (Diag RW Seatbelt FW Signal Resume), the Final Signal must resume again (Note: Only Elapsed duration chime shall Play)
3.Whenever there is a change in ‘Rear Chime SBR St = On’ ‘from Off, the ‘ Rear SeatBelt Final Condition St’ shall be evaluated from start and the chime shall be retriggered when ‘Rear Seat Belt Final Condition St =TRUE’.
4.IC2_100: SEAT_BELT_REMAINDER_FL_REAR: Shall be Set to 1 when Rear chime is played for 35 Sec (Diag RW SBR Final Chime Duration)
It shall change 1->0 when reverse gear engaged. It will send 1 again for remaining period once more than 10km/h speed met.
- Variant: S220, W502
- Stakeholder Requirement State: In Review
- System Requirement State: Draft
- Software Requirement State: Draft
- Primary Discipline: SW
- Requirement Type: Functional

###### MS22029826-73379: S237 (Information)
| IgnMode | LVDS/HVSD Flag | Rear Chime SBR St | CAN Signal missing for ^#1Gear | VCU10_100: GEAR_ACTUAL_VCU | Rear Seat Belt Final Condition St | Rear Chime Logic |
| --- | --- | --- | --- | --- | --- | --- |
| Off | X | X | X | X | X | Off |
| On | Set | X | X | X | X | Off |
| On | Not set | Off | X | X | X | Off |
| On | Not set | On | 1 | X | X | Off |
| On | Not Set | On | 0 | Reverse | X | Off |
| On | Not Set | On | 0 | ^#1Not Reverse | Not Met | Off |
| On | Not Set | On | 0 | ^#1Not Reverse | Met | On |
Note:
1. Reverse Use case:
When Forward gear is re-selected and forward motion commences (>10 km/h (Diag RW
Seatbelt FW Signal Resume), the Final Signal must resume again (Note: Only Elapsed duration chime shall Play)
2.Whenever there is a change in ‘Rear Chime SBR St = On’ ‘from Off, the ‘ Rear SeatBelt
Final Condition St’ shall be evaluated from start and the chime shall be retriggered when
‘Rear Seat Belt Final Condition St =TRUE’.
3.IC2_100: SEAT_BELT_REMAINDER_FL_REAR: Shall be Set to 1 when Rear chime is played
for 35 Sec (Diag RW SBR Final Chime Duration)
It shall change 1->0 when reverse gear engaged. It will send 1 again for remaining period
once more than 10km/h speed met.
- Stakeholder Requirement State: In Review
- System Requirement State: Draft
- Software Requirement State: Draft
- Primary Discipline: SW
- Requirement Type: Functional

###### MS22029826-64032: Drv /Psgr SeatBelt Chime Logic (Information)
| Drv /Psgr SeatBelt Chime Logic | Rear SeatBelt Chime Logic | Seatbelt Chime Functional logic |
| --- | --- | --- |
| Off | Off | Off |
| On | Off | Chime play for 95sec (Diag RW SBR Final Chime Duration) |
| Off | On | Chime play for 35sec (Diag RW Rear SBR Final Chime Duration) |
| On | On | # Chime play for FOR REQUIRED duration |
Note: In case both DRV AND REAR ARE ON chime needs play for required calibration
- Variant: S220, S237, W502
- Stakeholder Requirement State: In Review
- System Requirement State: Draft
- Software Requirement State: Draft
- Primary Discipline: SW
- Requirement Type: Functional

###### MS22029826-64034 (Information)
Ex:
1.Drv/Psgr unbuckled -> Chime to Play 95 sec. chime started and 80 sec is completed.
2.Rear unbuckled->chime to play for 35 sec.
3. Total duration of chime play is 80+35sec =115s (This meets 95 sec +35 sec)
In case unbuckle of any seatbelt in between Timer shall be restarted
- Variant: S220, S237, W502
- Stakeholder Requirement State: In Review
- System Requirement State: Draft
- Software Requirement State: Draft
- Primary Discipline: SW
- Requirement Type: Functional

###### MS22029826-64036 (Information)
--When the trigger 'SeatBelt Chime Functional Logic == TRUE' is met, the chime 'Seat Belt warning - Part1'
shall be triggered immediately whereas the other chime 'Seat Belt warning - Part2' shall be triggered with
a specific delay of 12sec (equals the duration of Part1 WAV duration x no. of cycles).
This is done such that Part2 chime shall ideally playback right after elapse of Part1 chime/
The priority shall be defined such that Part1 is higher priority than Part2 so that Part1 always plays first
before Part2--
- Variant: S220, S237, W502
- Stakeholder Requirement State: In Review
- System Requirement State: Draft
- Software Requirement State: Draft
- Primary Discipline: SW
- Requirement Type: Functional

##### MS22029826-73372: CAN Tx -Based on CO - Driver /Rear Seatbelt logic (Information)
- Variant: S220, S237, W502
- Stakeholder Requirement State: In Review
- System Requirement State: Draft
- Software Requirement State: Draft
- Primary Discipline: TBD
- Requirement Type: TBD

###### MS22029826-73373: CAN Tx Based on CODRIVER/ REAR (System Requirement)
CAN Tx Based on CODRIVER/ REAR
| FEATURE_CODE_CODRIVER_SBR_TT_CONFIG | Diag RW Rear PSGR SeatBelt Chime Enable | PSGR SeatBelt Chime Logic | Rear SeatBelt Chime Logic | IC2_200:SEAT_BELT_REMAINDER_FL_REAR |
| --- | --- | --- | --- | --- |
| 0 | X | OFF | X | 0 |
| 0 | X | ON | X | 1 |
| 1 | 0 | X | X | 0 |
| 1 | 1 | X | OFF | 0 |
| 1 | 1 | X | ON | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-73381: . (Information)
When SBR chime is being played in a channel, no other chime shall be played although the other channel is free.
Once played, SBR chime shall NOT be played again the same IGN cycle unless there is a change in Buckle status.
In case of change from Buckle > Unbuckle, the final condition shall be set to False and re-evaluated again from start.
- Variant: S220, S237, W502
- Stakeholder Requirement State: In Review
- System Requirement State: Draft
- Software Requirement State: Draft
- Primary Discipline: SW
- Requirement Type: Functional

### MS22029826-73383: Rear Passenger Seat Belt Chime (Heading)
- Variant: S237
- Stakeholder Requirement State: In Review
- System Requirement State: Draft
- Software Requirement State: Draft
- Primary Discipline: TBD
- Requirement Type: TBD

#### MS22029826-73384: Input Requirements (Heading)
- Variant: S237
- Stakeholder Requirement State: In Review
- System Requirement State: Draft
- Software Requirement State: Draft
- Primary Discipline: TBD
- Requirement Type: TBD

##### MS22029826-73387: IgnMode (Value: On, Off) (System Requirement)
- Variant: S237
- Stakeholder Requirement State: In Review
- System Requirement State: Draft
- Software Requirement State: Draft
- Primary Discipline: TBD
- Requirement Type: TBD

##### MS22029826-73390: LVSD/HVSD Flag (Value: Not Set, Set) (System Requirement)
- Variant: S237
- Stakeholder Requirement State: In Review
- System Requirement State: Draft
- Software Requirement State: Draft
- Primary Discipline: TBD
- Requirement Type: TBD

##### MS22029826-73391: VAR_CODING_MAHINDRA_BODY_FUNCTION_MODULE (Value: 0-Not Present, 1-Present) (System Requirement)
- Variant: S237
- Stakeholder Requirement State: In Review
- System Requirement State: Draft
- Software Requirement State: Draft
- Primary Discipline: TBD
- Requirement Type: TBD

##### MS22029826-73392 (System Requirement)
MBFM9_500: PSGR_REAR_SEAT_BELT (Value:0x0-0x3F)
BIT 0:- Rear Left Passenger(0-Not Buckled,1-Buckled)
BIT 1:- Rear Middle Passenger(0-Not Buckled,1-Buckled)
BIT 2:- Rear Right Passenger(0-Not Buckled,1-Buckled)
BIT 3:- Rear 3rd RowLeft Passenger(0-Not Buckled,1-Buckled)
BIT 4:- Rear 3rd Row Middle Passenger(0-Not Buckled,1-Buckled)
BIT 5:- Rear 3rd Row Right Passenger(0-Not Buckled,1-Buckled
- Variant: S237
- Stakeholder Requirement State: In Review
- System Requirement State: Draft
- Software Requirement State: Draft
- Primary Discipline: TBD
- Requirement Type: TBD

##### MS22029826-73393 (System Requirement)
VCU10_100: GEAR_ACTUAL_VCU (Values: 0x0=neutral/default, 0x1=Forward mode,
0x2=Reverse Mode, 0x3=Low mode, 0x4=Reserved, 0x5= Park Mode, 0x6= Reserved,
0x7= Signal invalid)
- Variant: S237
- Stakeholder Requirement State: In Review
- System Requirement State: Draft
- Software Requirement State: Draft
- Primary Discipline: TBD
- Requirement Type: TBD

##### MS22029826-73394: SeatBelt Final Condition St(Refer Seat Belt Chime Section (System Requirement)
- Variant: S237
- Stakeholder Requirement State: In Review
- System Requirement State: Draft
- Software Requirement State: Draft
- Primary Discipline: TBD
- Requirement Type: TBD

##### MS22029826-73395: Diag RW Rear PSGR SeatBelt Chime Enable (Value: 0-Disable, 1-Enable) (System Requirement)
- Variant: S237
- Stakeholder Requirement State: In Review
- System Requirement State: Draft
- Software Requirement State: Draft
- Primary Discipline: TBD
- Requirement Type: TBD

#### MS22029826-73385: Output Requirements (Heading)
- Variant: S237
- Stakeholder Requirement State: In Review
- System Requirement State: Draft
- Software Requirement State: Draft
- Primary Discipline: TBD
- Requirement Type: TBD

##### MS22029826-73388: Rear PSGR SeatBelt Chime Functional Logic (Value: Off, On) (System Requirement)
- Variant: S237
- Stakeholder Requirement State: In Review
- System Requirement State: Draft
- Software Requirement State: Draft
- Primary Discipline: TBD
- Requirement Type: TBD

#### MS22029826-73386: Performance Requirements (Heading)
- Variant: S237
- Stakeholder Requirement State: In Review
- System Requirement State: Draft
- Software Requirement State: Draft
- Primary Discipline: TBD
- Requirement Type: TBD

##### MS22029826-73389: Table- Rear PSGR Seat Belt Chime Configuration (System Requirement)
| VAR_CODING_MAHINDRA_BODY_FUNCTION_MODULE | Diag RW Rear PSGRSeatBelt Chime Enable | Rear PSGR SeatBelt Chime Configuration |
| --- | --- | --- |
| 0 | X | 0 |
| 1 | 0 | 0 |
| 1 | 1 | 1 |
- Variant: S237
- Stakeholder Requirement State: In Review
- System Requirement State: Draft
- Software Requirement State: Draft
- Primary Discipline: TBD
- Requirement Type: TBD

##### MS22029826-73396: Table- Rear PSGR Seat Belt Chime Functional Logic (System Requirement)
| IgnM ode | LVSD/ HVSD Flag | Rear PSGR SeatBel t Chime Configu ration | CAN Missing or Never Received | VCU10_100: GEAR_ACTUAL_VCU | Seat Belt Final Condition St | MBFM9_500: PSGR_REAR_SEAT_BELT | Rear PSGR Seat Belt Chime Functiona Logic |
| --- | --- | --- | --- | --- | --- | --- | --- |
| Off | X | X | X | X | X | X | Off |
| On | Set | X | X | X | X | X | Off |
| On | Not Set | 0 | X | X | X | X | Off |
| On | Not Set | 1 | 1 | X | X | X | Off |
| On | Not Set | 1 | 0 | Reverse | X | X | Off |
| On | Not Set | 1 | 0 | Not Reverse | No | Off | Off |
| On | Not Set | 1 | 0 | Not Reverse | Yes | =0x2F/0x3F (4th bit is Dont care) | Off |
| On | Not Set | 1 | 0 | Not Reverse | Yes | !=0x2F | On |
Note :
1.Seat Belt Final Condition st check need to be independent for seat belt and Rear passenger Seat belt chime Once played, Rear SBR chime shall NOT be played again the same IGN cycle unless there is a change in Buckle status.
In case of change from Buckle > Unbuckle, the final condition shall be set to False and re-evaluated again from start.
Reverse use case:
Once RSBR chime is triggered and currently playing --- Reverse->Not Reverse shall re-trigger chime again from start
If RSBR chime is already played in that ignition cycle ---- Reverse->Not Reverse chime shall not be played unless there is change in Buckle status
- Variant: S237
- Stakeholder Requirement State: In Review
- System Requirement State: Draft
- Software Requirement State: Draft
- Primary Discipline: TBD
- Requirement Type: TBD

##### MS22029826-73398 (System Requirement)
When the trigger 'Rear Seat Belt Chime Functional Logic == TRUE' is met, the chime 'Rear Seat Belt warning - Part1' shall be triggered immediately whereas the other chime 'Rear Seat Belt warning - Part2' shall be triggered with a specific delay of 12sec (equals the duration of Part1 WAV duration x no. of cycles).
This is done such that Part2 chime shall ideally playback right after elapse of Part1 chime/ The priority shall be defined such that Part1 is higher priority than Part2 so that Part1 always plays first before Part2.
- Variant: S237
- Stakeholder Requirement State: In Review
- System Requirement State: Draft
- Software Requirement State: Draft
- Primary Discipline: TBD
- Requirement Type: TBD

### MS22029826-44165: Park Brake Engaged Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52441: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60555: IgnMode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60557: LVSD/HVSD Flag (Value: Set, Not Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60559: ParkBrakeSt Hw Input (Value: 0-On, 1-Off) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60561: VAR_CODING_ELECTRONIC_STABILITY_CONTROL (Value: 0-Not Present, 1-Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60563: VAR_CODING_ANTILOCK_BRAKING_SYSTEM (Value: 0-Not Present, 1-Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60565: FEATURE_CODE_EPB_TT (0-CAN,1-HW) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60567: ESC14_500:PARK_BRK_ACTIVE_STS(Value:0x0 -Applied/Default,0x1-Released,0x2-In-progress 0x3-Invalid) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60569: Diag RW ParkBrake Chime Enable (Value: 0-Disabled, 1-Enabled) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60571: Vehicle Moving St (Value: Yes, No) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52443: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60573: ParkBrake Chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52445: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60575: Table - Park Brake Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64038: Park Brake/EPB TT Configuration (System Requirement)
| Park Brake/EPB TT Configuration | Diag RW ParkBrake Chime Enable | ParkBrake Chime Configuration |
| --- | --- | --- |
| X | 0 | 0 |
| CAN | 1 | CAN |
| HW | 1 | HW |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60577: Table - Park Brake Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64040: IgnMode (System Requirement)
| IgnMode | LVSD/HVSD Flag | ParkBrake Chime Configuration | ParkBrakeSt Hw Input | CAN Signal Missing/ Never Received | ESC14_500: PARK_BRK_ACTIVE_STS | Vehicle Moving St | ParkBrake Chime Functional Logic |
| --- | --- | --- | --- | --- | --- | --- | --- |
| Off | X | X | X | X | X | X | Off |
| On | Set | X | X | X | X | X | Off |
| On | Not Set | 0 | X | X | X | X | Off |
| On | Not Set | HW | 1 | X | X | X | Off |
| On | Not Set | HW | 0 | X | X | Yes | On |
| On | Not Set | HW | 0 | X | X | No | Off |
| On | Not Set | CAN | X | 1 | X | X | Off |
| On | Not Set | CAN | X | 0 | 0x0 | Yes | On |
| On | Not Set | CAN | X | 0 | 0x0 | No | Off |
| On | Not Set | CAN | X | 0 | 0x1,0x2, 0x3 | X | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44167: PKE Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52447: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60579: IgnMode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60580: LVSD/HVSD Flag (Value: Set, Not Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60582: VAR_CODING_PASSIVE_KEY_ENTRY (Value: 0-Not Present, 1-Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60583: VAR_CODING_IMMOBILIZER_CONTROL_UNIT_A (Value: 0-Not Present, 1-Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60585: PKE2_200(0x440):KEY_FOB_INSD_WRN (Value:1-Warning On ,0 -Warning Off ) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60587: PKE2_200(0x440):KEY_NOT_VEH_WRN (Value:1-Warning On ,0 -Warning Off ) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60589: Diag RW PKE Keyout Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60591: Diag RW PKE FOB Key Reminder Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52449: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60592: PKE Keyout Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60594: PKE FOB Key Reminder Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52451: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60241: Table - PKE Key Out Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64042: VAR_CODING_IMMOBILIZER_CONTROL_UNIT_A (System Requirement)
|  | VAR_CODING_IMMOBILIZER_CONTROL_UNIT_A | VAR_CODING_PASSIVE_KEYLESS_ENTRY | Diag RW PKE Keyout Chime Enable | PKE Key Out Chime configuration |
| --- | --- | --- | --- | --- |
| 1 | 0 | 0 | X | 0 |
| 2 | X | X | 0 | 0 |
| 3 | 1 | 0 | 1 | 0 |
| 4 | 0 | 1 | 1 | 1 |
| 5 | 1 | 1 | 1 | 0 (Log Var Code Error DTC) |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60242: Table - PKE FOB Key Reminder Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64044: VAR_CODING_IMMOBILIZER_CONTROL_UNIT_A (System Requirement)
|  | VAR_CODING_IMMOBILIZER_CONTROL_UNIT_A | VAR_CODING_PASSIVE_KEYLESS_ENTRY | Diag RW PKE FOB Key Reminder Chime Enable | PKE FOB Key Reminder Configuration |
| --- | --- | --- | --- | --- |
| 1 | 0 | 0 | X | 0 |
| 2 | X | X | 0 | 0 |
| 3 | 1 | 0 | 1 | 0 |
| 4 | 0 | 1 | 1 | 1 |
| 5 | 1 | 1 | 1 | 0 (Log Var Code Error DTC) |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60244: Table - PKE Key Out Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64046: LVSD/HVSD Flag (System Requirement)
| LVSD/HVSD Flag | PKE Keyout Chime Configuration | CAN Missing or Never Received | PKE2_200(0x440): KEY_NOT_VEH_WRN | PKE Keyout Chime Functional Logic |
| --- | --- | --- | --- | --- |
| Set | X | X | X | Off |
| Not Set | 0 | X | X | Off |
| Not Set | 1 | 1 | X | Off |
| Not Set | 1 | 0 | 1 | On |
| Not Set | 1 | 0 | 0 | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60246: Table - PKE FOB Key Reminder Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64048: LVSD/HVSD Flag (System Requirement)
| LVSD/HVSD Flag | PKE FOB Key Reminder Chime Configuration | CAN Missing or Never Received | PKE2_200(0x440): KEY_FOB_INSD_WRN | PKE FOB Key Reminder Chime Functional Logic |
| --- | --- | --- | --- | --- |
| Set | X | X | X | Off |
| Not Set | 0 | X | X | Off |
| Not Set | 1 | 1 | X | Off |
| Not Set | 1 | 0 | 1 | On |
| Not Set | 1 | 0 | 0 | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44169: Wireless Charging Forgotten Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52453: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60248: IgnMode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60249: LVSD/HVSD Flag (Value: Set, Not Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60251: VAR_CODING_WIRELESS_CHARGE (Value: 0-Not Present, 1-Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60253: FEATURE_CODE_WIRELESS_CHARGE (Value: 0-Not Present, 1-Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60255: Diag RW WIRELESS CHARGE Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60256: WLC3_2000: TIME_TO_CHARGE (Value: 0x0 -Full Charge, 0xF1 -No device / Default , 0xF2 - Forgotten device , 0xFF- Invalid) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52455: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60258: Wireless Charging Chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52458: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60260: Table - Wireless Charging Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64050: VAR_CODING_ (System Requirement)
| VAR_CODING_ WIRELESS_CHARGE | FEATURE_CODE_ WIRELESS_CHARGE | Diag RW WIRELESS CHARGE Chime Enable | Wireless Charging Chime Configuration |
| --- | --- | --- | --- |
| 0 | X | X | 0 |
| 1 | 0 | X | 0 |
| 1 | 1 | 0 | 0 |
| 1 | 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60261: Table - Wireless Charging Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64051: Ign Mode (System Requirement)
| Ign Mode | LVSD / HVSD Flag | Wireless Charging Chime Configuration | CAN Missing / Never received | WLC3_2000: TIME_TO_CHARGE | Wireless Charging Chime Functional Logic |
| --- | --- | --- | --- | --- | --- |
| On | X | X | X | X | Off |
| Off | Set | X | X | X | Off |
| Off | Not set | 0 | X | X | Off |
| Off | Not set | 1 | 1 | X | Off |
| Off | Not set | 1 | 0 | !0xF2 | Off |
| Off | Not set | 1 | 0 | 0xF2 | On |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44171: Sunroof open Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52460: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60263: Ign Mode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60265: LVSD/ HVSD Flag (Value: Not set, Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60267: VAR_CODING_MAHINDRA_BODY_FUNCTION_MODULE (Value: 0- Not present, 1- Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60268: MBFM9_500:STS_SRS_POS (Value: 0x0- Fully Closed, 0x1- Partial Open, 0x2- Fully Open, 0x3-Unable to detect) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60270: Diag RW Check Sunroof Chime Enable (Value:0- Disable, 1- Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60272: Driver Door St(Refer Check sunroof alert section) (Information)
- Variant: S220, S237, W502
- Stakeholder Requirement State: In Review
- System Requirement State: Draft
- Software Requirement State: Draft
- Primary Discipline: SW
- Requirement Type: Functional

#### MS22029826-52462: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60274: Check Sunroof Chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52464: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60275: Table- Check Sunroof Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64053: VAR_CODING_ (System Requirement)
| VAR_CODING_ MAHINDRA_BODY_ FUNCTION_MODULE | Diag RW Check Sunroof Chime Enable | Check Sunroof Chime Configuration |
| --- | --- | --- |
| 0 | X | 0 |
| 1 | 0 | 0 |
| 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60277: Table- Check Sunroof Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64055: gn Mode (System Requirement)
| Ign Mode | LVSD / HVSD Flag | Check Sunroof Chime Configuration |  | CAN Missing / Never received | MBFM9_500 STS_SRF_POS | Driver Door St | Check Sunroof Chime Functional Logic |
| --- | --- | --- | --- | --- | --- | --- | --- |
| On | X | X |  | X | X | X | Off |
| Off | Set | X |  | X | X | X | Off |
| Off | Not set | 0 |  | X | X | X | Off |
| Off | Not set | 1 |  | 1 | X | X | Off |
| Off | Not set | 1 |  | 0 | 0x0/0x3 | X | Off |
| Off | Not set | 1 |  | 0 | 0x1/0x2 | FALSE | Off |
| Off | Not set | 1 |  | 0 | 0x1/0x2 | True | On |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44173: DriverDrowsyDetection Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52467: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60279: Ign Mode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60281: LVSD/ HVSD Flag (Value: Not set, Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60282: VAR_CODING_MAHINDRA_BODY_FUNCTION_MODULE (Value: 0- Not present, 1- Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60284: VAR_CODING_ANTILOCK_BRAKING_SYSTEM (Value: 0-Not Present, 1-Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60286: FEATURE_CODE_DDD_FUNCTION (Value: 0-Not Present, 1-Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60287: ESC13_100:STS_DDD (Value: 0x0-Not Active, 0x1-Active, 0x2-Reserved, 0x3-Malfunction) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60289: Diag RW DDD Chime Enable (Value: 0-Disabled, 1-Enabled) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60291: Diag RW DDD Warn Enable (Value: 0-Disabled, 1-Enabled) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60293: Diag RW Snooze Timer (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60295: DDD HMI Req (Value:0-No Acknowledge,1-Acknowledge received) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60297: DDD_SW_IC (0X0-Enable, 0x1-Disable) Refer Setting req ID:2615579 (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52469: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60299: DDD Chime Functional Logic(Value:0-On, 1-Off) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52471: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60301: Table- DDD Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64057: VAR_CODING_ELECTRONIC_STABILITY_CONTROL (System Requirement)
|  | VAR_CODING_ELECTRONIC_STABILITY_CONTROL | VAR_CODING_ANTILOCK_BRAKING_SYSTEM | FEATURE_CODE_DDD_FUNCTION | Diag RW DDD Warn Enable | Diag RW DDD ChimeEnable | DDD chime Configuration |
| --- | --- | --- | --- | --- | --- | --- |
| 1 | 0 | 0 | 0 | X | X | 0 |
| 2 | 1 | 1 | X | X | X | 0 DTC Shall be logged |
| 3 | X | X | X | X | 0 | 0 |
| 4 | X | X | 0 | 1 | 1 | 0 |
| 5 | X | X | 1 | 0 | 1 | 0 |
| 6 | 0 | 1 | 1 | 1 | 1 | 1 |
| 7 | 1 | 0 | 1 | 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60303: Table- DDD Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64059 (System Requirement)
If DDD setting(DDD_SW_IC) is disabled, chime shall not be played
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- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44175: Message Notification Chime (Heading)
- Variant: S220, S237, W502
- Stakeholder Requirement State: In Review
- System Requirement State: Draft
- Software Requirement State: Draft
- Primary Discipline: SW
- Requirement Type: Functional

#### MS22029826-52472: Input Requirements (Heading)
- Variant: S220, S237, W502
- Stakeholder Requirement State: In Review
- System Requirement State: Draft
- Software Requirement State: Draft
- Primary Discipline: SW
- Requirement Type: Functional

##### MS22029826-60305: Ign Mode (Value: On, Off) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60307: LVSD / HVSD Flag (Value: Not set, Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60309: Current Display (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60311: Diag RW Message Notification Chime Enable (Value:0- Disable, 1- Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52475: Output Requirements (Heading)
- Variant: S220, S237, W502
- Stakeholder Requirement State: In Review
- System Requirement State: Draft
- Software Requirement State: Draft
- Primary Discipline: SW
- Requirement Type: Functional

##### MS22029826-60312: Message Notification Chime Functional Logic (Value: On, Off) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52477: Performance Requirements (Heading)
- Variant: S220, S237, W502
- Stakeholder Requirement State: In Review
- System Requirement State: Draft
- Software Requirement State: Draft
- Primary Discipline: SW
- Requirement Type: Functional

##### MS22029826-60315: Table- Message Notificaion Chime Configuration (Heading)
- Variant: S220, S237, W502
- Stakeholder Requirement State: In Review
- System Requirement State: Draft
- Software Requirement State: Draft
- Primary Discipline: SW
- Requirement Type: Functional

###### MS22029826-64061: Diag RW Message Notification Chime Enable (System Requirement)
| Diag RW Message Notification Chime Enable | Message Notification Chime configuration |
| --- | --- |
| 0 | 0 |
| 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60317: Table- Message Notificaion Chime Functional Logic (Heading)
- Variant: S220, S237, W502
- Stakeholder Requirement State: In Review
- System Requirement State: Draft
- Software Requirement State: Draft
- Primary Discipline: SW
- Requirement Type: Functional

###### MS22029826-64063: IgnMode (System Requirement)
| IgnMode | LVSD/HVSD Flag | Message Notification Chime configuration | Current Display | Message Notification Chime Functional Logic |
| --- | --- | --- | --- | --- |
| Off | X | X | X | Off |
| On | Set | X | X | Off |
| On | Not Set | 0 | X | Off |
| On | Not Set | 1 | Check ESC Warning \|\| ABS Malfunction Warning \|\| Check EBD Warning\|\| Service Reminder Warning\|\| Check Engine Warning | On |
| On | Not Set | 1 | Not (Check ESC Warning && ABS Malfunction Warning && Check EBD Warning&& Service Reminder Warning && Check Engine Warning) | Off |
- Variant: S220, S220_SB_ADP_W601-V1, S220_SB_ADP_W601-V2, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-84183: IgnMode (System Requirement)
| IgnMode | LVSD/HVSD Flag | Message Notification Chime configuration | Current Display | Message Notification Chime Functional Logic |
| --- | --- | --- | --- | --- |
| Off | X | X | X | Off |
| On | Set | X | X | Off |
| On | Not Set | 0 | X | Off |
| On/Off | Not Set | 1 | Check ESC Warning \|\| ABS Malfunction Warning \|\| Check EBD Warning\|\| Service Reminder Warning\|\| Flap Alert | On |
| On/Off | Not Set | 1 | Not (Check ESC Warning && ABS Malfunction Warning && Check EBD Warning&& Service Reminder Warning && Flap Alert) | Off |
- Variant: S237
- Stakeholder Requirement State: In Review
- System Requirement State: Draft
- Software Requirement State: Draft
- Primary Discipline: SW
- Requirement Type: Functional

### MS22029826-44177: Key Fob Memory (Heading)
- Variant: S220, S237, W502
- Stakeholder Requirement State: In Review
- System Requirement State: Draft
- Software Requirement State: Draft
- Primary Discipline: TBD
- Requirement Type: TBD

#### MS22029826-52479: Input Requirements (Heading)
- Variant: S220, S237, W502
- Stakeholder Requirement State: In Review
- System Requirement State: Draft
- Software Requirement State: Draft
- Primary Discipline: TBD
- Requirement Type: TBD

##### MS22029826-60319: IgnMode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60321: LVSD/HVSD Flag (Value: Set, Not Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60323: SCM1_500: POWER_SET_MEMORY_RECALL(0X0-Default Value,0x1-Position 1,0x2- Position 2, Position 3) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60325: SCM1_500: POWER_SET_MEMORY_STORE(0X0-Default Value,0x1-Position 1,0x2- Position 2, Position 3) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60327: SCM1_500:SCM_MEMORY_STS(Value:0x0-Default , 0x1-Failed , 0x2-Succeed , 0x3-Reserved) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60329: VAR_CODING_SCM (Value: 0-Not Present, 1-Present) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60331: Diag RW Key FOB Memory 1 Chime Enable (Value: 0-Disabled, 1-Enabled) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60181: Diag RW Key FOB Memory 2 Chime Enable (Value: 0-Disabled, 1-Enabled) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52481: Output Requirements (Heading)
- Variant: S220, S237, W502
- Stakeholder Requirement State: In Review
- System Requirement State: Draft
- Software Requirement State: Draft
- Primary Discipline: TBD
- Requirement Type: TBD

##### MS22029826-60184: Power Set memory Recall Chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60186: Power Set memory Store Chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52483: Performance Requirements (Heading)
- Variant: S220, S237, W502
- Stakeholder Requirement State: In Review
- System Requirement State: Draft
- Software Requirement State: Draft
- Primary Discipline: TBD
- Requirement Type: TBD

##### MS22029826-60188: Table - Key FOB Memory 1 Recall Chime Configuration (Heading)
- Variant: S220, S237, W502
- Stakeholder Requirement State: In Review
- System Requirement State: Draft
- Software Requirement State: Draft
- Primary Discipline: TBD
- Requirement Type: TBD

###### MS22029826-64065: VAR_CODING_SCM (System Requirement)
| VAR_CODING_SCM | Diag RW Key FOB Memory 1 Chime Enable | Key Fob Memory 1 Recall Chime Configuration |
| --- | --- | --- |
| 0 | X | 0 |
| 1 | 0 | 0 |
| 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60190: Table - Key FOB Memory 2 Store Chime Configuration (Heading)
- Variant: S220, S237, W502
- Stakeholder Requirement State: In Review
- System Requirement State: Draft
- Software Requirement State: Draft
- Primary Discipline: TBD
- Requirement Type: TBD

###### MS22029826-64067: VAR_CODING_SCM (System Requirement)
| VAR_CODING_SCM | Diag RW Key FOB Memory 2 Chime Enable | Key Fob Memory 2 Store Chime Configuration |
| --- | --- | --- |
| 0 | X | 0 |
| 1 | 0 | 0 |
| 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60192: Table - Key Fob Memory 1 Recall Chime Functional Logic (Heading)
- Variant: S220, S237, W502
- Stakeholder Requirement State: In Review
- System Requirement State: Draft
- Software Requirement State: Draft
- Primary Discipline: TBD
- Requirement Type: TBD

###### MS22029826-64069: Ign Mode (System Requirement)
| Ign Mode | LVSD / HVSD Flag | Key Fob Memory 1 recall Chime Configuration | CAN Missing / Never received | SCM1_500: POWER_SET_MEMORY_RECALL | SCM1_500: SCM_MEMORY_STS | Key Fob Memory 1 Recall Chime Functional Logic |
| --- | --- | --- | --- | --- | --- | --- |
| Off | X | X | X | X | X | Off |
| On | Set | X | X | X | X | Off |
| On | Not set | 0 | X | X | X | Off |
| On | Not set | 1 | 1 | X | X | Off |
| On | Not set | 1 | 0 | 0x0 | X | Off |
| On | Not set | 1 | 0 | 0x1/0x2/0x3 | !=0x2 | Off |
| On | Not set | 1 | 0 | 0x1/0x2/0x3 | =0x2 | On |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60194: Table - Key Fob Memory 2 Store Chime Functional Logic (Heading)
- Variant: S220, S237, W502
- Stakeholder Requirement State: In Review
- System Requirement State: Draft
- Software Requirement State: Draft
- Primary Discipline: TBD
- Requirement Type: TBD

###### MS22029826-64070: Ign Mode (System Requirement)
| Ign Mode | LVSD / HVSD Flag | Key Fob Memory 2 Store Chime Configuration | CAN Missing / Never received | SCM1_500: POWER_SET_MEMORY_STORE | SCM1_500: SCM_MEMORY_STS | Key Fob Memory 2 Store Chime Functional Logic |
| --- | --- | --- | --- | --- | --- | --- |
| Off | X | X | X | X | X | Off |
| On | Set | X | X | X | X | Off |
| On | Not set | 0 | X | X | X | Off |
| On | Not set | 1 | 1 | X | X | Off |
| On | Not set | 1 | 0 | 0x0 | X | Off |
| On | Not set | 1 | 0 | 0x1/0x2/0x3 | !=0x2 | Off |
| On | Not set | 1 | 0 | 0x1/0x2/0x3 | =0x2 | On |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44179: APA Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52486: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60196: Ign Mode (Value: On, Off) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60198: LVSD / HVSD Flag (Value: Not set, Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60199: RPAS Activation condition (Refer Alert Section) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60201: APA2_50(0X3A0): FPAS_SPAS_ACTIVE_STS (Value:0X0 - Not Active/Default, 0x1 -Active) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60203: Diag RW APA Wrn Lvl Dist 1 (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60205: Diag RW APA Wrn Lvl Dist 2 (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60207: Diag RW APA Wrn Lvl Dist 3 (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60209: Diag RW APA Wrn Lvl Dist 4 (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60211: Diag RW APA Side Wrn Lvl Dist 1 (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60213: Diag RW APA Side Wrn Lvl Dist 2 (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60215: Diag RW APA Side Wrn Lvl Dist 3 (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60217: APA2_50(0X3A0):FRONT_MIN_DIST(Value:0x0 -Valid Dist(0x0 to 0xFA),0xFF - Default Value, 0xFB -Reserved (0xFB to 0xFE)) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60219: APA2_50(0X3A0):REAR_MIN_DIST(Value:0x0 -Valid Dist(0x0 to 0xFA),0xFF - Default Value, 0xFB -Reserved (0xFB to 0xFE)) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60221: APA3_50(0X3A1):LEFT_MIN_DIST(Value:0x0 -Valid Dist(0x0 to 0xFA),0xFF - Default Value, 0xFB -Reserved (0xFB to 0xFE)) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60223: APA3_50(0X3A1):RIGHT_MIN_DIST(Value:0x0 -Valid Dist(0x0 to 0xFA),0xFF - Default Value, 0xFB -Reserved (0xFB to 0xFE)) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60225: APA4_50(0X3A2):FPAS_SW_STS(Value:0x0 -FPAS not Active, 0x1 -FPAS Active) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60227: Diag RW RPAS Self Check Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60229: Diag RW RPAS Error Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60231: Diag RW RPAS status Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60233: Diag RW FPAS status Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60236: Diag RW SPAS status Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60238: FEATURE_CODE_APA_IND (Values: 0-Disabled, 1-Enabled) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52488: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60239: RPAS Self Check Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60240: RPAS Fail Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60243: RPAS Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60245: FPAS Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60247: SPAS Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52490: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60250: Table –RPAS Status Chime Configuration (Heading)
- Variant: S220, S237, W502
- Stakeholder Requirement State: In Review
- System Requirement State: Draft
- Software Requirement State: Draft
- Primary Discipline: TBD
- Requirement Type: TBD

###### MS22029826-64072: VAR_CODING_APA (System Requirement)
| VAR_CODING_APA | FEATURE_CODE_APA_IND | Diag RW RPAS Status Chime Enable | RPAS Status Chime Configuration |
| --- | --- | --- | --- |
| 0 | X | X | 0 |
| 1 | 0 | X | 0 |
| 1 | 1 | 0 | 0 |
| 1 | 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60252: Table –FPAS Status Chime Configuration (Heading)
- Variant: S220, S237, W502
- Stakeholder Requirement State: In Review
- System Requirement State: Draft
- Software Requirement State: Draft
- Primary Discipline: TBD
- Requirement Type: TBD

###### MS22029826-64074: VAR_CODING_APA (System Requirement)
| VAR_CODING_APA | FEATURE_CODE_APA_IND | Diag RW FPAS Status Chime Enable | FPAS Status Chime Configuration |
| --- | --- | --- | --- |
| 0 | X | X | 0 |
| 1 | 0 | X | 0 |
| 1 | 1 | 0 | 0 |
| 1 | 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60254: Table –SPAS Status Chime Configuration (Heading)
- Variant: S220, S237, W502
- Stakeholder Requirement State: In Review
- System Requirement State: Draft
- Software Requirement State: Draft
- Primary Discipline: TBD
- Requirement Type: TBD

###### MS22029826-64076: VAR_CODING_APA (System Requirement)
| VAR_CODING_APA | FEATURE_CODE_APA_IND | Diag RW SPAS Status Chime Enable | S PAS Status Chime Configuration |
| --- | --- | --- | --- |
| 0 | X | X | 0 |
| 1 | 0 | X | 0 |
| 1 | 1 | 0 | 0 |
| 1 | 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60257: Table –RPAS Self check Chime Configuration (Heading)
- Variant: S220, S237, W502
- Stakeholder Requirement State: In Review
- System Requirement State: Draft
- Software Requirement State: Draft
- Primary Discipline: TBD
- Requirement Type: TBD

###### MS22029826-64077: VAR_CODING_APA (System Requirement)
| VAR_CODING_APA | FEATURE_CODE_APA_IND | Diag RW RPAS Self Check Chime Enable | RPAS Self Check Chime Configuration |
| --- | --- | --- | --- |
| 0 | X | X | 0 |
| 1 | 0 | X | 0 |
| 1 | 1 | 0 | 0 |
| 1 | 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60259: Table -RPAS Error Chime Configuration (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64071: VAR_CODING_APA (System Requirement)
| VAR_CODING_APA | FEATURE_CODE_APA_IND | Diag RW RPAS Error Chime Enable | RPAS Error Chime Configuration |
| --- | --- | --- | --- |
| 0 | X | X | 0 |
| 1 | 0 | X | 0 |
| 1 | 1 | 0 | 0 |
| 1 | 1 | 1 | 1 |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60262: Table -RPAS Error Chime Functional Logic (Heading)
- Variant: S220, S237, W502
- Stakeholder Requirement State: In Review
- System Requirement State: Draft
- Software Requirement State: Draft
- Primary Discipline: TBD
- Requirement Type: TBD

###### MS22029826-64073: Ign Mode (System Requirement)
| Ign Mode | LVSD/ HVSD | RPAS Error Chime Configuration | Trailer St | RPAS Activation condition | CAN Signal Missing or Never Received | APA2_50(0X3A0) xx - SEGEMENT (xx- RL&& RR&&RML&&RMR) | RPAS Error Chime Functional Logic |
| --- | --- | --- | --- | --- | --- | --- | --- |
| Off | X | X | X | X | X | X | Off |
| On | Set | X | X | X | X | X | Off |
| On | Not set | 0 | X | X | X | X | Off |
| On | Not set | 1 | 1 | X | X | X | Off |
| On | Not set | 1 | 0 | Off | X | X | Off |
| On | Not set | 1 | 0 | On | 1 | X | On |
| On | Not set | 1 | 0 | On | 0 | !=0xF | Off |
| On | Not set | 1 | 0 | On | 0 | =0xF | On |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60264: Table -RPAS Self Check Chime Functional Logic (Heading)
- Variant: S220, S237, W502
- Stakeholder Requirement State: In Review
- System Requirement State: Draft
- Software Requirement State: Draft
- Primary Discipline: TBD
- Requirement Type: TBD

###### MS22029826-64075: Ign Mode (System Requirement)
| Ign Mode | LVSD/ HVSD | RPAS Self Check Chime Configuration | Trailer St | RPAS Activation condition | CAN Signal Missing or Never Received | APA2_50(0X3A0) xx - SEGEMENT (xx- RL/RR/RML/RMR) | RPAS Self Check Chime Functional Logic |
| --- | --- | --- | --- | --- | --- | --- | --- |
| Off | X | X | X | X | X | X | Off |
| On | Set | X | X | X | X | X | Off |
| On | Not set | 0 | X | X | X | X | Off |
| On | Not set | 1 | 1 | X | X | X | Off |
| On | Not set | 1 | 0 | Off | X | X | Off |
| On | Not set | 1 | 0 | Off->On | 1 | X | Off |
| On | Not set | 1 | 0 | Off->On | 0 | !=0xF | On |
| On | Not set | 1 | 0 | Off->On | 0 | =0XF | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60266: Table -RPAS Status Chime Functional Logic (Heading)
- Variant: S220, S237, W502
- Stakeholder Requirement State: In Review
- System Requirement State: Draft
- Software Requirement State: Draft
- Primary Discipline: TBD
- Requirement Type: TBD

###### MS22029826-64078: Ign Mode (System Requirement)
| Ign Mode | LVSD/ HVSD | RPAS Status Chime Configuration | Trailer St | RPAS Activation condition | CAN Signal Missing or Never Received | APA2_50(0X3A0) REAR_MIN_DIST | RPAS Status Chime Functional Logic |
| --- | --- | --- | --- | --- | --- | --- | --- |
| Off | X | X | X | X | X | X | Off |
| On | Set | X | X | X | X | X | Off |
| On | Not set | 0 | X | X | X | X | Off |
| On | Not set | 1 | 1 | X | X | X | Off |
| On | Not set | 1 | 0 | Off | X | X | Off |
| On | Not set | 1 | 0 | On | 1 | X | Off |
| On | Not set | 1 | 0 | On | 0 | >=250 | Off |
| On | Not set | 1 | 0 | On | 0 | <= Diag RW APA Wrn Lvl Dist 1 | 1st Level of tone |
| On | Not set | 1 | 0 | On | 0 | > Diag RW APA Wrn Lvl Dist 1 to <= Diag RW APA Wrn Lvl Dist 2 | 2nd Level of tone |
| On | Not set | 1 | 0 | On | 0 | > Diag RW APA Wrn Lvl Dist 2 to <= Diag RW APA Wrn Lvl Dist 3 | 3rd Level of tone |
| On | Not set | 1 | 0 | On | 0 | > Diag RW APA Wrn Lvl Dist 3 to <= Diag RW APA Wrn Lvl Dist 4 | 4th Level of tone |
| On | Not set | 1 | 0 | On | 0 | > Diag RW APA Wrn Lvl Dist 4 | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60269: Table -FPAS Status Chime Functional Logic (Heading)
- Variant: S220, S237, W502
- Stakeholder Requirement State: In Review
- System Requirement State: Draft
- Software Requirement State: Draft
- Primary Discipline: TBD
- Requirement Type: TBD

###### MS22029826-64079: Ign Mode (System Requirement)
| Ign Mode | LVSD/ HVSD | FPAS Status Chime Configuration | CAN Signal Missing or Never Received | APA4_50(0X3A2): FPAS_SW_STS | APA2_50(0X3A0): FPAS_SPAS_ACTIVE_STSOR RPAS Activation condition | APA2_50(0X3A0) FRONT_MIN_DIST | FPAS StatusChime Functional Logic |
| --- | --- | --- | --- | --- | --- | --- | --- |
| Off | X | X | X | X | X | X | Off |
| On | Set | X | X | X | X | X | Off |
| On | Not set | 0 | X | X | X | X | Off |
| On | Not set | 1 | 1 | X | X | X | Off |
| On | Not set | 1 | 1 | 1 | X | X | Off |
| On | Not set | 1 | 0 | 0 | Off | X | Off |
| On | Not set | 1 | 0 | 0 | On | >=250 | Off |
| On | Not set | 1 | 0 | 0 | On | <= Diag RW APA Wrn Lvl Dist 1 | 1st Level of tone |
| On | Not set | 1 | 0 | 0 | On | > Diag RW APA Wrn Lvl Dist 1 to <= Diag RW APA Wrn Lvl Dist 2 | 2nd Level of tone |
| On | Not set | 1 | 0 | 0 | On | > Diag RW APA Wrn Lvl Dist 2 to <= Diag RW APA Wrn Lvl Dist 3 | 3rd Level of tone |
| On | Not set | 1 | 0 | 0 | On | > Diag RW APA Wrn Lvl Dist 3 to <= Diag RW APA Wrn Lvl Dist 4 | 4th Level of tone |
| On | Not set | 1 | 0 | 0 | On | > Diag RW APA Wrn Lvl Dist 4 | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60271: Table -SPAS Status Chime Functional Logic (Heading)
- Variant: S220, S237, W502
- Stakeholder Requirement State: In Review
- System Requirement State: Draft
- Software Requirement State: Draft
- Primary Discipline: TBD
- Requirement Type: TBD

###### MS22029826-64081: Ign Mode (System Requirement)
| Ign Mode | LVSD/ HVSD | SPAS Status Chime Configuration | CAN Signal Missing or Never Received | APA4_50(0X3A2): FPAS_SW_STS | APA2_50(0X3A0): FPAS_SPAS_ACTIVE_STSOR RPAS Activation condition | APA3_50(0X3A0) MIN (LEFT_MIN_DIST or RIGHT_MIN_DIST) | SPAS StatusChime Functional Logic |
| --- | --- | --- | --- | --- | --- | --- | --- |
| Off | X | X | X | X | X | X | Off |
| On | Set | X | X | X | X | X | Off |
| On | Not set | 0 | X | X | X | X | Off |
| On | Not set | 1 | 1 | X | X | X | Off |
| On | Not set | 1 | 0 | 1 | X | X | Off |
| On | Not set | 1 | 0 | 0 | Off | X | Off |
| On | Not set | 1 | 0 | 0 | On | >=250 | Off |
| On | Not set | 1 | 0 | 0 | On | <= Diag RW APA Side Wrn Lvl Dist 1 | 1st Level of tone |
| On | Not set | 1 | 0 | 0 | On | > Diag RW APA Side Wrn Lvl Dist 1 to <= Diag RW APA Wrn Lvl Dist 2 | 2nd Level of tone |
| On | Not set | 1 | 0 | 0 | On | > Diag RW APA Side Wrn Lvl Dist 2 to <= Diag RW APA Side Wrn Lvl Dist 3 | 3rd Level of tone |
| On | Not set | 1 | 0 | 0 | On | > Diag RW APA Side Wrn Lvl Dist 3 | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44181: AEB Collision Warning Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52493: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60273: Ign Mode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60276: AEB Configuration (Value: Not configured, Invalid, RADAR, CAMERA) -refer AEB OFF telltale section (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60278: FRM2_20: AEB_WRN_FRM (Value: 0x0-No warning/ Default, 0x1- 1st Warning, 0x2- 2nd warning, 0x3- 3rd Warning) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60280: FCM1_20: AEB_WRN_FCM (Value: 0x0-No warning/ Default, 0x1- 1st Warning, 0x2- 2nd warning, 0x3- 3rd Warning) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60283: Diag RW AEB Collision Warning1 Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-60285: Diag RW AEB Collision Warning2 Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63325: Diag RW AEB Collision Warning3 Chime Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52494: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63326: AEB Collision Warning Chime Functional Logic (Value: Off, On (Collision Warning1 Chime), On (Collision Warning2 Chime), On (Collision Warning3 Chime)) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52495: Performance Requirements (System Requirement)
- Variant: S220, S237, W502
- Stakeholder Requirement State: In Review
- System Requirement State: Draft
- Software Requirement State: Draft
- Primary Discipline: SW
- Requirement Type: Functional

##### MS22029826-63327: Table- AEB Collision Warning Chime Functional logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64084: Ign Mode (System Requirement)
| Ign Mode | LVSD /HVSD Flag | AEB Configuration | FRM2_20: AEB_WRN_FRM | FCM1_20: AEB_WRN_FCM | Diag RW AEB Collision Warning1 Chime Enable | Diag RW AEB Collision Warning2 Chime Enable | Diag RW AEB Collision Warning3 Chime Enable | AEB Collision Warning Chime Functional Logic |
| --- | --- | --- | --- | --- | --- | --- | --- | --- |
| Off | X | X | X | X | X | X | X | OFF |
| On | Set | X | X | X | X | X | X | OFF |
| On | Not Set | Invalid or not configured | X | X | X | X | X | OFF |
| On | Not Set | RADAR | 0x0 | X | X | X | X | OFF |
| On | Not Set | RADAR | 0x0->0x1 | X | 0 | X | X | OFF |
| On | Not Set | RADAR | 0x0->0x1 | X | 1 | X | X | ON (Collision Warning1 Chime) |
| On | Not Set | RADAR | <0x2->0x2 | X | X | 0 | X | OFF |
| On | Not Set | RADAR | <0x2->0x2 | X | X | 1 | X | ON (Collision Warning2 Chime) |
| On | Not Set | RADAR | <0x3->0x3 | X | X | X | 0 | OFF |
| On | Not Set | RADAR | <0x3->0x3 | X | X | X | 1 | ON (Collision Warning3 Chime) |
| On | Not Set | CAMERA | X | 0x0 | X | X | X | OFF |
| On | Not Set | CAMERA | X | 0x0->0x1 | 0 | X | X | OFF |
| On | Not Set | CAMERA | X | 0x0->0x1 | 1 | X | X | ON (Collision Warning1 Chime) |
| On | Not Set | CAMERA | X | <0x2->0x2 | X | 0 | X | OFF |
| On | Not Set | CAMERA | X | <0x2->0x2 | X | 1 | X | ON (Collision Warning2 Chime) |
| On | Not Set | CAMERA | X | <0x3->0x3 | X | X | 0 | OFF |
| On | Not Set | CAMERA | X | <0x3->0x3 | X | X | 1 | ON (Collision Warning3 Chime) |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44184: ACC Info Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52496: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63328: Ign Mode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63329: LVSD / HVSD Flag (Value: Not set, Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63330: FRM2_20: ACC_SYS_INFO (Value: 0x0-Default, 0x1~0x2- Reserved, 0x3-Object disappeared, 0x4-Available to resume acceleration control, 0x5-ACC Disengaged, 0x6-Not a condition to enter ACC, 0x7-TakeOver Request,.... (System Requirement)
FRM2_20: ACC_SYS_INFO (Value: 0x0-Default, 0x1 -Increase speed above 10kmph, 0x2- Enable AEB function to engage ACC, 0x3-Object disappeared, 0x4-Available to resume acceleration control, 0x5-ACC Disengaged, 0x6-Not a condition to enter ACC, 0x7-TakeOver Request, 0x8 -Seatbelt not buckled, 0x9- Driver Door open ,0xA-OFF Road Mode-ACC not available, 0xB-ESC Turned OFF, 0xC-Set SPD Higher then MAX, 0xD- Manual Park brake engage 0xE~0xF-Reserved)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63331: FRM2_20: FRM2_CRC (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63332: ACC Configuration (Value: 0-Disable, 1- Enable) - refer ACC set distance/speed/Target vehicle Display section (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63333: Diag RW ACC Info Chimes Enable (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52498: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63334: ACC Info Chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52501: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63335: Table- ACC Info Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64086: Ign Mode (System Requirement)
| Ign Mode | LVSD / HVSD Flag | ACC Configuration | Diag RW ACC Info Chime Enable | FRM2_20: ACC_SYS_INFO | ACC Info Chimes Functional logic |
| --- | --- | --- | --- | --- | --- |
| Off | X | X | X | X | Off |
| On | Set | X | X | X | Off |
| On | Not Set | 0 | X | X | Off |
| On | Not Set | 1 | 0 | X | Off |
| On | Not Set | 1 | 1 | Timeout or Never received | Off |
| On | Not Set | 1 | 1 | FRM2_20 CRC mismatch | Off |
| On | Not Set | 1 | 1 | 0x0 (Default) or 0x1 (Reserved) or 0x2 (Reserved) | OFF |
| On | Not Set | 1 | 1 | 0x1 | On |
| On | Not Set | 1 | 1 | 0x2 | On |
| On | Not Set | 1 | 1 | 0x3 (Object Disappeared) | On |
| On | Not Set | 1 | 1 | 0x4 (Available to Resume acceleration control) | On |
| On | Not Set | 1 | 1 | 0x5 (ACC Disengaged) | On |
| On | Not set | 1 | 1 | 0x6 (Not a condition to enter to enter ACC) | On |
| On | Not set | 1 | 1 | 0x7 (Takeover request) | On |
| On | Not set | 1 | 1 | 0x8 | On |
| On | Not Set | 1 | 1 | 0x9 | On |
| On | Not Set | 1 | 1 | 0xA | On |
| On | Not Set | 1 | 1 | 0xB | On |
| On | Not Set | 1 | 1 | 0xC | On |
| On | Not Set | 1 | 1 | 0xD | On |
| On | Not Set | 1 | 1 | 0xE or 0xF | OFF |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44186: LDWS/LKAS Lane Departure Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52504: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63336: Ign Mode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63337: LVSD / HVSD Flag (Value: Not set, Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63338: FCM_LKAS1_10: LDW_LKA _Mode (Value: 0x0- LDW+LKA Off, 0x1- LDW, 0x2- LDW+LKA, 0x3- Reserved) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63339: FCM_LKAS1_10: LDW_LKA_SYS_STATE (Value: 0x0- System Off/Default, 0x1- Standby, 0x2- Active, 0x3- Warning, 0x4- System fail, 0x5- System Not calibratable, 0x6~0x7- Reserved) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63340: FCM_LKAS1_10: LDW_LKA_LANE_RECOGN (Value: 0x0- No recognition, 0x1- Left Lane, 0x2- Right Lane, 0x3- Both Line) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63341: FCM_LKAS1_10: LDW_LKA_Warning (Value: 0x0- No Warning, 0x1- left Lane Departure Warning, 0x2- Right Lane Departure Warning, 0x3- Reserved) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63342: LDWS_LKAS configuration (Value: 0-Disable, 1-Enable) - Refer LANE Display Section (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63343: Diag RW Lane Departure Chime Enable (Value: 0- Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52506: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63344: LKA_LDW_Lane Departure Chime Functional Logic (Value: On, Off) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52508: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63345: Table- LDW_LKA_Lane Departure Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64088: Ign Mode (System Requirement)
| Ign Mode | LVSD / HVSD Flag | LKAS_LDWS Configuration | Diag RW Lane Departure Chime Enable | FCM_LKAS1_10: LDW_LKA _Mode | FCM_LKAS1_10: LDW_LKA_SYS_STATE | FCM_LKAS1_10: LDW_LKA_LANE_RECOGN | FCM_LKAS1_10: LDW_LKA_Warning | LKA_LDW_Lane Departure chime Functional Logic |
| --- | --- | --- | --- | --- | --- | --- | --- | --- |
| Off | X | X | X | X | X | X | X | Off |
| On | Set | X | X | X | X | X | X | Off |
| On | Not Set | 0 | X | X | X | X | X | Off |
| On | Not Set | 1 | 0 | X | X | X | X | Off |
| On | Not Set | 1 | 1 | Timeout or Never Received |  |  |  | Off |
| On | Not Set | 1 | 1 | 0x0(Off) or 0x3 (Reserved) | X | X | X | Off |
| On | Not Set | 1 | 1 | 0x1 or 0x2 | !=0x3 | X | X | Off |
| On | Not Set | 1 | 1 | 0x1 or 0x2 | 0x3 (Warning) | 0x0 (No recognition) | X | Off |
| On | Not Set | 1 | 1 | 0x1 or 0x2 | 0x3 (Warning) | 0x1 (Left Line recognition) | 0x1 (Left Warning) | ON (Left Line Departure Chime) |
| On | Not Set | 1 | 1 | 0x1 or 0x2 | 0x3 (Warning) | 0x1 (Left Line recognition) | !=0x1 | Off |
| On | Not Set | 1 | 1 | 0x1 or 0x2 | 0x3 (Warning) | 0x2 (Right Line Recognition) | 0x2 (Right Warning) | ON (Right Line Departure chime) |
| On | Not Set | 1 | 1 | 0x1 or 0x2 | 0x3 (Warning) | 0x2 (Right Line Recognition) | !=0x2 | Off |
| On | Not Set | 1 | 1 | 0x1 or 0x2 | 0x3 (Warning) | 0 x3 (Both Lines recognition) | 0x1 (Left Warning) | ON (Left Line Departure Chime) |
| On | Not Set | 1 | 1 | 0x1 or 0x2 | 0x3 (Warning) | 0x3 (Both Lines recognition) | 0x2 (Right Warning) | ON (Right Lane Departure chime) |
| On | Not Set | 1 | 1 | 0x1 or 0x2 | 0x3 (Warning) | 0x3 (Both Lines recognition) | !=(0x1 and 0x2) | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64091 (Information)
In setting when there user option is selected as LDW chime off, the Chime shall not be played.
Refer req id :3098624
- Variant: S220, S237, W502
- Stakeholder Requirement State: In Review
- System Requirement State: Draft
- Software Requirement State: Draft
- Primary Discipline: SW
- Requirement Type: Functional

### MS22029826-44188: LKA/TJA Hands-Off Chime (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52510: Input Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63346: Ign Mode (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63347: LVSD / HVSD Flag (Value: Not set, Set) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63348: FCM_LKAS1_10: TJA_STATE (Value: 0x0- TJA Off/ Default, 0x1- TJA Ready, 0x2- TJA Active, 0x3- Control Off, 0x4- Control In, 0x5~0x6- Reserved, 0x7- System Failure) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63349: FCM_LKAS1_10: LDW_LKA _Mode (Value: 0x0- LDW+LKA Off, 0x1- LDW, 0x2- LDW+LKA, 0x3- Reserved) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63350: FCM_LKAS1_10: LKA_HANDSOFF_AUDIO_WARNING (Value: 0x0- No warning, 0x1- Audio Warning) (System Requirement)
FCM_LKAS1_10:LKA_HANDSOFF_AUDIO_WARNING (Value: 0x0- No warning, 0x1- Audio Warning)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63351: FCM_LKAS1_10: TJA_HANDSOFF _WARNING (Value: 0x0- No Warning/ Default, 0x1- Hands Off 1st warning, 0x2- Hands off 2nd Warning, 0x3- Automatic Off warning) (System Requirement)
FCM_LKAS1_10:TJA_HANDSOFF _WARNING (Value: 0x0- No Warning/ Default, 0x1- Hands Off 1 st warning, 0x2- Hands off 2 nd Warning, 0x3- Automatic Off warning)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63352: LDWS_LKAS configuration (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63353: TJA configuration (Value: 0-Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63354: Diag RW LKA Hands-off Chime Enable (Value: 0- Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63355: Diag RW TJA Hands-off Chime Enable (Value: 0- Disable, 1-Enable) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52513: Output Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63356: LKA Hands-Off chime Functional Logic (Value: Off, On) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63357: TJA Hands-Off Chime Functional Logic (Value: Off, On (Hands Off Level 2 chime), On (Released the steering control_Chime)) (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-52515: Performance Requirements (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63358: Table- LKA Hands-Off Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64093: Ign Mode (System Requirement)
| Ign Mode | LVSD / HVSD Flag | LDWS_LKAS configuration | Diag RW LKA Hands-off Chime Enable | FCM_LKAS1_10: TJA_STATE | FCM_LKAS1_10: LDW_LKA _MODE | FCM_LKAS1_10: LKA_HANDSOFF _AUDIO_WARNING | LKA Hands-Off Chime Functional Logic |
| --- | --- | --- | --- | --- | --- | --- | --- |
| Off | X | X | X | X | X | X | Off |
| On | Set | X | X | X | X | X | Off |
| On | Not Set | 0 | X | X | X | X | Off |
| On | Not Set | 1 | 0 | X | X | X | Off |
| On | Not Set | 1 | 1 | Timeout or Never received |  |  | Off |
| On | Not Set | 1 | 1 | 0x0 | 0x2 (LKA+LDW) | 0x1 | On |
| On | Not Set | 1 | 1 | !-0x0 | Other values |  | Off |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-63359: Table- TJA Hands-Off Chime Functional Logic (System Requirement)
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-64095: Ign Mode (System Requirement)
| Ign Mode | LVSD / HVSD Flag | TJA configuration | Diag RW TJA Hands-off Chime Enable | FCM_LKAS1_10: TJA_STATE | FCM_LKAS1_10: TJA_HANDSOFF _WARNING | TJA Hands-Off Chime Functional Logic |
| --- | --- | --- | --- | --- | --- | --- |
| Off | X | X | X | X | X | Off |
| On | Set | X | X | X | X | Off |
| On | Not Set | 0 | X | X | X | Off |
| On | Not Set | 1 | 0 | X | X | Off |
| On | Not Set | 1 | 1 | Timeout or Never Received |  | Off |
| On | Not Set | 1 | 1 | !=0x1/0x2/0x3/0x4 | X | Off |
| On | Not Set | 1 | 1 | 0x1/0x2/0x3/0x4 | 0x0 | Off |
| On | Not Set | 1 | 1 | 0x0 | 0x1/0x2 | Off |
| On | Not Set | 1 | 1 | 0x1/0x2/0x3/0x4 | 0x1 (Hands Off Warning 1 st) | Off |
| On | Not Set | 1 | 1 | 0x1/0x2/0x3/0x4 | 0x2 (Hands Off Warning 2 nd) | On (Level 2 chime) |
| On | Not Set | 1 | 1 | 0x0/0x1/0x2/0x3/0x4 | 0x3 (Steering control Automatic Cancel Warning) | On (Released steering control chime) |
- Variant: S220, S220_SB_ADP_W601-V1, S220_SB_ADP_W601-V2, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-44190: DPF Chime (Information)
- Variant: S220, W502
- Stakeholder Requirement State: In Review
- System Requirement State: Draft
- Software Requirement State: Draft
- Primary Discipline: TBD
- Requirement Type: TBD

#### MS22029826-52517: Input Requirements (Information)
- Variant: S220, W502
- Stakeholder Requirement State: In Review
- System Requirement State: Draft
- Software Requirement State: Draft
- Primary Discipline: TBD
- Requirement Type: TBD

##### MS22029826-63360: IgnMode (Value: Off, On) (Information)
- Variant: S220, W502
- Stakeholder Requirement State: In Review
- System Requirement State: Draft
- Software Requirement State: Draft
- Primary Discipline: SW
- Requirement Type: Functional

##### MS22029826-63361: LVSD/HVSD Flag (Value: Set, Not Set) (Information)
- Variant: S220, W502
- Stakeholder Requirement State: In Review
- System Requirement State: Draft
- Software Requirement State: Draft
- Primary Discipline: SW
- Requirement Type: Functional

##### MS22029826-63362: VAR_CODING_ENGINE_MANAGEMENT_SYSTEM (Value: 0-Not Present, 1-Present) (Information)
- Variant: S220, W502
- Stakeholder Requirement State: In Review
- System Requirement State: Draft
- Software Requirement State: Draft
- Primary Discipline: SW
- Requirement Type: Functional

##### MS22029826-63363: FEATURE_CODE_DPF_CONFIG(Value: 0-Not Present, 1-Present) (Information)
- Variant: S220, W502
- Stakeholder Requirement State: In Review
- System Requirement State: Draft
- Software Requirement State: Draft
- Primary Discipline: SW
- Requirement Type: Functional

##### MS22029826-63364: EMS4_20: INDC_DPF_REGEN (Value: 0-Off,1-On, 2-Blink, 3-Off/Reserved) (Information)
- Variant: S220, W502
- Stakeholder Requirement State: In Review
- System Requirement State: Draft
- Software Requirement State: Draft
- Primary Discipline: SW
- Requirement Type: Functional

##### MS22029826-63365: Diag RW DPF Chime Enable (Value: 0-Disable, 1-Enable) (Information)
- Variant: S220, W502
- Stakeholder Requirement State: In Review
- System Requirement State: Draft
- Software Requirement State: Draft
- Primary Discipline: SW
- Requirement Type: Functional

#### MS22029826-52520: Output Requirements (Information)
- Variant: S220, W502
- Stakeholder Requirement State: In Review
- System Requirement State: Draft
- Software Requirement State: Draft
- Primary Discipline: TBD
- Requirement Type: TBD

##### MS22029826-63366: DPF Chime Functional Logic (Value: On, Off) (Information)
- Variant: S220, W502
- Stakeholder Requirement State: In Review
- System Requirement State: Draft
- Software Requirement State: Draft
- Primary Discipline: SW
- Requirement Type: Functional

#### MS22029826-52522: Performance Requirements (Information)
- Variant: S220, W502
- Stakeholder Requirement State: In Review
- System Requirement State: Draft
- Software Requirement State: Draft
- Primary Discipline: TBD
- Requirement Type: TBD

##### MS22029826-63367: Table- DPF Chime configuration (Information)
- Variant: S220, W502
- Stakeholder Requirement State: In Review
- System Requirement State: Draft
- Software Requirement State: Draft
- Primary Discipline: TBD
- Requirement Type: TBD

###### MS22029826-64098: Table- DPF Chime configuration (Information)
| VAR_CODING_ENGINE_MANAGEMENT_SYSTEM | FEATURE_CODE_DPF_CONFIG | Diag RW DPF Chime Enable | DPF Chime Configuration |  |
| --- | --- | --- | --- | --- |
| 0 | X | X | 0 |  |
| 1 | 0 | X | 0 |  |
| 1 | 1 | 0 | 0 |  |
| 1 | 1 | 1 | 1 |  |
- Variant: S220, W502
- Stakeholder Requirement State: In Review
- System Requirement State: Draft
- Software Requirement State: Draft
- Primary Discipline: SW
- Requirement Type: Functional

##### MS22029826-63368: Table- DPF Chime Functional Logic (Information)
- Variant: S220, W502
- Stakeholder Requirement State: In Review
- System Requirement State: Draft
- Software Requirement State: Draft
- Primary Discipline: TBD
- Requirement Type: TBD

###### MS22029826-64100: Table- DPF Chime Functional Logic (Information)
| Ign Mode | LVSD/HVSD Flag | DPF Chime Configuration | CAN signal missing/Never received | EMS4_20: INDC_DPF_REGEN | DPF Chime Functional logic |
| --- | --- | --- | --- | --- | --- |
| Off | X | X | X | X | Off |
| On | Set | X | X | X | Off |
| On | Not Set | 0 | X | X | Off |
| On | Not Set | 1 | 1 | X | Off |
| On | Not Set | 1 | 0 | 0x0 | Off |
| On | Not Set | 1 | 0 | !0x1->0x1 !0x2->0x2 | On |
| On | Not Set | 1 | 0 | 0x1->0x2 | On |
| On | Not Set | 1 | 0 | 0x2->0x1 | On |
| On | Not set | 1 | 0 | 0x3 | Off |
Note: In case of Transition from 0x1->0x2 / 0x2->0x1 Cluster shall retrigger the chime
- Variant: S220, W502
- Stakeholder Requirement State: In Review
- System Requirement State: Draft
- Software Requirement State: Draft
- Primary Discipline: SW
- Requirement Type: Functional

###### MS22029826-64102: Reference Chime Pattern (Information)
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• If there is any other chime to be played while this is active, it shall be played in the other
channel provided it is free
• During the 3 min interval this chime shall not hold the channel so that other chimes shall be
allowed to play as necessary
• Chime Shall be Play with repetition interval 3min for complete ignition cycle until condition is
OFF.
- Variant: S220, W502
- Stakeholder Requirement State: In Review
- System Requirement State: Draft
- Software Requirement State: Draft
- Primary Discipline: SW
- Requirement Type: Functional

### MS22029826-73673: AMT Buzzer (Information)
- Variant: S220
- Stakeholder Requirement State: In Review
- System Requirement State: Draft
- Software Requirement State: Draft
- Primary Discipline: TBD
- Requirement Type: TBD

#### MS22029826-73674: Input Requirements (Information)
- Variant: S220
- Stakeholder Requirement State: In Review
- System Requirement State: Draft
- Software Requirement State: Draft
- Primary Discipline: TBD
- Requirement Type: TBD

##### MS22029826-73678: IgnMode (Value: Off, On) (Information)
- Variant: S220
- Stakeholder Requirement State: In Review
- System Requirement State: Draft
- Software Requirement State: Draft
- Primary Discipline: SW
- Requirement Type: Functional

##### MS22029826-73680: LVSD/HVSD Flag (Value: Set, Not Set) (Information)
- Variant: S220
- Stakeholder Requirement State: In Review
- System Requirement State: Draft
- Software Requirement State: Draft
- Primary Discipline: SW
- Requirement Type: Functional

##### MS22029826-73682: VAR_CODING_AUTOMATED_MANUAL_TRANSMISSION (Value: 0-Not Present, 1-Present). (Information)
- Variant: S220
- Stakeholder Requirement State: In Review
- System Requirement State: Draft
- Software Requirement State: Draft
- Primary Discipline: SW
- Requirement Type: Functional

##### MS22029826-73683: VAR_CODING_TRANSMISSION_CONTROL_UNIT (Value: 0-Not Present, 1-Present) (Information)
- Variant: S220
- Stakeholder Requirement State: In Review
- System Requirement State: Draft
- Software Requirement State: Draft
- Primary Discipline: SW
- Requirement Type: Functional

##### MS22029826-73684: VAR_CODING_ENGINE_MANAGEMENT_SYSTEM (Value: 0-Not Present, 1-Present). (Information)
- Variant: S220
- Stakeholder Requirement State: In Review
- System Requirement State: Draft
- Software Requirement State: Draft
- Primary Discipline: SW
- Requirement Type: Functional

##### MS22029826-73685: CAN input (Information)
| Msg Name/Msg ID | Signal Name | Size(bits) | Value Range |
| --- | --- | --- | --- |
| AMT6_20 (0x177) | AMT_BUZZER | 1 | 0x0 -Buzzer Off/Default 0x1- Buzzer On |
| MBFM7_100 (0x21C) | HAND_BRAKE_REMINDER | 1 | 0x0 – Park Buzzer Off 0x1 – Park Buzzer On |
- Variant: S220
- Stakeholder Requirement State: In Review
- System Requirement State: Draft
- Software Requirement State: Draft
- Primary Discipline: SW
- Requirement Type: Functional

##### MS22029826-73717: Diag RW AMT Chime Enable (Value: 0-Disable, 1-Enable) (Information)
- Variant: S220
- Stakeholder Requirement State: In Review
- System Requirement State: Draft
- Software Requirement State: Draft
- Primary Discipline: SW
- Requirement Type: Functional

##### MS22029826-73718 (Information)
Diag RW AMT Engage Park Brake Chime Enable(Value : 0- Disable ,1 –Enable)
- Variant: S220
- Stakeholder Requirement State: In Review
- System Requirement State: Draft
- Software Requirement State: Draft
- Primary Discipline: SW
- Requirement Type: Functional

#### MS22029826-73675: Output Requirements (Information)
- Variant: S220
- Stakeholder Requirement State: In Review
- System Requirement State: Draft
- Software Requirement State: Draft
- Primary Discipline: TBD
- Requirement Type: TBD

##### MS22029826-73677: AMT Chime functional logic (Value: On, Off) (Information)
- Variant: S220
- Stakeholder Requirement State: In Review
- System Requirement State: Draft
- Software Requirement State: Draft
- Primary Discipline: SW
- Requirement Type: Functional

##### MS22029826-73719 (Information)
AMTEngage Park Brake Chime Functional Logic(Value : On, Off)
- Variant: S220
- Stakeholder Requirement State: In Review
- System Requirement State: Draft
- Software Requirement State: Draft
- Primary Discipline: SW
- Requirement Type: Functional

#### MS22029826-73676: Performance Requirements (Information)
- Variant: S220
- Stakeholder Requirement State: In Review
- System Requirement State: Draft
- Software Requirement State: Draft
- Primary Discipline: TBD
- Requirement Type: TBD

##### MS22029826-73679: Table - AMT Chime Configuration (Information)
- Variant: S220
- Stakeholder Requirement State: In Review
- System Requirement State: Draft
- Software Requirement State: Draft
- Primary Discipline: TBD
- Requirement Type: TBD

###### MS22029826-73686: VAR_CODING_AUTOMATED_MANUAL_TRANSMISSION (Information)
| VAR_CODING_AUTOMATED_MANUAL_TRANSMISSION | VAR_CODING_TRANSMISSION_CONTROL_UNIT |  | VAR_CODING_ENGINE_MANAGEMENT_SYSTEM | AMT Chime Configuration |
| --- | --- | --- | --- | --- |
| 0 | 0 |  | 0 | 0 |
| 1 | 1 |  | X | 0 |
| 0 | 0 |  | 1 | MT |
| 1 | 0 |  | X | AMT |
| 0 | 1 |  | X | AT |
- Variant: S220
- Stakeholder Requirement State: In Review
- System Requirement State: Draft
- Software Requirement State: Draft
- Primary Discipline: SW
- Requirement Type: Functional

##### MS22029826-73681: Table- AMT Chime Functional Logic (Information)
- Variant: S220
- Stakeholder Requirement State: In Review
- System Requirement State: Draft
- Software Requirement State: Draft
- Primary Discipline: TBD
- Requirement Type: TBD

###### MS22029826-73687: Table- DPF Chime Functional Logic (Information)
| IgnMode | LVSD/HVSD Flag | AMT Chime Configuration | Diag RW AMT Chime Warn Enable | CAN Missing or Never Received | AMT6_20: AMT_BUZZER | AMT Chime Functional Logic |
| --- | --- | --- | --- | --- | --- | --- |
| Off | X | X | X | X | X | Off |
| On | Set | X | X | X | X | Off |
| On | Not Set | 0, | X | X | X | Off |
| On | Not Set | AT, MT | X | X | X | Off |
| On | Not Set | AMT | 0 | X | X | Off |
| On | Not Set | AMT | 1 | 1 | X | Off |
| On | Not Set | AMT | 1 | 0 | 0x0 | Off |
| On | Not Set | AMT | 1 | 0 | 0x1 | On |
- Variant: S220
- Stakeholder Requirement State: In Review
- System Requirement State: Draft
- Software Requirement State: Draft
- Primary Discipline: SW
- Requirement Type: Functional

##### MS22029826-73732: Table- AMT Engage Park Brake chime Functional Logic (Information)
Table- AMT Chime Functional Logic
- Variant: S220
- Stakeholder Requirement State: In Review
- System Requirement State: Draft
- Software Requirement State: Draft
- Primary Discipline: TBD
- Requirement Type: TBD

###### MS22029826-73733: Table- DPF Chime Functional Logic (Information)
| IgnMode | LVSD/ HVSD Flag | AMT Chime Configuration | VAR_CODE_MAHINDRA_BODY_FUNCTION_MODULE | Diag RW AMT Engage Park Brake Chime Enable | CAN Signal Missing/ Never Received | MBFM7_100: | AMTEngage Park Brake Chime Functional Logic |
| --- | --- | --- | --- | --- | --- | --- | --- |
| IgnMode | LVSD/ HVSD Flag | AMT Chime Configuration | VAR_CODE_MAHINDRA_BODY_FUNCTION_MODULE | Diag RW AMT Engage Park Brake Chime Enable | CAN Signal Missing/ Never Received | HAND_BRAKE_REMINDER | AMTEngage Park Brake Chime Functional Logic |
| On | X | X | X | X | X | X | Off |
| Off | Set | X | X | X | X | X | Off |
| Off | Not set | 0,AT,MT | X | X | X | X | Off |
| Off | Not set | AMT | 0 | X | X | X | Off |
| Off | Not set | AMT | 1 | 0 | X | X | Off |
| Off | Not set | AMT | 1 | 1 | 1 | X | Off |
| Off | Not set | AMT | 1 | 1 | 0 | 0 | Off |
| Off | Not set | AMT | 1 | 1 | 0 | 1 | On |
- Variant: S220
- Stakeholder Requirement State: In Review
- System Requirement State: Draft
- Software Requirement State: Draft
- Primary Discipline: SW
- Requirement Type: Functional

### MS22029826-73756: Gear Shift Error Chime (Heading)
- Variant: S237
- Stakeholder Requirement State: In Review
- System Requirement State: Draft
- Software Requirement State: Draft
- Primary Discipline: TBD
- Requirement Type: TBD

#### MS22029826-73757: Input Requirements (Heading)
- Variant: S237
- Stakeholder Requirement State: In Review
- System Requirement State: Draft
- Software Requirement State: Draft
- Primary Discipline: TBD
- Requirement Type: TBD

##### MS22029826-73761: IgnMode (Value: On, Off) (System Requirement)
- Variant: S237
- Stakeholder Requirement State: In Review
- System Requirement State: Draft
- Software Requirement State: Draft
- Primary Discipline: TBD
- Requirement Type: TBD

##### MS22029826-73763: LVSD/HVSD Flag (Value: Not Set, Set) (System Requirement)
- Variant: S237
- Stakeholder Requirement State: In Review
- System Requirement State: Draft
- Software Requirement State: Draft
- Primary Discipline: TBD
- Requirement Type: TBD

##### MS22029826-73764: VAR_CODING_SWITCH_BY_WIRE(Value: 0-Not Present, 1-Present) (System Requirement)
- Variant: S237
- Stakeholder Requirement State: In Review
- System Requirement State: Draft
- Software Requirement State: Draft
- Primary Discipline: TBD
- Requirement Type: TBD

##### MS22029826-73765: SBW1_50(0x250): SBW_WARN (System Requirement)
SBW1_50(0x250): SBW_WARN (0X0-No warning/Default, 0x1-TGS Service Warning, 0x2 Cannot Change gear, 0x3 Condition is not P, 0X4, Brake Not Presses, 0x5-Shift Lock Not Presses, 0x6-Park Switch Failure, 0x7-Shift Lock Switch Failure, 0xF-Signal Invalid)
- Variant: S237
- Stakeholder Requirement State: In Review
- System Requirement State: Draft
- Software Requirement State: Draft
- Primary Discipline: TBD
- Requirement Type: TBD

##### MS22029826-73766: Diag RW Gear Shift Error Chime Enable (Value: 0-Disable, 1-Enable) (System Requirement)
- Variant: S237
- Stakeholder Requirement State: In Review
- System Requirement State: Draft
- Software Requirement State: Draft
- Primary Discipline: TBD
- Requirement Type: TBD

#### MS22029826-73758: Output Requirements (Heading)
- Variant: S237
- Stakeholder Requirement State: In Review
- System Requirement State: Draft
- Software Requirement State: Draft
- Primary Discipline: TBD
- Requirement Type: TBD

##### MS22029826-73762: Gear Shift Error Chime Functional Logic (Value: Off, On) (System Requirement)
- Variant: S237
- Stakeholder Requirement State: In Review
- System Requirement State: Draft
- Software Requirement State: Draft
- Primary Discipline: TBD
- Requirement Type: TBD

#### MS22029826-73759: Performance Requirements (Heading)
- Variant: S237
- Stakeholder Requirement State: In Review
- System Requirement State: Draft
- Software Requirement State: Draft
- Primary Discipline: TBD
- Requirement Type: TBD

##### MS22029826-73760 (System Requirement)
Table- Gear Shift Error Chime Functional Logic
| Ign Mode | LVSD/HVSD Flag | VAR_CODING_SWITCH_ BY_WIRE | Diag RW Gear Shift Error Chime Enable | CAN Signal Missing or Never Received | SBW1_50(0x250): SBW_WARN | Gear Shift Error Chime Functional Logic |
| --- | --- | --- | --- | --- | --- | --- |
| Off | X | X | X | X | X | Off |
| On | Set | X | X | X | X | Off |
| On | Not Set | 0 | X | X | X | Off |
| On | Not Set | 1 | 0 | X | X | Off |
| On | Not Set | 1 | 1 | 1 | X | Off |
| On | Not Set | 1 | 1 | 0 | !=0x1 | Off |
| On | Not Set | 1 | 1 | 0 | 0x1 | On |
- Variant: S237
- Stakeholder Requirement State: In Review
- System Requirement State: Draft
- Software Requirement State: Draft
- Primary Discipline: TBD
- Requirement Type: TBD

### MS22029826-73767: Shift Not Possible Chime (Heading)
- Variant: S237
- Stakeholder Requirement State: In Review
- System Requirement State: Draft
- Software Requirement State: Draft
- Primary Discipline: TBD
- Requirement Type: TBD

#### MS22029826-73768: Input Requirements (Heading)
- Variant: S237
- Stakeholder Requirement State: In Review
- System Requirement State: Draft
- Software Requirement State: Draft
- Primary Discipline: TBD
- Requirement Type: TBD

##### MS22029826-73772: IgnMode (Value: On, Off) (System Requirement)
- Variant: S237
- Stakeholder Requirement State: In Review
- System Requirement State: Draft
- Software Requirement State: Draft
- Primary Discipline: TBD
- Requirement Type: TBD

##### MS22029826-73774: LVSD/HVSD Flag (Value: Not Set, Set) (System Requirement)
- Variant: S237
- Stakeholder Requirement State: In Review
- System Requirement State: Draft
- Software Requirement State: Draft
- Primary Discipline: TBD
- Requirement Type: TBD

##### MS22029826-73775: VAR_CODING_SWITCH_BY_WIRE(Value: 0-Not Present, 1-Present) (System Requirement)
- Variant: S237
- Stakeholder Requirement State: In Review
- System Requirement State: Draft
- Software Requirement State: Draft
- Primary Discipline: TBD
- Requirement Type: TBD

##### MS22029826-73776: SBW1_50(0x250): SBW_WARN (System Requirement)
SBW1_50(0x250): SBW_WARN (0X0-No warning/Default, 0x1-TGS Service Warning, 0x2 Cannot Change gear, 0x3 Condition is not P, 0X4, Brake Not Presses, 0x5-Shift Lock Not Presses, 0x6-Park Switch Failure, 0x7-Shift Lock Switch Failure, 0xF-Signal Invalid)
- Variant: S237
- Stakeholder Requirement State: In Review
- System Requirement State: Draft
- Software Requirement State: Draft
- Primary Discipline: TBD
- Requirement Type: TBD

##### MS22029826-73777: Diag RW Shift Not Possible Chime Enable (Value: 0-Disable, 1-Enable) (System Requirement)
- Variant: S237
- Stakeholder Requirement State: In Review
- System Requirement State: Draft
- Software Requirement State: Draft
- Primary Discipline: TBD
- Requirement Type: TBD

#### MS22029826-73769: Output Requirements (Heading)
- Variant: S237
- Stakeholder Requirement State: In Review
- System Requirement State: Draft
- Software Requirement State: Draft
- Primary Discipline: TBD
- Requirement Type: TBD

##### MS22029826-73771: Shift Not Possible Chime Functional Logic (Value: Off, On) (System Requirement)
- Variant: S237
- Stakeholder Requirement State: In Review
- System Requirement State: Draft
- Software Requirement State: Draft
- Primary Discipline: TBD
- Requirement Type: TBD

#### MS22029826-73770: Performance Requirements (Heading)
- Variant: S237
- Stakeholder Requirement State: In Review
- System Requirement State: Draft
- Software Requirement State: Draft
- Primary Discipline: TBD
- Requirement Type: TBD

##### MS22029826-73773 (System Requirement)
Table- Shift Not Possible Chime Functional Logic
| Ign Mode | LVSD/HVSD Flag | VAR_CODING_SWITCH_ BY_WIRE | Diag RW Shift Not Possible Chime Enable | CAN Signal Missing or Never Received | SBW1_50(0x250): SBW_WARN | Shift Not Possible Chime Functional Logic |
| --- | --- | --- | --- | --- | --- | --- |
| Off | X | X | X | X | X | Off |
| On | Set | X | X | X | X | Off |
| On | Not Set | 0 | X | X | X | Off |
| On | Not Set | 1 | 0 | X | X | Off |
| On | Not Set | 1 | 1 | 1 | X | Off |
| On | Not Set | 1 | 1 | 0 | !=0x2 | Off |
| On | Not Set | 1 | 1 | 0 | 0x2 | On |
- Variant: S237
- Stakeholder Requirement State: In Review
- System Requirement State: Draft
- Software Requirement State: Draft
- Primary Discipline: TBD
- Requirement Type: TBD

### MS22029826-73778: Shift to P not Allowed Chime (Heading)
- Variant: S237
- Stakeholder Requirement State: In Review
- System Requirement State: Draft
- Software Requirement State: Draft
- Primary Discipline: TBD
- Requirement Type: TBD

#### MS22029826-73779: Input Requirements (Heading)
- Variant: S237
- Stakeholder Requirement State: In Review
- System Requirement State: Draft
- Software Requirement State: Draft
- Primary Discipline: TBD
- Requirement Type: TBD

##### MS22029826-73783: IgnMode (Value: On, Off) (System Requirement)
- Variant: S237
- Stakeholder Requirement State: In Review
- System Requirement State: Draft
- Software Requirement State: Draft
- Primary Discipline: TBD
- Requirement Type: TBD

##### MS22029826-73785: LVSD/HVSD Flag (Value: Not Set, Set) (System Requirement)
- Variant: S237
- Stakeholder Requirement State: In Review
- System Requirement State: Draft
- Software Requirement State: Draft
- Primary Discipline: TBD
- Requirement Type: TBD

##### MS22029826-73786: VAR_CODING_SWITCH_BY_WIRE(Value: 0-Not Present, 1-Present) (System Requirement)
- Variant: S237
- Stakeholder Requirement State: In Review
- System Requirement State: Draft
- Software Requirement State: Draft
- Primary Discipline: TBD
- Requirement Type: TBD

##### MS22029826-73787: SBW1_50(0x250): SBW_WARN (System Requirement)
SBW1_50(0x250): SBW_WARN (0X0-No warning/Default, 0x1-TGS Service Warning, 0x2 Cannot Change gear, 0x3 Condition is not P, 0X4, Brake Not Presses, 0x5-Shift Lock Not Presses, 0x6-Park Switch Failure, 0x7-Shift Lock Switch Failure, 0xF-Signal Invalid)
- Variant: S237
- Stakeholder Requirement State: In Review
- System Requirement State: Draft
- Software Requirement State: Draft
- Primary Discipline: TBD
- Requirement Type: TBD

##### MS22029826-73788: Diag RW Shift to P not Allowed Chime Enable (Value: 0-Disable, 1-Enable) (System Requirement)
- Variant: S237
- Stakeholder Requirement State: In Review
- System Requirement State: Draft
- Software Requirement State: Draft
- Primary Discipline: TBD
- Requirement Type: TBD

#### MS22029826-73780: Output Requirements (Heading)
- Variant: S237
- Stakeholder Requirement State: In Review
- System Requirement State: Draft
- Software Requirement State: Draft
- Primary Discipline: TBD
- Requirement Type: TBD

##### MS22029826-73782: Shift to P not Allowed Chime Functional Logic (Value: Off, On) (System Requirement)
- Variant: S237
- Stakeholder Requirement State: In Review
- System Requirement State: Draft
- Software Requirement State: Draft
- Primary Discipline: TBD
- Requirement Type: TBD

#### MS22029826-73781: Performance Requirements (Heading)
- Variant: S237
- Stakeholder Requirement State: In Review
- System Requirement State: Draft
- Software Requirement State: Draft
- Primary Discipline: TBD
- Requirement Type: TBD

##### MS22029826-73784 (System Requirement)
Table- Shift to P not Allowed Chime Functional Logic
| Ign Mode | LVSD/HVSD Flag | VAR_CODING_SWITCH_ BY_WIRE | Diag RW Shift to P not Allowed Chime Enable | CAN Signal Missing or Never Received | SBW1_50(0x250): SBW_WARN | Shift to P not Allowed Chime Functional Logic |
| --- | --- | --- | --- | --- | --- | --- |
| Off | X | X | X | X | X | Off |
| On | Set | X | X | X | X | Off |
| On | Not Set | 0 | X | X | X | Off |
| On | Not Set | 1 | 0 | X | X | Off |
| On | Not Set | 1 | 1 | 1 | X | Off |
| On | Not Set | 1 | 1 | 0 | !=0x3 | Off |
| On | Not Set | 1 | 1 | 0 | 0x3 | On |
- Variant: S237
- Stakeholder Requirement State: In Review
- System Requirement State: Draft
- Software Requirement State: Draft
- Primary Discipline: TBD
- Requirement Type: TBD

### MS22029826-73789: Press Brake to Shift Chime (Heading)
- Variant: S237
- Stakeholder Requirement State: In Review
- System Requirement State: Draft
- Software Requirement State: Draft
- Primary Discipline: TBD
- Requirement Type: TBD

#### MS22029826-73790: Input Requirements (Heading)
- Variant: S237
- Stakeholder Requirement State: In Review
- System Requirement State: Draft
- Software Requirement State: Draft
- Primary Discipline: TBD
- Requirement Type: TBD

##### MS22029826-73794: IgnMode (Value: On, Off) (System Requirement)
- Variant: S237
- Stakeholder Requirement State: In Review
- System Requirement State: Draft
- Software Requirement State: Draft
- Primary Discipline: TBD
- Requirement Type: TBD

##### MS22029826-73796: LVSD/HVSD Flag (Value: Not Set, Set) (System Requirement)
- Variant: S237
- Stakeholder Requirement State: In Review
- System Requirement State: Draft
- Software Requirement State: Draft
- Primary Discipline: TBD
- Requirement Type: TBD

##### MS22029826-73797: VAR_CODING_SWITCH_BY_WIRE(Value: 0-Not Present, 1-Present) (System Requirement)
- Variant: S237
- Stakeholder Requirement State: In Review
- System Requirement State: Draft
- Software Requirement State: Draft
- Primary Discipline: TBD
- Requirement Type: TBD

##### MS22029826-73798: SBW1_50(0x250): SBW_WARN (System Requirement)
SBW1_50(0x250): SBW_WARN (0X0-No warning/Default, 0x1-TGS Service Warning, 0x2 Cannot Change gear, 0x3 Condition is not P, 0X4, Brake Not Presses, 0x5-Shift Lock Not Presses, 0x6-Park Switch Failure, 0x7-Shift Lock Switch Failure, 0xF-Signal Invalid)
- Variant: S237
- Stakeholder Requirement State: In Review
- System Requirement State: Draft
- Software Requirement State: Draft
- Primary Discipline: TBD
- Requirement Type: TBD

##### MS22029826-73799: Diag RW Press Brake to Shift Chime Enable (Value: 0-Disable, 1-Enable) (System Requirement)
- Variant: S237
- Stakeholder Requirement State: In Review
- System Requirement State: Draft
- Software Requirement State: Draft
- Primary Discipline: TBD
- Requirement Type: TBD

#### MS22029826-73791: Output Requirements (Heading)
- Variant: S237
- Stakeholder Requirement State: In Review
- System Requirement State: Draft
- Software Requirement State: Draft
- Primary Discipline: TBD
- Requirement Type: TBD

##### MS22029826-73793: Press Brake to Shift Chime Functional Logic (Value: Off, On) (System Requirement)
- Variant: S237
- Stakeholder Requirement State: In Review
- System Requirement State: Draft
- Software Requirement State: Draft
- Primary Discipline: TBD
- Requirement Type: TBD

#### MS22029826-73792: Performance Requirements (Heading)
- Variant: S237
- Stakeholder Requirement State: In Review
- System Requirement State: Draft
- Software Requirement State: Draft
- Primary Discipline: TBD
- Requirement Type: TBD

##### MS22029826-73795 (System Requirement)
Table - Press Brake to Shift Chime Functional Logic
| Ign Mode | LVSD/HVSD Flag | VAR_CODING_SWITCH_ BY_WIRE | Diag RW Press Brake to Shift Chime Enable | CAN Signal Missing or Never Received | SBW1_50(0x250): SBW_WARN | Press Brake to Shift Chime Functional Logic |
| --- | --- | --- | --- | --- | --- | --- |
| Off | X | X | X | X | X | Off |
| On | Set | X | X | X | X | Off |
| On | Not Set | 0 | X | X | X | Off |
| On | Not Set | 1 | 0 | X | X | Off |
| On | Not Set | 1 | 1 | 1 | X | Off |
| On | Not Set | 1 | 1 | 0 | !=0x4 | Off |
| On | Not Set | 1 | 1 | 0 | 0x4 | On |
- Variant: S237
- Stakeholder Requirement State: In Review
- System Requirement State: Draft
- Software Requirement State: Draft
- Primary Discipline: TBD
- Requirement Type: TBD

### MS22029826-73800: Press Shift unlock Switch Chime (Heading)
Shift Not Possible Chime
- Variant: S237
- Stakeholder Requirement State: In Review
- System Requirement State: Draft
- Software Requirement State: Draft
- Primary Discipline: TBD
- Requirement Type: TBD

#### MS22029826-73801: Input Requirements (Heading)
- Variant: S237
- Stakeholder Requirement State: In Review
- System Requirement State: Draft
- Software Requirement State: Draft
- Primary Discipline: TBD
- Requirement Type: TBD

##### MS22029826-73805: IgnMode (Value: On, Off) (System Requirement)
- Variant: S237
- Stakeholder Requirement State: In Review
- System Requirement State: Draft
- Software Requirement State: Draft
- Primary Discipline: TBD
- Requirement Type: TBD

##### MS22029826-73807: LVSD/HVSD Flag (Value: Not Set, Set) (System Requirement)
- Variant: S237
- Stakeholder Requirement State: In Review
- System Requirement State: Draft
- Software Requirement State: Draft
- Primary Discipline: TBD
- Requirement Type: TBD

##### MS22029826-73808: VAR_CODING_SWITCH_BY_WIRE(Value: 0-Not Present, 1-Present) (System Requirement)
- Variant: S237
- Stakeholder Requirement State: In Review
- System Requirement State: Draft
- Software Requirement State: Draft
- Primary Discipline: TBD
- Requirement Type: TBD

##### MS22029826-73809: SBW1_50(0x250): SBW_WARN (System Requirement)
SBW1_50(0x250): SBW_WARN (0X0-No warning/Default, 0x1-TGS Service Warning, 0x2 Cannot Change gear, 0x3 Condition is not P, 0X4, Brake Not Presses, 0x5-Shift Lock Not Presses, 0x6-Park Switch Failure, 0x7-Shift Lock Switch Failure, 0xF-Signal Invalid)
- Variant: S237
- Stakeholder Requirement State: In Review
- System Requirement State: Draft
- Software Requirement State: Draft
- Primary Discipline: TBD
- Requirement Type: TBD

##### MS22029826-73810: Diag RW Press shift unlock Switch Chime Enable (Value: 0-Disable, 1-Enable) (System Requirement)
- Variant: S237
- Stakeholder Requirement State: In Review
- System Requirement State: Draft
- Software Requirement State: Draft
- Primary Discipline: TBD
- Requirement Type: TBD

#### MS22029826-73802: Output Requirements (Heading)
- Variant: S237
- Stakeholder Requirement State: In Review
- System Requirement State: Draft
- Software Requirement State: Draft
- Primary Discipline: TBD
- Requirement Type: TBD

##### MS22029826-73804: Press shift unlock Switch Chime Functional Logic (Value: Off, On) (System Requirement)
- Variant: S237
- Stakeholder Requirement State: In Review
- System Requirement State: Draft
- Software Requirement State: Draft
- Primary Discipline: TBD
- Requirement Type: TBD

#### MS22029826-73803: Performance Requirements (Heading)
- Variant: S237
- Stakeholder Requirement State: In Review
- System Requirement State: Draft
- Software Requirement State: Draft
- Primary Discipline: TBD
- Requirement Type: TBD

##### MS22029826-73806 (System Requirement)
Table - Press shift unlock Switch Chime Functional Logic
| Ign Mode | LVSD/HVSD Flag | VAR_CODING_SWITCH_ BY_WIRE | Diag RW Press shift unlock Switch Chime Enable | CAN Signal Missing or Never Received | SBW1_50(0x250): SBW_WARN | Press shift unlock Switch Chime Functional Logic |
| --- | --- | --- | --- | --- | --- | --- |
| Off | X | X | X | X | X | Off |
| On | Set | X | X | X | X | Off |
| On | Not Set | 0 | X | X | X | Off |
| On | Not Set | 1 | 0 | X | X | Off |
| On | Not Set | 1 | 1 | 1 | X | Off |
| On | Not Set | 1 | 1 | 0 | !=0x5 | Off |
| On | Not Set | 1 | 1 | 0 | 0x5 | On |
- Variant: S237
- Stakeholder Requirement State: In Review
- System Requirement State: Draft
- Software Requirement State: Draft
- Primary Discipline: TBD
- Requirement Type: TBD

### MS22029826-73811: Park Switch Struck Chime (Heading)
- Variant: S237
- Stakeholder Requirement State: In Review
- System Requirement State: Draft
- Software Requirement State: Draft
- Primary Discipline: TBD
- Requirement Type: TBD

#### MS22029826-73812: Input Requirements (Heading)
- Variant: S237
- Stakeholder Requirement State: In Review
- System Requirement State: Draft
- Software Requirement State: Draft
- Primary Discipline: TBD
- Requirement Type: TBD

##### MS22029826-73816: IgnMode (Value: On, Off) (System Requirement)
- Variant: S237
- Stakeholder Requirement State: In Review
- System Requirement State: Draft
- Software Requirement State: Draft
- Primary Discipline: TBD
- Requirement Type: TBD

##### MS22029826-73818: LVSD/HVSD Flag (Value: Not Set, Set) (System Requirement)
- Variant: S237
- Stakeholder Requirement State: In Review
- System Requirement State: Draft
- Software Requirement State: Draft
- Primary Discipline: TBD
- Requirement Type: TBD

##### MS22029826-73819: VAR_CODING_SWITCH_BY_WIRE(Value: 0-Not Present, 1-Present) (System Requirement)
- Variant: S237
- Stakeholder Requirement State: In Review
- System Requirement State: Draft
- Software Requirement State: Draft
- Primary Discipline: TBD
- Requirement Type: TBD

##### MS22029826-73820: SBW1_50(0x250): SBW_WARN (System Requirement)
SBW1_50(0x250): SBW_WARN (0X0-No warning/Default, 0x1-TGS Service Warning, 0x2 Cannot Change gear, 0x3 Condition is not P, 0X4, Brake Not Presses, 0x5-Shift Lock Not Presses, 0x6-Park Switch Failure, 0x7-Shift Lock Switch Failure, 0xF-Signal Invalid)
- Variant: S237
- Stakeholder Requirement State: In Review
- System Requirement State: Draft
- Software Requirement State: Draft
- Primary Discipline: TBD
- Requirement Type: TBD

##### MS22029826-73821: Diag RW Park Switch Struck Chime Enable (Value: 0-Disable, 1-Enable) (System Requirement)
- Variant: S237
- Stakeholder Requirement State: In Review
- System Requirement State: Draft
- Software Requirement State: Draft
- Primary Discipline: TBD
- Requirement Type: TBD

#### MS22029826-73813: Output Requirements (Heading)
- Variant: S237
- Stakeholder Requirement State: In Review
- System Requirement State: Draft
- Software Requirement State: Draft
- Primary Discipline: TBD
- Requirement Type: TBD

##### MS22029826-73815: Park Switch Struck Chime Functional Logic (Value: Off, On) (System Requirement)
- Variant: S237
- Stakeholder Requirement State: In Review
- System Requirement State: Draft
- Software Requirement State: Draft
- Primary Discipline: TBD
- Requirement Type: TBD

#### MS22029826-73814: Performance Requirements (Heading)
- Variant: S237
- Stakeholder Requirement State: In Review
- System Requirement State: Draft
- Software Requirement State: Draft
- Primary Discipline: TBD
- Requirement Type: TBD

##### MS22029826-73817 (System Requirement)
Table- Park Switch Struck Chime Functional Logic
| Ign Mode | LVSD/HVSD Flag | VAR_CODING_SWITCH_ BY_WIRE | Diag RW Park Switch Struck Chime Enable | CAN Signal Missing or Never Received | SBW1_50(0x250): SBW_WARN | Park Switch Struck Chime Functional Logic |
| --- | --- | --- | --- | --- | --- | --- |
| Off | X | X | X | X | X | Off |
| On | Set | X | X | X | X | Off |
| On | Not Set | 0 | X | X | X | Off |
| On | Not Set | 1 | 0 | X | X | Off |
| On | Not Set | 1 | 1 | 1 | X | Off |
| On | Not Set | 1 | 1 | 0 | !=0x6 | Off |
| On | Not Set | 1 | 1 | 0 | 0x6 | On |
- Variant: S237
- Stakeholder Requirement State: In Review
- System Requirement State: Draft
- Software Requirement State: Draft
- Primary Discipline: TBD
- Requirement Type: TBD

### MS22029826-73822: Shift Unlock Switch Struck Chime (Heading)
- Variant: S237
- Stakeholder Requirement State: In Review
- System Requirement State: Draft
- Software Requirement State: Draft
- Primary Discipline: TBD
- Requirement Type: TBD

#### MS22029826-73823: Input Requirements (Heading)
- Variant: S237
- Stakeholder Requirement State: In Review
- System Requirement State: Draft
- Software Requirement State: Draft
- Primary Discipline: TBD
- Requirement Type: TBD

##### MS22029826-73827: IgnMode (Value: On, Off) (System Requirement)
- Variant: S237
- Stakeholder Requirement State: In Review
- System Requirement State: Draft
- Software Requirement State: Draft
- Primary Discipline: TBD
- Requirement Type: TBD

##### MS22029826-73829: LVSD/HVSD Flag (Value: Not Set, Set) (System Requirement)
- Variant: S237
- Stakeholder Requirement State: In Review
- System Requirement State: Draft
- Software Requirement State: Draft
- Primary Discipline: TBD
- Requirement Type: TBD

##### MS22029826-73830: VAR_CODING_SWITCH_BY_WIRE(Value: 0-Not Present, 1-Present) (System Requirement)
- Variant: S237
- Stakeholder Requirement State: In Review
- System Requirement State: Draft
- Software Requirement State: Draft
- Primary Discipline: TBD
- Requirement Type: TBD

##### MS22029826-73831: SBW1_50(0x250): SBW_WARN (System Requirement)
SBW1_50(0x250): SBW_WARN (0X0-No warning/Default, 0x1-TGS Service Warning, 0x2 Cannot Change gear, 0x3 Condition is not P, 0X4, Brake Not Presses, 0x5-Shift Lock Not Presses, 0x6-Park Switch Failure, 0x7-Shift Lock Switch Failure, 0xF-Signal Invalid)
- Variant: S237
- Stakeholder Requirement State: In Review
- System Requirement State: Draft
- Software Requirement State: Draft
- Primary Discipline: TBD
- Requirement Type: TBD

##### MS22029826-73832: Diag RW Shift Unlock Switch Struck Chime Enable (Value: 0-Disable, 1-Enable) (System Requirement)
- Variant: S237
- Stakeholder Requirement State: In Review
- System Requirement State: Draft
- Software Requirement State: Draft
- Primary Discipline: TBD
- Requirement Type: TBD

#### MS22029826-73824: Output Requirements (Heading)
- Variant: S237
- Stakeholder Requirement State: In Review
- System Requirement State: Draft
- Software Requirement State: Draft
- Primary Discipline: TBD
- Requirement Type: TBD

##### MS22029826-73826: Shift Unlock Switch Struck Chime Functional Logic (Value: Off, On) (System Requirement)
- Variant: S237
- Stakeholder Requirement State: In Review
- System Requirement State: Draft
- Software Requirement State: Draft
- Primary Discipline: TBD
- Requirement Type: TBD

#### MS22029826-73825: Performance Requirements (Heading)
- Variant: S237
- Stakeholder Requirement State: In Review
- System Requirement State: Draft
- Software Requirement State: Draft
- Primary Discipline: TBD
- Requirement Type: TBD

##### MS22029826-73828 (System Requirement)
Table- Shift Unlock Switch Struck Chime Functional Logic
| Ign Mode | LVSD/HVSD Flag | VAR_CODING_SWITCH_ BY_WIRE | Diag RW Shift Unlock Switch Struck Chime Enable | CAN Signal Missing or Never Received | SBW1_50(0x250): SBW_WARN | Shift Unlock Switch Struck Chime Functional Logic |
| --- | --- | --- | --- | --- | --- | --- |
| Off | X | X | X | X | X | Off |
| On | Set | X | X | X | X | Off |
| On | Not Set | 0 | X | X | X | Off |
| On | Not Set | 1 | 0 | X | X | Off |
| On | Not Set | 1 | 1 | 1 | X | Off |
| On | Not Set | 1 | 1 | 0 | !=0x7 | Off |
| On | Not Set | 1 | 1 | 0 | 0x7 | On |
- Variant: S237
- Stakeholder Requirement State: In Review
- System Requirement State: Draft
- Software Requirement State: Draft
- Primary Discipline: TBD
- Requirement Type: TBD

### MS22029826-73833: Charge Fault Chime (Heading)
- Variant: S237
- Stakeholder Requirement State: In Review
- System Requirement State: Draft
- Software Requirement State: Draft
- Primary Discipline: TBD
- Requirement Type: TBD

#### MS22029826-73834: Input Requirements (Heading)
- Variant: S237
- Stakeholder Requirement State: In Review
- System Requirement State: Draft
- Software Requirement State: Draft
- Primary Discipline: TBD
- Requirement Type: TBD

##### MS22029826-73839: IgnMode (Value: On, Off) (System Requirement)
- Variant: S237
- Stakeholder Requirement State: In Review
- System Requirement State: Draft
- Software Requirement State: Draft
- Primary Discipline: TBD
- Requirement Type: TBD

##### MS22029826-73840: LVSD/HVSD Flag (Value: Not Set, Set) (System Requirement)
- Variant: S237
- Stakeholder Requirement State: In Review
- System Requirement State: Draft
- Software Requirement State: Draft
- Primary Discipline: TBD
- Requirement Type: TBD

##### MS22029826-73841: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-73842: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-73843: Diag RW Charge Fault Chime Enable (Value: 0-Disable, 1-Enable) (System Requirement)
- Variant: S237
- Stakeholder Requirement State: In Review
- System Requirement State: Draft
- Software Requirement State: Draft
- Primary Discipline: TBD
- Requirement Type: TBD

#### MS22029826-73835: Output Requirements (Heading)
- Variant: S237
- Stakeholder Requirement State: In Review
- System Requirement State: Draft
- Software Requirement State: Draft
- Primary Discipline: TBD
- Requirement Type: TBD

##### MS22029826-73837: Charge Fault Chime Functional Logic (Value: Off, On) (System Requirement)
- Variant: S237
- Stakeholder Requirement State: In Review
- System Requirement State: Draft
- Software Requirement State: Draft
- Primary Discipline: TBD
- Requirement Type: TBD

#### MS22029826-73836: Performance Requirements (Heading)
- Variant: S237
- Stakeholder Requirement State: In Review
- System Requirement State: Draft
- Software Requirement State: Draft
- Primary Discipline: TBD
- Requirement Type: TBD

##### MS22029826-73838 (System Requirement)
Table - Charge Fault Chime Functional Logic
| Ign Mode | LVSD/HVSD Flag | VAR_CODING_VEHICLE_CONTROL_UNIT | Diag RW Charge Fault Chime Enable | CAN Signal Missing or Never Received | VCU10_100(0X30A): ALERT_MSGS | Charge Fault Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x1 | Off |
| On/Off | Not Set | 1 | 1 | 0 | =0x1 | On |
- Variant: S237
- Stakeholder Requirement State: In Review
- System Requirement State: Draft
- Software Requirement State: Draft
- Primary Discipline: TBD
- Requirement Type: TBD

### MS22029826-73844: Charge Complete Chime (Heading)
- Variant: S237
- Stakeholder Requirement State: In Review
- System Requirement State: Draft
- Software Requirement State: Draft
- Primary Discipline: TBD
- Requirement Type: TBD

#### MS22029826-73845: Input Requirements (Heading)
- Variant: S237
- Stakeholder Requirement State: In Review
- System Requirement State: Draft
- Software Requirement State: Draft
- Primary Discipline: TBD
- Requirement Type: TBD

##### MS22029826-73849: IgnMode (Value: On, Off) (System Requirement)
- Variant: S237
- Stakeholder Requirement State: In Review
- System Requirement State: Draft
- Software Requirement State: Draft
- Primary Discipline: TBD
- Requirement Type: TBD

##### MS22029826-73851: LVSD/HVSD Flag (Value: Not Set, Set) (System Requirement)
- Variant: S237
- Stakeholder Requirement State: In Review
- System Requirement State: Draft
- Software Requirement State: Draft
- Primary Discipline: TBD
- Requirement Type: TBD

##### MS22029826-73852: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-73853: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-73854: Diag RW Charge Complete Chime Enable (Value: 0-Disable, 1-Enable) (System Requirement)
- Variant: S237
- Stakeholder Requirement State: In Review
- System Requirement State: Draft
- Software Requirement State: Draft
- Primary Discipline: TBD
- Requirement Type: TBD

#### MS22029826-73846: Output Requirements (Heading)
- Variant: S237
- Stakeholder Requirement State: In Review
- System Requirement State: Draft
- Software Requirement State: Draft
- Primary Discipline: TBD
- Requirement Type: TBD

##### MS22029826-73848: Charge Complete Chime Functional Logic (Value: Off, On) (System Requirement)
- Variant: S237
- Stakeholder Requirement State: In Review
- System Requirement State: Draft
- Software Requirement State: Draft
- Primary Discipline: TBD
- Requirement Type: TBD

#### MS22029826-73847: Performance Requirements (Heading)
- Variant: S237
- Stakeholder Requirement State: In Review
- System Requirement State: Draft
- Software Requirement State: Draft
- Primary Discipline: TBD
- Requirement Type: TBD

##### MS22029826-73850 (System Requirement)
Table - Charge Complete Chime Functional Logic
| Ign Mode | LVSD/HVSD Flag | VAR_CODING_VEHICLE_CONTROL_UNIT | Diag RW Charge Complete Chime Enable | CAN Signal Missing or Never Received | VCU10_100(0X30A): ALERT_MSGS | Charge Complete Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x2 | Off |
| On/Off | Not Set | 1 | 1 | 0 | =0x2 | On |
- Variant: S237
- Stakeholder Requirement State: In Review
- System Requirement State: Draft
- Software Requirement State: Draft
- Primary Discipline: TBD
- Requirement Type: TBD

### MS22029826-73855: Charge Terminate Chime (Heading)
- Variant: S237
- Stakeholder Requirement State: In Review
- System Requirement State: Draft
- Software Requirement State: Draft
- Primary Discipline: TBD
- Requirement Type: TBD

#### MS22029826-73856: Input Requirements (Heading)
- Variant: S237
- Stakeholder Requirement State: In Review
- System Requirement State: Draft
- Software Requirement State: Draft
- Primary Discipline: TBD
- Requirement Type: TBD

##### MS22029826-73860: IgnMode (Value: On, Off) (System Requirement)
- Variant: S237
- Stakeholder Requirement State: In Review
- System Requirement State: Draft
- Software Requirement State: Draft
- Primary Discipline: TBD
- Requirement Type: TBD

##### MS22029826-73862: LVSD/HVSD Flag (Value: Not Set, Set) (System Requirement)
- Variant: S237
- Stakeholder Requirement State: In Review
- System Requirement State: Draft
- Software Requirement State: Draft
- Primary Discipline: TBD
- Requirement Type: TBD

##### MS22029826-73863: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-73864: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-73865: Diag RW Charge Terminate Chime Enable (Value: 0-Disable, 1-Enable) (System Requirement)
- Variant: S237
- Stakeholder Requirement State: In Review
- System Requirement State: Draft
- Software Requirement State: Draft
- Primary Discipline: TBD
- Requirement Type: TBD

#### MS22029826-73857: Output Requirements (Heading)
- Variant: S237
- Stakeholder Requirement State: In Review
- System Requirement State: Draft
- Software Requirement State: Draft
- Primary Discipline: TBD
- Requirement Type: TBD

##### MS22029826-73859: Charge Terminate Chime Functional Logic (Value: Off, On) (System Requirement)
- Variant: S237
- Stakeholder Requirement State: In Review
- System Requirement State: Draft
- Software Requirement State: Draft
- Primary Discipline: TBD
- Requirement Type: TBD

#### MS22029826-73858: Performance Requirements (Heading)
- Variant: S237
- Stakeholder Requirement State: In Review
- System Requirement State: Draft
- Software Requirement State: Draft
- Primary Discipline: TBD
- Requirement Type: TBD

##### MS22029826-73861 (System Requirement)
Table - Charge Terminate Chime Functional Logic
| Ign Mode | LVSD/HVSD Flag | VAR_CODING_VEHICLE_CONTROL_UNIT | Diag RW Charge Terminate Chime Enable | CAN Signal Missing or Never Received | VCU10_100(0X30A): ALERT_MSGS | Charge Terminate Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x3 | Off |
| On/Off | Not Set | 1 | 1 | 0 | =0x3 | On |
- Variant: S237
- Stakeholder Requirement State: In Review
- System Requirement State: Draft
- Software Requirement State: Draft
- Primary Discipline: TBD
- Requirement Type: TBD

### MS22029826-73866: Go Slow Chime (Heading)
- Variant: S237
- Stakeholder Requirement State: In Review
- System Requirement State: Draft
- Software Requirement State: Draft
- Primary Discipline: TBD
- Requirement Type: TBD

#### MS22029826-73867: Input Requirements (Heading)
- Variant: S237
- Stakeholder Requirement State: In Review
- System Requirement State: Draft
- Software Requirement State: Draft
- Primary Discipline: TBD
- Requirement Type: TBD

##### MS22029826-73871: IgnMode (Value: On, Off) (System Requirement)
- Variant: S237
- Stakeholder Requirement State: In Review
- System Requirement State: Draft
- Software Requirement State: Draft
- Primary Discipline: TBD
- Requirement Type: TBD

##### MS22029826-73873: LVSD/HVSD Flag (Value: Not Set, Set) (System Requirement)
- Variant: S237
- Stakeholder Requirement State: In Review
- System Requirement State: Draft
- Software Requirement State: Draft
- Primary Discipline: TBD
- Requirement Type: TBD

##### MS22029826-73874: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-73875: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-73876: Diag RW Go Slow Chime Enable (Value: 0-Disable, 1-Enable) (System Requirement)
- Variant: S237
- Stakeholder Requirement State: In Review
- System Requirement State: Draft
- Software Requirement State: Draft
- Primary Discipline: TBD
- Requirement Type: TBD

#### MS22029826-73868: Output Requirements (Heading)
- Variant: S237
- Stakeholder Requirement State: In Review
- System Requirement State: Draft
- Software Requirement State: Draft
- Primary Discipline: TBD
- Requirement Type: TBD

##### MS22029826-73870: Go slow Chime Functional Logic (Value: Off, On) (System Requirement)
- Variant: S237
- Stakeholder Requirement State: In Review
- System Requirement State: Draft
- Software Requirement State: Draft
- Primary Discipline: TBD
- Requirement Type: TBD

#### MS22029826-73869: Performance Requirements (Heading)
- Variant: S237
- Stakeholder Requirement State: In Review
- System Requirement State: Draft
- Software Requirement State: Draft
- Primary Discipline: TBD
- Requirement Type: TBD

##### MS22029826-73872: Table - Go slow Chime Functional Logic (System Requirement)
Table - Go slow Chime Functional Logic
| Ign Mode | LVSD/HVSD Flag | VAR_CODING_VEHICLE_CONTROL_UNIT | Diag RW Go Slow Chime Enable | CAN Signal Missing or Never Received | VCU10_100(0X30A): ALERT_MSGS | Go Slow Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x4 | Off |
| On/Off | Not Set | 1 | 1 | 0 | =0x4 | On |
- Variant: S237
- Stakeholder Requirement State: In Review
- System Requirement State: Draft
- Software Requirement State: Draft
- Primary Discipline: TBD
- Requirement Type: TBD

### MS22029826-73877: Stop Car Status Chime (Heading)
- Variant: S237
- Stakeholder Requirement State: In Review
- System Requirement State: Draft
- Software Requirement State: Draft
- Primary Discipline: TBD
- Requirement Type: TBD

#### MS22029826-73878: Input Requirements (Heading)
- Variant: S237
- Stakeholder Requirement State: In Review
- System Requirement State: Draft
- Software Requirement State: Draft
- Primary Discipline: TBD
- Requirement Type: TBD

##### MS22029826-73882: IgnMode (Value: On, Off) (System Requirement)
- Variant: S237
- Stakeholder Requirement State: In Review
- System Requirement State: Draft
- Software Requirement State: Draft
- Primary Discipline: TBD
- Requirement Type: TBD

##### MS22029826-73884: LVSD/HVSD Flag (Value: Not Set, Set) (System Requirement)
- Variant: S237
- Stakeholder Requirement State: In Review
- System Requirement State: Draft
- Software Requirement State: Draft
- Primary Discipline: TBD
- Requirement Type: TBD

##### MS22029826-73885: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-73886: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-73887: Diag RW Stop car status chime Enable (Value: 0-Disable, 1-Enable) (System Requirement)
- Variant: S237
- Stakeholder Requirement State: In Review
- System Requirement State: Draft
- Software Requirement State: Draft
- Primary Discipline: TBD
- Requirement Type: TBD

#### MS22029826-73879: Output Requirements (Heading)
- Variant: S237
- Stakeholder Requirement State: In Review
- System Requirement State: Draft
- Software Requirement State: Draft
- Primary Discipline: TBD
- Requirement Type: TBD

##### MS22029826-73881: Stop car Status Chime Functional Logic (Value: Off, On) (System Requirement)
- Variant: S237
- Stakeholder Requirement State: In Review
- System Requirement State: Draft
- Software Requirement State: Draft
- Primary Discipline: TBD
- Requirement Type: TBD

#### MS22029826-73880: Performance Requirements (Heading)
- Variant: S237
- Stakeholder Requirement State: In Review
- System Requirement State: Draft
- Software Requirement State: Draft
- Primary Discipline: TBD
- Requirement Type: TBD

##### MS22029826-73883 (System Requirement)
Table - Stop car Status Chime Functional Logic
| Ign Mode | LVSD/HVSD Flag | VAR_CODING_VEHICLE_CONTROL_UNIT | Diag RW Stop car status Chime Enable | CAN Signal Missing or Never Received | VCU10_100(0X30A): ALERT_MSGS | Stop car status Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x5 | Off |
| On/Off | Not Set | 1 | 1 | 0 | =0x5 | On |
- Variant: S237
- Stakeholder Requirement State: In Review
- System Requirement State: Draft
- Software Requirement State: Draft
- Primary Discipline: TBD
- Requirement Type: TBD

### MS22029826-73888: Safe Mode Chime (Heading)
- Variant: S237
- Stakeholder Requirement State: In Review
- System Requirement State: Draft
- Software Requirement State: Draft
- Primary Discipline: TBD
- Requirement Type: TBD

#### MS22029826-73889: Input Requirements (Heading)
- Variant: S237
- Stakeholder Requirement State: In Review
- System Requirement State: Draft
- Software Requirement State: Draft
- Primary Discipline: TBD
- Requirement Type: TBD

##### MS22029826-73893: IgnMode (Value: On, Off) (System Requirement)
- Variant: S237
- Stakeholder Requirement State: In Review
- System Requirement State: Draft
- Software Requirement State: Draft
- Primary Discipline: TBD
- Requirement Type: TBD

##### MS22029826-73895: LVSD/HVSD Flag (Value: Not Set, Set) (System Requirement)
- Variant: S237
- Stakeholder Requirement State: In Review
- System Requirement State: Draft
- Software Requirement State: Draft
- Primary Discipline: TBD
- Requirement Type: TBD

##### MS22029826-73896: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-73897: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-73898: Diag RW Safe Mode Chime Enable (Value: 0-Disable, 1-Enable) (System Requirement)
- Variant: S237
- Stakeholder Requirement State: In Review
- System Requirement State: Draft
- Software Requirement State: Draft
- Primary Discipline: TBD
- Requirement Type: TBD

#### MS22029826-73890: Output Requirements (Heading)
- Variant: S237
- Stakeholder Requirement State: In Review
- System Requirement State: Draft
- Software Requirement State: Draft
- Primary Discipline: TBD
- Requirement Type: TBD

##### MS22029826-73892: Safe Mode Chime Functional Logic (Value: Off, On) (System Requirement)
- Variant: S237
- Stakeholder Requirement State: In Review
- System Requirement State: Draft
- Software Requirement State: Draft
- Primary Discipline: TBD
- Requirement Type: TBD

#### MS22029826-73891: Performance Requirements (Heading)
- Variant: S237
- Stakeholder Requirement State: In Review
- System Requirement State: Draft
- Software Requirement State: Draft
- Primary Discipline: TBD
- Requirement Type: TBD

##### MS22029826-73894: Table - Safe Mode Chime Functional Logic (System Requirement)
Table - Safe Mode Chime Functional Logic
| Ign Mode | LVSD/HVSD Flag | VAR_CODING_VEHICLE_CONTROL_UNIT | Diag RW Safe Mode Chime Enable | CAN Signal Missing or Never Received | VCU10_100(0X30A): ALERT_MSGS | Safe Mode Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x7 | Off |
| On/Off | Not Set | 1 | 1 | 0 | =0x7 | On |
- Variant: S237
- Stakeholder Requirement State: In Review
- System Requirement State: Draft
- Software Requirement State: Draft
- Primary Discipline: TBD
- Requirement Type: TBD

### MS22029826-73899: Drive Fault Chime (Heading)
- Variant: S237
- Stakeholder Requirement State: In Review
- System Requirement State: Draft
- Software Requirement State: Draft
- Primary Discipline: TBD
- Requirement Type: TBD

#### MS22029826-73900: Input Requirements (Heading)
- Variant: S237
- Stakeholder Requirement State: In Review
- System Requirement State: Draft
- Software Requirement State: Draft
- Primary Discipline: TBD
- Requirement Type: TBD

##### MS22029826-73904: IgnMode (Value: On, Off) (System Requirement)
- Variant: S237
- Stakeholder Requirement State: In Review
- System Requirement State: Draft
- Software Requirement State: Draft
- Primary Discipline: TBD
- Requirement Type: TBD

##### MS22029826-73906: LVSD/HVSD Flag (Value: Not Set, Set) (System Requirement)
- Variant: S237
- Stakeholder Requirement State: In Review
- System Requirement State: Draft
- Software Requirement State: Draft
- Primary Discipline: TBD
- Requirement Type: TBD

##### MS22029826-73907: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-73908: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-73909: Diag RW Drive Fault Chime Enable (Value: 0-Disable, 1-Enable) (System Requirement)
- Variant: S237
- Stakeholder Requirement State: In Review
- System Requirement State: Draft
- Software Requirement State: Draft
- Primary Discipline: TBD
- Requirement Type: TBD

#### MS22029826-73901: Output Requirements (Heading)
- Variant: S237
- Stakeholder Requirement State: In Review
- System Requirement State: Draft
- Software Requirement State: Draft
- Primary Discipline: TBD
- Requirement Type: TBD

##### MS22029826-73903: Drive Fault Chime Functional Logic (Value: Off, On) (System Requirement)
- Variant: S237
- Stakeholder Requirement State: In Review
- System Requirement State: Draft
- Software Requirement State: Draft
- Primary Discipline: TBD
- Requirement Type: TBD

#### MS22029826-73902: Performance Requirements (Heading)
- Variant: S237
- Stakeholder Requirement State: In Review
- System Requirement State: Draft
- Software Requirement State: Draft
- Primary Discipline: TBD
- Requirement Type: TBD

##### MS22029826-73905 (System Requirement)
Table - Drive Fault Chime Functional Logic
| Ign Mode | LVSD/HVSD Flag | VAR_CODING_VEHICLE_CONTROL_UNIT | Diag RW Drive Fault Chime Enable | CAN Signal Missing or Never Received | VCU10_100(0X30A): ALERT_MSGS | Drive Fault Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x8 | Off |
| On/Off | Not Set | 1 | 1 | 0 | =0x8 | On |
- Variant: S237
- Stakeholder Requirement State: In Review
- System Requirement State: Draft
- Software Requirement State: Draft
- Primary Discipline: TBD
- Requirement Type: TBD

### MS22029826-73910: Restart Chime (Heading)
- Variant: S237
- Stakeholder Requirement State: In Review
- System Requirement State: Draft
- Software Requirement State: Draft
- Primary Discipline: TBD
- Requirement Type: TBD

#### MS22029826-73911: Input Requirements (Heading)
- Variant: S237
- Stakeholder Requirement State: In Review
- System Requirement State: Draft
- Software Requirement State: Draft
- Primary Discipline: TBD
- Requirement Type: TBD

##### MS22029826-73915: IgnMode (Value: On, Off) (System Requirement)
- Variant: S237
- Stakeholder Requirement State: In Review
- System Requirement State: Draft
- Software Requirement State: Draft
- Primary Discipline: TBD
- Requirement Type: TBD

##### MS22029826-73917: LVSD/HVSD Flag (Value: Not Set, Set) (System Requirement)
- Variant: S237
- Stakeholder Requirement State: In Review
- System Requirement State: Draft
- Software Requirement State: Draft
- Primary Discipline: TBD
- Requirement Type: TBD

##### MS22029826-73918: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-73919: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-73920: Diag RW Restart Chime Enable (Value: 0-Disable, 1-Enable) (System Requirement)
- Variant: S237
- Stakeholder Requirement State: In Review
- System Requirement State: Draft
- Software Requirement State: Draft
- Primary Discipline: TBD
- Requirement Type: TBD

#### MS22029826-73912: Output Requirements (Heading)
- Variant: S237
- Stakeholder Requirement State: In Review
- System Requirement State: Draft
- Software Requirement State: Draft
- Primary Discipline: TBD
- Requirement Type: TBD

##### MS22029826-73914: Restart Chime Functional Logic (Value: Off, On) (System Requirement)
- Variant: S237
- Stakeholder Requirement State: In Review
- System Requirement State: Draft
- Software Requirement State: Draft
- Primary Discipline: TBD
- Requirement Type: TBD

#### MS22029826-73913: Performance Requirements (Heading)
- Variant: S237
- Stakeholder Requirement State: In Review
- System Requirement State: Draft
- Software Requirement State: Draft
- Primary Discipline: TBD
- Requirement Type: TBD

##### MS22029826-73916: Table - Restart Chime Functional Logic (System Requirement)
Table - Restart Chime Functional Logic
| Ign Mode | LVSD/HVSD Flag | VAR_CODING_VEHICLE_CONTROL_UNIT | Diag RW Restart Chime Enable | CAN Signal Missing or Never Received | VCU10_100(0X30A): ALERT_MSGS | Restart Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x9 | Off |
| On/Off | Not Set | 1 | 1 | 0 | =0x9 | On |
- Variant: S237
- Stakeholder Requirement State: In Review
- System Requirement State: Draft
- Software Requirement State: Draft
- Primary Discipline: TBD
- Requirement Type: TBD

### MS22029826-74230: EV Service Due Chime (Heading)
- Variant: S237
- Stakeholder Requirement State: In Review
- System Requirement State: Draft
- Software Requirement State: Draft
- Primary Discipline: TBD
- Requirement Type: TBD

#### MS22029826-74231: Input Requirements (Heading)
- Variant: S237
- Stakeholder Requirement State: In Review
- System Requirement State: Draft
- Software Requirement State: Draft
- Primary Discipline: TBD
- Requirement Type: TBD

##### MS22029826-74235: IgnMode (Value: On, Off) (System Requirement)
- Variant: S237
- Stakeholder Requirement State: In Review
- System Requirement State: Draft
- Software Requirement State: Draft
- Primary Discipline: TBD
- Requirement Type: TBD

##### MS22029826-74237: LVSD/HVSD Flag (Value: Not Set, Set) (System Requirement)
- Variant: S237
- Stakeholder Requirement State: In Review
- System Requirement State: Draft
- Software Requirement State: Draft
- Primary Discipline: TBD
- Requirement Type: TBD

##### MS22029826-74238: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74239: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74240: Diag RW EV Service Due Chime Enable (Value: 0-Disable, 1-Enable) (System Requirement)
- Variant: S237
- Stakeholder Requirement State: In Review
- System Requirement State: Draft
- Software Requirement State: Draft
- Primary Discipline: TBD
- Requirement Type: TBD

#### MS22029826-74232: Output Requirements (Heading)
- Variant: S237
- Stakeholder Requirement State: In Review
- System Requirement State: Draft
- Software Requirement State: Draft
- Primary Discipline: TBD
- Requirement Type: TBD

##### MS22029826-74234: EV Service Due Chime Functional Logic (Value: Off, On) (System Requirement)
- Variant: S237
- Stakeholder Requirement State: In Review
- System Requirement State: Draft
- Software Requirement State: Draft
- Primary Discipline: TBD
- Requirement Type: TBD

#### MS22029826-74233: Performance Requirements (Heading)
- Variant: S237
- Stakeholder Requirement State: In Review
- System Requirement State: Draft
- Software Requirement State: Draft
- Primary Discipline: TBD
- Requirement Type: TBD

##### MS22029826-74236 (System Requirement)
Table - EV Service Due Chime Functional Logic
| Ign Mode | LVSD/HVSD Flag | VAR_CODING_VEHICLE_CONTROL_UNIT | Diag RW EV Service Due Chime Enable | CAN Signal Missing or Never Received | VCU10_100(0X30A): ALERT_MSGS | EV Service Due Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0xB | Off |
| On/Off | Not Set | 1 | 1 | 0 | =0xB | On |
- Variant: S237
- Stakeholder Requirement State: In Review
- System Requirement State: Draft
- Software Requirement State: Draft
- Primary Discipline: TBD
- Requirement Type: TBD

### MS22029826-74241: Stopping Chime (Heading)
- Variant: S237
- Stakeholder Requirement State: In Review
- System Requirement State: Draft
- Software Requirement State: Draft
- Primary Discipline: TBD
- Requirement Type: TBD

#### MS22029826-74242: Input Requirements (Heading)
- Variant: S237
- Stakeholder Requirement State: In Review
- System Requirement State: Draft
- Software Requirement State: Draft
- Primary Discipline: TBD
- Requirement Type: TBD

##### MS22029826-74246: IgnMode (Value: On, Off) (System Requirement)
- Variant: S237
- Stakeholder Requirement State: In Review
- System Requirement State: Draft
- Software Requirement State: Draft
- Primary Discipline: TBD
- Requirement Type: TBD

##### MS22029826-74248: LVSD/HVSD Flag (Value: Not Set, Set) (System Requirement)
- Variant: S237
- Stakeholder Requirement State: In Review
- System Requirement State: Draft
- Software Requirement State: Draft
- Primary Discipline: TBD
- Requirement Type: TBD

##### MS22029826-74249: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74250: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74251: Diag RW Stopping Chime Enable (Value: 0-Disable, 1-Enable) (System Requirement)
- Variant: S237
- Stakeholder Requirement State: In Review
- System Requirement State: Draft
- Software Requirement State: Draft
- Primary Discipline: TBD
- Requirement Type: TBD

#### MS22029826-74243: Output Requirements (Heading)
- Variant: S237
- Stakeholder Requirement State: In Review
- System Requirement State: Draft
- Software Requirement State: Draft
- Primary Discipline: TBD
- Requirement Type: TBD

##### MS22029826-74245: Stopping Chime Functional Logic (Value: Off, On) (System Requirement)
- Variant: S237
- Stakeholder Requirement State: In Review
- System Requirement State: Draft
- Software Requirement State: Draft
- Primary Discipline: TBD
- Requirement Type: TBD

#### MS22029826-74244: Performance Requirements (Heading)
- Variant: S237
- Stakeholder Requirement State: In Review
- System Requirement State: Draft
- Software Requirement State: Draft
- Primary Discipline: TBD
- Requirement Type: TBD

##### MS22029826-74247: Table - Stopping Chime Functional Logic (System Requirement)
Table - Stopping Chime Functional Logic
| Ign Mode | LVSD/HVSD Flag | VAR_CODING_VEHICLE_CONTROL_UNIT | Diag RW Stopping Chime Enable | CAN Signal Missing or Never Received | VCU10_100(0X30A): ALERT_MSGS | Stopping Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0xC | Off |
| On/Off | Not Set | 1 | 1 | 0 | =0xC | On |
- Variant: S237
- Stakeholder Requirement State: In Review
- System Requirement State: Draft
- Software Requirement State: Draft
- Primary Discipline: TBD
- Requirement Type: TBD

### MS22029826-74252: Insert Plug Full Chime (Heading)
- Variant: S237
- Stakeholder Requirement State: In Review
- System Requirement State: Draft
- Software Requirement State: Draft
- Primary Discipline: TBD
- Requirement Type: TBD

#### MS22029826-74253: Input Requirements (Heading)
- Variant: S237
- Stakeholder Requirement State: In Review
- System Requirement State: Draft
- Software Requirement State: Draft
- Primary Discipline: TBD
- Requirement Type: TBD

##### MS22029826-74257: IgnMode (Value: On, Off) (System Requirement)
- Variant: S237
- Stakeholder Requirement State: In Review
- System Requirement State: Draft
- Software Requirement State: Draft
- Primary Discipline: TBD
- Requirement Type: TBD

##### MS22029826-74259: LVSD/HVSD Flag (Value: Not Set, Set) (System Requirement)
- Variant: S237
- Stakeholder Requirement State: In Review
- System Requirement State: Draft
- Software Requirement State: Draft
- Primary Discipline: TBD
- Requirement Type: TBD

##### MS22029826-74260: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74261: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74262: Diag RW Insert Plug Full Chime Enable (Value: 0-Disable, 1-Enable) (System Requirement)
- Variant: S237
- Stakeholder Requirement State: In Review
- System Requirement State: Draft
- Software Requirement State: Draft
- Primary Discipline: TBD
- Requirement Type: TBD

#### MS22029826-74254: Output Requirements (Heading)
- Variant: S237
- Stakeholder Requirement State: In Review
- System Requirement State: Draft
- Software Requirement State: Draft
- Primary Discipline: TBD
- Requirement Type: TBD

##### MS22029826-74256: Insert Plug Full Chime Functional Logic (Value: Off, On) (System Requirement)
- Variant: S237
- Stakeholder Requirement State: In Review
- System Requirement State: Draft
- Software Requirement State: Draft
- Primary Discipline: TBD
- Requirement Type: TBD

#### MS22029826-74255: Performance Requirements (Heading)
- Variant: S237
- Stakeholder Requirement State: In Review
- System Requirement State: Draft
- Software Requirement State: Draft
- Primary Discipline: TBD
- Requirement Type: TBD

##### MS22029826-74258 (System Requirement)
Table - Insert Plug Full Chime Functional Logic
| Ign Mode | LVSD/HVSD Flag | VAR_CODING_VEHICLE_CONTROL_UNIT | Diag RW Insert Plug Full Chime Enable | CAN Signal Missing or Never Received | VCU10_100(0X30A): ALERT_MSGS | Insert Plug Full Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0xD | Off |
| On/Off | Not Set | 1 | 1 | 0 | =0xD | On |
- Variant: S237
- Stakeholder Requirement State: In Review
- System Requirement State: Draft
- Software Requirement State: Draft
- Primary Discipline: TBD
- Requirement Type: TBD

### MS22029826-74263: Power Save Mode Chime (Heading)
- Variant: S237
- Stakeholder Requirement State: In Review
- System Requirement State: Draft
- Software Requirement State: Draft
- Primary Discipline: TBD
- Requirement Type: TBD

#### MS22029826-74264: Input Requirements (Heading)
- Variant: S237
- Stakeholder Requirement State: In Review
- System Requirement State: Draft
- Software Requirement State: Draft
- Primary Discipline: TBD
- Requirement Type: TBD

##### MS22029826-74268: IgnMode (Value: On, Off) (System Requirement)
- Variant: S237
- Stakeholder Requirement State: In Review
- System Requirement State: Draft
- Software Requirement State: Draft
- Primary Discipline: TBD
- Requirement Type: TBD

##### MS22029826-74270: LVSD/HVSD Flag (Value: Not Set, Set) (System Requirement)
- Variant: S237
- Stakeholder Requirement State: In Review
- System Requirement State: Draft
- Software Requirement State: Draft
- Primary Discipline: TBD
- Requirement Type: TBD

##### MS22029826-74271: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74272: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74273: Diag RW Power Save Mode Chime Enable (Value: 0-Disable, 1-Enable) (System Requirement)
- Variant: S237
- Stakeholder Requirement State: In Review
- System Requirement State: Draft
- Software Requirement State: Draft
- Primary Discipline: TBD
- Requirement Type: TBD

#### MS22029826-74265: Output Requirements (Heading)
- Variant: S237
- Stakeholder Requirement State: In Review
- System Requirement State: Draft
- Software Requirement State: Draft
- Primary Discipline: TBD
- Requirement Type: TBD

##### MS22029826-74267: Power Save Mode Chime Functional Logic (Value: Off, On) (System Requirement)
- Variant: S237
- Stakeholder Requirement State: In Review
- System Requirement State: Draft
- Software Requirement State: Draft
- Primary Discipline: TBD
- Requirement Type: TBD

#### MS22029826-74266: Performance Requirements (Heading)
- Variant: S237
- Stakeholder Requirement State: In Review
- System Requirement State: Draft
- Software Requirement State: Draft
- Primary Discipline: TBD
- Requirement Type: TBD

##### MS22029826-74269 (System Requirement)
Table - Power Save Mode Chime Functional Logic
| Ign Mode | LVSD/HVSD Flag | VAR_CODING_VEHICLE_CONTROL_UNIT | Diag RW Power Save Mode Chime Enable | CAN Signal Missing or Never Received | VCU10_100(0X30A): ALERT_MSGS | Power Save Mode Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0xE | Off |
| On/Off | Not Set | 1 | 1 | 0 | =0xE | On |
- Variant: S237
- Stakeholder Requirement State: In Review
- System Requirement State: Draft
- Software Requirement State: Draft
- Primary Discipline: TBD
- Requirement Type: TBD

### MS22029826-74276: Shift Gear to N Chime (Heading)
- Variant: S237
- Stakeholder Requirement State: In Review
- System Requirement State: Draft
- Software Requirement State: Draft
- Primary Discipline: TBD
- Requirement Type: TBD

#### MS22029826-74277: Input Requirements (Heading)
- Variant: S237
- Stakeholder Requirement State: In Review
- System Requirement State: Draft
- Software Requirement State: Draft
- Primary Discipline: TBD
- Requirement Type: TBD

##### MS22029826-74281: IgnMode (Value: On, Off) (System Requirement)
- Variant: S237
- Stakeholder Requirement State: In Review
- System Requirement State: Draft
- Software Requirement State: Draft
- Primary Discipline: TBD
- Requirement Type: TBD

##### MS22029826-74283: LVSD/HVSD Flag (Value: Not Set, Set) (System Requirement)
- Variant: S237
- Stakeholder Requirement State: In Review
- System Requirement State: Draft
- Software Requirement State: Draft
- Primary Discipline: TBD
- Requirement Type: TBD

##### MS22029826-74284: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74285: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74286: Diag RW Shift Gear to N Chime Enable (Value: 0-Disable, 1-Enable) (System Requirement)
- Variant: S237
- Stakeholder Requirement State: In Review
- System Requirement State: Draft
- Software Requirement State: Draft
- Primary Discipline: TBD
- Requirement Type: TBD

#### MS22029826-74278: Output Requirements (Heading)
- Variant: S237
- Stakeholder Requirement State: In Review
- System Requirement State: Draft
- Software Requirement State: Draft
- Primary Discipline: TBD
- Requirement Type: TBD

##### MS22029826-74280: Shift Gear to N Chime Functional Logic (Value: Off, On) (System Requirement)
- Variant: S237
- Stakeholder Requirement State: In Review
- System Requirement State: Draft
- Software Requirement State: Draft
- Primary Discipline: TBD
- Requirement Type: TBD

#### MS22029826-74279: Performance Requirements (Heading)
- Variant: S237
- Stakeholder Requirement State: In Review
- System Requirement State: Draft
- Software Requirement State: Draft
- Primary Discipline: TBD
- Requirement Type: TBD

##### MS22029826-74282 (System Requirement)
Table - Shift Gear to N Chime Functional Logic
| Ign Mode | LVSD/HVSD Flag | VAR_CODING_VEHICLE_CONTROL_UNIT | Diag RW Shift Gear to N Chime Enable | CAN Signal Missing or Never Received | VCU10_100(0X30A): ALERT_MSGS | Shift Gear to N Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0xF | Off |
| On/Off | Not Set | 1 | 1 | 0 | =0xF | On |
- Variant: S237
- Stakeholder Requirement State: In Review
- System Requirement State: Draft
- Software Requirement State: Draft
- Primary Discipline: TBD
- Requirement Type: TBD

### MS22029826-74287: Release Throttle Chime (Heading)
- Variant: S237
- Stakeholder Requirement State: In Review
- System Requirement State: Draft
- Software Requirement State: Draft
- Primary Discipline: TBD
- Requirement Type: TBD

#### MS22029826-74288: Input Requirements (Heading)
- Variant: S237
- Stakeholder Requirement State: In Review
- System Requirement State: Draft
- Software Requirement State: Draft
- Primary Discipline: TBD
- Requirement Type: TBD

##### MS22029826-74292: IgnMode (Value: On, Off) (System Requirement)
- Variant: S237
- Stakeholder Requirement State: In Review
- System Requirement State: Draft
- Software Requirement State: Draft
- Primary Discipline: TBD
- Requirement Type: TBD

##### MS22029826-74294: LVSD/HVSD Flag (Value: Not Set, Set) (System Requirement)
- Variant: S237
- Stakeholder Requirement State: In Review
- System Requirement State: Draft
- Software Requirement State: Draft
- Primary Discipline: TBD
- Requirement Type: TBD

##### MS22029826-74295: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74296: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74297: Diag RW Release Throttle Chime Enable (Value: 0-Disable, 1-Enable) (System Requirement)
- Variant: S237
- Stakeholder Requirement State: In Review
- System Requirement State: Draft
- Software Requirement State: Draft
- Primary Discipline: TBD
- Requirement Type: TBD

#### MS22029826-74289: Output Requirements (Heading)
- Variant: S237
- Stakeholder Requirement State: In Review
- System Requirement State: Draft
- Software Requirement State: Draft
- Primary Discipline: TBD
- Requirement Type: TBD

##### MS22029826-74291: Release Throttle Chime Functional Logic (Value: Off, On) (System Requirement)
- Variant: S237
- Stakeholder Requirement State: In Review
- System Requirement State: Draft
- Software Requirement State: Draft
- Primary Discipline: TBD
- Requirement Type: TBD

#### MS22029826-74290: Performance Requirements (Heading)
- Variant: S237
- Stakeholder Requirement State: In Review
- System Requirement State: Draft
- Software Requirement State: Draft
- Primary Discipline: TBD
- Requirement Type: TBD

##### MS22029826-74293 (System Requirement)
Table - Release Throttle Chime Functional Logic
| Ign Mode | LVSD/HVSD Flag | VAR_CODING_VEHICLE_CONTROL_UNIT | Diag RW Release Throttle Chime Enable | CAN Signal Missing or Never Received | VCU10_100(0X30A): ALERT_MSGS | Release Throttle Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0xC | Off |
| On/Off | Not Set | 1 | 1 | 0 | =0xC | On |
- Variant: S237
- Stakeholder Requirement State: In Review
- System Requirement State: Draft
- Software Requirement State: Draft
- Primary Discipline: TBD
- Requirement Type: TBD

### MS22029826-74298: Unplug CAR Chime (Heading)
- Variant: S237
- Stakeholder Requirement State: In Review
- System Requirement State: Draft
- Software Requirement State: Draft
- Primary Discipline: TBD
- Requirement Type: TBD

#### MS22029826-74299: Input Requirements (Heading)
- Variant: S237
- Stakeholder Requirement State: In Review
- System Requirement State: Draft
- Software Requirement State: Draft
- Primary Discipline: TBD
- Requirement Type: TBD

##### MS22029826-74303: IgnMode (Value: On, Off) (System Requirement)
- Variant: S237
- Stakeholder Requirement State: In Review
- System Requirement State: Draft
- Software Requirement State: Draft
- Primary Discipline: TBD
- Requirement Type: TBD

##### MS22029826-74305: LVSD/HVSD Flag (Value: Not Set, Set) (System Requirement)
- Variant: S237
- Stakeholder Requirement State: In Review
- System Requirement State: Draft
- Software Requirement State: Draft
- Primary Discipline: TBD
- Requirement Type: TBD

##### MS22029826-74306: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74307: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74308: Diag RW Unplug CAR Chime Enable (Value: 0-Disable, 1-Enable) (System Requirement)
- Variant: S237
- Stakeholder Requirement State: In Review
- System Requirement State: Draft
- Software Requirement State: Draft
- Primary Discipline: TBD
- Requirement Type: TBD

#### MS22029826-74300: Output Requirements (Heading)
- Variant: S237
- Stakeholder Requirement State: In Review
- System Requirement State: Draft
- Software Requirement State: Draft
- Primary Discipline: TBD
- Requirement Type: TBD

##### MS22029826-74302: Unplug CAR Chime Functional Logic (Value: Off, On) (System Requirement)
- Variant: S237
- Stakeholder Requirement State: In Review
- System Requirement State: Draft
- Software Requirement State: Draft
- Primary Discipline: TBD
- Requirement Type: TBD

#### MS22029826-74301: Performance Requirements (Heading)
- Variant: S237
- Stakeholder Requirement State: In Review
- System Requirement State: Draft
- Software Requirement State: Draft
- Primary Discipline: TBD
- Requirement Type: TBD

##### MS22029826-74304 (System Requirement)
Table - Unplug CAR Chime Functional Logic
| Ign Mode | LVSD/HVSD Flag | VAR_CODING_VEHICLE_CONTROL_UNIT | Diag RW Unplug CAR Chime Enable | CAN Signal Missing or Never Received | VCU10_100(0X30A): ALERT_MSGS | Unplug CAR Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x11 | Off |
| On/Off | Not Set | 1 | 1 | 0 | =0x11 | On |
- Variant: S237
- Stakeholder Requirement State: In Review
- System Requirement State: Draft
- Software Requirement State: Draft
- Primary Discipline: TBD
- Requirement Type: TBD

### MS22029826-74309: Turn On Mains Chime (Heading)
- Variant: S237
- Stakeholder Requirement State: In Review
- System Requirement State: Draft
- Software Requirement State: Draft
- Primary Discipline: TBD
- Requirement Type: TBD

#### MS22029826-74310: Input Requirements (Heading)
- Variant: S237
- Stakeholder Requirement State: In Review
- System Requirement State: Draft
- Software Requirement State: Draft
- Primary Discipline: TBD
- Requirement Type: TBD

##### MS22029826-74314: IgnMode (Value: On, Off) (System Requirement)
- Variant: S237
- Stakeholder Requirement State: In Review
- System Requirement State: Draft
- Software Requirement State: Draft
- Primary Discipline: TBD
- Requirement Type: TBD

##### MS22029826-74316: LVSD/HVSD Flag (Value: Not Set, Set) (System Requirement)
- Variant: S237
- Stakeholder Requirement State: In Review
- System Requirement State: Draft
- Software Requirement State: Draft
- Primary Discipline: TBD
- Requirement Type: TBD

##### MS22029826-74317: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74318: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74319: Diag RW Turn On Mains Chime Enable (Value: 0-Disable, 1-Enable) (System Requirement)
- Variant: S237
- Stakeholder Requirement State: In Review
- System Requirement State: Draft
- Software Requirement State: Draft
- Primary Discipline: TBD
- Requirement Type: TBD

#### MS22029826-74311: Output Requirements (Heading)
- Variant: S237
- Stakeholder Requirement State: In Review
- System Requirement State: Draft
- Software Requirement State: Draft
- Primary Discipline: TBD
- Requirement Type: TBD

##### MS22029826-74313: Turn On Mains Chime Functional Logic (Value: Off, On) (System Requirement)
- Variant: S237
- Stakeholder Requirement State: In Review
- System Requirement State: Draft
- Software Requirement State: Draft
- Primary Discipline: TBD
- Requirement Type: TBD

#### MS22029826-74312: Performance Requirements (Heading)
- Variant: S237
- Stakeholder Requirement State: In Review
- System Requirement State: Draft
- Software Requirement State: Draft
- Primary Discipline: TBD
- Requirement Type: TBD

##### MS22029826-74315 (System Requirement)
Table - Turn On Mains Chime Functional Logic
| Ign Mode | LVSD/HVSD Flag | VAR_CODING_VEHICLE_CONTROL_UNIT | Diag RW Turn On Mains Chime Enable | CAN Signal Missing or Never Received | VCU10_100(0X30A): ALERT_MSGS | Turn On Mains Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x12 | Off |
| On/Off | Not Set | 1 | 1 | 0 | =0x12 | On |
- Variant: S237
- Stakeholder Requirement State: In Review
- System Requirement State: Draft
- Software Requirement State: Draft
- Primary Discipline: TBD
- Requirement Type: TBD

### MS22029826-74344: Charge Car Chime (Heading)
- Variant: S237
- Stakeholder Requirement State: In Review
- System Requirement State: Draft
- Software Requirement State: Draft
- Primary Discipline: TBD
- Requirement Type: TBD

#### MS22029826-74345: Input Requirements (Heading)
- Variant: S237
- Stakeholder Requirement State: In Review
- System Requirement State: Draft
- Software Requirement State: Draft
- Primary Discipline: TBD
- Requirement Type: TBD

##### MS22029826-74349: IgnMode (Value: On, Off) (System Requirement)
- Variant: S237
- Stakeholder Requirement State: In Review
- System Requirement State: Draft
- Software Requirement State: Draft
- Primary Discipline: TBD
- Requirement Type: TBD

##### MS22029826-74351: LVSD/HVSD Flag (Value: Not Set, Set) (System Requirement)
- Variant: S237
- Stakeholder Requirement State: In Review
- System Requirement State: Draft
- Software Requirement State: Draft
- Primary Discipline: TBD
- Requirement Type: TBD

##### MS22029826-74352: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74353: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74354: Diag RW Charge CAR Chime Enable (Value: 0-Disable, 1-Enable) (System Requirement)
- Variant: S237
- Stakeholder Requirement State: In Review
- System Requirement State: Draft
- Software Requirement State: Draft
- Primary Discipline: TBD
- Requirement Type: TBD

#### MS22029826-74346: Output Requirements (Heading)
- Variant: S237
- Stakeholder Requirement State: In Review
- System Requirement State: Draft
- Software Requirement State: Draft
- Primary Discipline: TBD
- Requirement Type: TBD

##### MS22029826-74348: Charge CAR Chime Functional Logic (Value: Off, On) (System Requirement)
- Variant: S237
- Stakeholder Requirement State: In Review
- System Requirement State: Draft
- Software Requirement State: Draft
- Primary Discipline: TBD
- Requirement Type: TBD

#### MS22029826-74347: Performance Requirements (Heading)
- Variant: S237
- Stakeholder Requirement State: In Review
- System Requirement State: Draft
- Software Requirement State: Draft
- Primary Discipline: TBD
- Requirement Type: TBD

##### MS22029826-74350 (System Requirement)
Table - Charge CAR Chime Functional Logic
| Ign Mode | LVSD/HVSD Flag | VAR_CODING_VEHICLE_CONTROL_UNIT | Diag RW Charge CAR Chime Enable | CAN Signal Missing or Never Received | VCU10_100(0X30A): ALERT_MSGS | Charge CAR Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x15 | Off |
| On/Off | Not Set | 1 | 1 | 0 | =0x15 | On |
- Variant: S237
- Stakeholder Requirement State: In Review
- System Requirement State: Draft
- Software Requirement State: Draft
- Primary Discipline: TBD
- Requirement Type: TBD

### MS22029826-74355: Activate Revive Chime (Heading)
- Variant: S237
- Stakeholder Requirement State: In Review
- System Requirement State: Draft
- Software Requirement State: Draft
- Primary Discipline: TBD
- Requirement Type: TBD

#### MS22029826-74356: Input Requirements (Heading)
- Variant: S237
- Stakeholder Requirement State: In Review
- System Requirement State: Draft
- Software Requirement State: Draft
- Primary Discipline: TBD
- Requirement Type: TBD

##### MS22029826-74360: IgnMode (Value: On, Off) (System Requirement)
- Variant: S237
- Stakeholder Requirement State: In Review
- System Requirement State: Draft
- Software Requirement State: Draft
- Primary Discipline: TBD
- Requirement Type: TBD

##### MS22029826-74362: LVSD/HVSD Flag (Value: Not Set, Set) (System Requirement)
- Variant: S237
- Stakeholder Requirement State: In Review
- System Requirement State: Draft
- Software Requirement State: Draft
- Primary Discipline: TBD
- Requirement Type: TBD

##### MS22029826-74363: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74364: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74365: Diag RW Activate Revive Chime Enable (Value: 0-Disable, 1-Enable) (System Requirement)
- Variant: S237
- Stakeholder Requirement State: In Review
- System Requirement State: Draft
- Software Requirement State: Draft
- Primary Discipline: TBD
- Requirement Type: TBD

#### MS22029826-74357: Output Requirements (Heading)
- Variant: S237
- Stakeholder Requirement State: In Review
- System Requirement State: Draft
- Software Requirement State: Draft
- Primary Discipline: TBD
- Requirement Type: TBD

##### MS22029826-74359: Activate Revive Chime Functional Logic (Value: Off, On) (System Requirement)
- Variant: S237
- Stakeholder Requirement State: In Review
- System Requirement State: Draft
- Software Requirement State: Draft
- Primary Discipline: TBD
- Requirement Type: TBD

#### MS22029826-74358: Performance Requirements (Heading)
- Variant: S237
- Stakeholder Requirement State: In Review
- System Requirement State: Draft
- Software Requirement State: Draft
- Primary Discipline: TBD
- Requirement Type: TBD

##### MS22029826-74361 (System Requirement)
Table - Activate Revive Chime Functional Logic
| Ign Mode | LVSD/HVSD Flag | VAR_CODING_VEHICLE_CONTROL_UNIT | Diag RW Activate Revive Chime Enable | CAN Signal Missing or Never Received | VCU10_100(0X30A): ALERT_MSGS | Activate Revive Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x16 | Off |
| On/Off | Not Set | 1 | 1 | 0 | =0x16 | On |
- Variant: S237
- Stakeholder Requirement State: In Review
- System Requirement State: Draft
- Software Requirement State: Draft
- Primary Discipline: TBD
- Requirement Type: TBD

### MS22029826-74366: Revive Chime (Heading)
- Variant: S237
- Stakeholder Requirement State: In Review
- System Requirement State: Draft
- Software Requirement State: Draft
- Primary Discipline: TBD
- Requirement Type: TBD

#### MS22029826-74367: Input Requirements (Heading)
- Variant: S237
- Stakeholder Requirement State: In Review
- System Requirement State: Draft
- Software Requirement State: Draft
- Primary Discipline: TBD
- Requirement Type: TBD

##### MS22029826-74371: IgnMode (Value: On, Off) (System Requirement)
- Variant: S237
- Stakeholder Requirement State: In Review
- System Requirement State: Draft
- Software Requirement State: Draft
- Primary Discipline: TBD
- Requirement Type: TBD

##### MS22029826-74373: LVSD/HVSD Flag (Value: Not Set, Set) (System Requirement)
- Variant: S237
- Stakeholder Requirement State: In Review
- System Requirement State: Draft
- Software Requirement State: Draft
- Primary Discipline: TBD
- Requirement Type: TBD

##### MS22029826-74374: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74375: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74376: Diag RW Revive Chime Enable (Value: 0-Disable, 1-Enable) (System Requirement)
- Variant: S237
- Stakeholder Requirement State: In Review
- System Requirement State: Draft
- Software Requirement State: Draft
- Primary Discipline: TBD
- Requirement Type: TBD

#### MS22029826-74368: Output Requirements (Heading)
- Variant: S237
- Stakeholder Requirement State: In Review
- System Requirement State: Draft
- Software Requirement State: Draft
- Primary Discipline: TBD
- Requirement Type: TBD

##### MS22029826-74370: Revive Chime Functional Logic (Value: Off, On) (System Requirement)
- Variant: S237
- Stakeholder Requirement State: In Review
- System Requirement State: Draft
- Software Requirement State: Draft
- Primary Discipline: TBD
- Requirement Type: TBD

#### MS22029826-74369: Performance Requirements (Heading)
- Variant: S237
- Stakeholder Requirement State: In Review
- System Requirement State: Draft
- Software Requirement State: Draft
- Primary Discipline: TBD
- Requirement Type: TBD

##### MS22029826-74372: Table - Revive Chime Functional Logic (System Requirement)
Table - Revive Chime Functional Logic
| Ign Mode | LVSD/HVSD Flag | VAR_CODING_VEHICLE_CONTROL_UNIT | Diag RW Revive Chime Enable | CAN Signal Missing or Never Received | VCU10_100(0X30A): ALERT_MSGS | Revive Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x17 | Off |
| On/Off | Not Set | 1 | 1 | 0 | =0x17 | On |
- Variant: S237
- Stakeholder Requirement State: In Review
- System Requirement State: Draft
- Software Requirement State: Draft
- Primary Discipline: TBD
- Requirement Type: TBD

### MS22029826-74377: Revive Mode Chime (Heading)
- Variant: S237
- Stakeholder Requirement State: In Review
- System Requirement State: Draft
- Software Requirement State: Draft
- Primary Discipline: TBD
- Requirement Type: TBD

#### MS22029826-74378: Input Requirements (Heading)
- Variant: S237
- Stakeholder Requirement State: In Review
- System Requirement State: Draft
- Software Requirement State: Draft
- Primary Discipline: TBD
- Requirement Type: TBD

##### MS22029826-74382: IgnMode (Value: On, Off) (System Requirement)
- Variant: S237
- Stakeholder Requirement State: In Review
- System Requirement State: Draft
- Software Requirement State: Draft
- Primary Discipline: TBD
- Requirement Type: TBD

##### MS22029826-74384: LVSD/HVSD Flag (Value: Not Set, Set) (System Requirement)
- Variant: S237
- Stakeholder Requirement State: In Review
- System Requirement State: Draft
- Software Requirement State: Draft
- Primary Discipline: TBD
- Requirement Type: TBD

##### MS22029826-74385: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74386: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74387: Diag RW Revive Mode Chime Enable (Value: 0-Disable, 1-Enable) (System Requirement)
- Variant: S237
- Stakeholder Requirement State: In Review
- System Requirement State: Draft
- Software Requirement State: Draft
- Primary Discipline: TBD
- Requirement Type: TBD

#### MS22029826-74379: Output Requirements (Heading)
- Variant: S237
- Stakeholder Requirement State: In Review
- System Requirement State: Draft
- Software Requirement State: Draft
- Primary Discipline: TBD
- Requirement Type: TBD

##### MS22029826-74381: Revive Mode Chime Functional Logic (Value: Off, On) (System Requirement)
- Variant: S237
- Stakeholder Requirement State: In Review
- System Requirement State: Draft
- Software Requirement State: Draft
- Primary Discipline: TBD
- Requirement Type: TBD

#### MS22029826-74380: Performance Requirements (Heading)
- Variant: S237
- Stakeholder Requirement State: In Review
- System Requirement State: Draft
- Software Requirement State: Draft
- Primary Discipline: TBD
- Requirement Type: TBD

##### MS22029826-74383 (System Requirement)
Table - Revive Mode Chime Functional Logic
| Ign Mode | LVSD/HVSD Flag | VAR_CODING_VEHICLE_CONTROL_UNIT | Diag RW Revive Mode Chime Enable | CAN Signal Missing or Never Received | VCU10_100(0X30A): ALERT_MSGS | Revive Mode Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x18 | Off |
| On/Off | Not Set | 1 | 1 | 0 | =0x18 | On |
- Variant: S237
- Stakeholder Requirement State: In Review
- System Requirement State: Draft
- Software Requirement State: Draft
- Primary Discipline: TBD
- Requirement Type: TBD

### MS22029826-74391: Revive Unsuccessful Chime (Heading)
- Variant: S237
- Stakeholder Requirement State: In Review
- System Requirement State: Draft
- Software Requirement State: Draft
- Primary Discipline: TBD
- Requirement Type: TBD

#### MS22029826-74392: Input Requirements (Heading)
- Variant: S237
- Stakeholder Requirement State: In Review
- System Requirement State: Draft
- Software Requirement State: Draft
- Primary Discipline: TBD
- Requirement Type: TBD

##### MS22029826-74396: IgnMode (Value: On, Off) (System Requirement)
- Variant: S237
- Stakeholder Requirement State: In Review
- System Requirement State: Draft
- Software Requirement State: Draft
- Primary Discipline: TBD
- Requirement Type: TBD

##### MS22029826-74398: LVSD/HVSD Flag (Value: Not Set, Set) (System Requirement)
- Variant: S237
- Stakeholder Requirement State: In Review
- System Requirement State: Draft
- Software Requirement State: Draft
- Primary Discipline: TBD
- Requirement Type: TBD

##### MS22029826-74399: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74400: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74401: Diag RW Revive Unsuccessful Chime Enable (Value: 0-Disable, 1-Enable) (System Requirement)
- Variant: S237
- Stakeholder Requirement State: In Review
- System Requirement State: Draft
- Software Requirement State: Draft
- Primary Discipline: TBD
- Requirement Type: TBD

#### MS22029826-74393: Output Requirements (Heading)
- Variant: S237
- Stakeholder Requirement State: In Review
- System Requirement State: Draft
- Software Requirement State: Draft
- Primary Discipline: TBD
- Requirement Type: TBD

##### MS22029826-74395: Revive Unsuccessful Chime Functional Logic (Value: Off, On) (System Requirement)
- Variant: S237
- Stakeholder Requirement State: In Review
- System Requirement State: Draft
- Software Requirement State: Draft
- Primary Discipline: TBD
- Requirement Type: TBD

#### MS22029826-74394: Performance Requirements (Heading)
- Variant: S237
- Stakeholder Requirement State: In Review
- System Requirement State: Draft
- Software Requirement State: Draft
- Primary Discipline: TBD
- Requirement Type: TBD

##### MS22029826-74397 (System Requirement)
Table - Revive Unsuccessful Chime Functional Logic
| Ign Mode | LVSD/HVSD Flag | VAR_CODING_VEHICLE_CONTROL_UNIT | Diag RW Revive Unsuccessful Chime Enable | CAN Signal Missing or Never Received | VCU10_100(0X30A): ALERT_MSGS | Revive Unsuccessful Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x19 | Off |
| On/Off | Not Set | 1 | 1 | 0 | =0x19 | On |
- Variant: S237
- Stakeholder Requirement State: In Review
- System Requirement State: Draft
- Software Requirement State: Draft
- Primary Discipline: TBD
- Requirement Type: TBD

### MS22029826-74402: Isolation Fault Chime (Heading)
- Variant: S237
- Stakeholder Requirement State: In Review
- System Requirement State: Draft
- Software Requirement State: Draft
- Primary Discipline: TBD
- Requirement Type: TBD

#### MS22029826-74403: Input Requirements (Heading)
- Variant: S237
- Stakeholder Requirement State: In Review
- System Requirement State: Draft
- Software Requirement State: Draft
- Primary Discipline: TBD
- Requirement Type: TBD

##### MS22029826-74407: IgnMode (Value: On, Off) (System Requirement)
- Variant: S237
- Stakeholder Requirement State: In Review
- System Requirement State: Draft
- Software Requirement State: Draft
- Primary Discipline: TBD
- Requirement Type: TBD

##### MS22029826-74409: LVSD/HVSD Flag (Value: Not Set, Set) (System Requirement)
- Variant: S237
- Stakeholder Requirement State: In Review
- System Requirement State: Draft
- Software Requirement State: Draft
- Primary Discipline: TBD
- Requirement Type: TBD

##### MS22029826-74410: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74411: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74412: Diag RW Isolation Fault Chime Enable (Value: 0-Disable, 1-Enable) (System Requirement)
- Variant: S237
- Stakeholder Requirement State: In Review
- System Requirement State: Draft
- Software Requirement State: Draft
- Primary Discipline: TBD
- Requirement Type: TBD

#### MS22029826-74404: Output Requirements (Heading)
- Variant: S237
- Stakeholder Requirement State: In Review
- System Requirement State: Draft
- Software Requirement State: Draft
- Primary Discipline: TBD
- Requirement Type: TBD

##### MS22029826-74406: Isolation Fault Chime Functional Logic (Value: Off, On) (System Requirement)
- Variant: S237
- Stakeholder Requirement State: In Review
- System Requirement State: Draft
- Software Requirement State: Draft
- Primary Discipline: TBD
- Requirement Type: TBD

#### MS22029826-74405: Performance Requirements (Heading)
- Variant: S237
- Stakeholder Requirement State: In Review
- System Requirement State: Draft
- Software Requirement State: Draft
- Primary Discipline: TBD
- Requirement Type: TBD

##### MS22029826-74408 (System Requirement)
Table - Isolation Fault Chime Functional Logic
| Ign Mode | LVSD/HVSD Flag | VAR_CODING_VEHICLE_CONTROL_UNIT | Diag RW Isolation Fault Chime Enable | CAN Signal Missing or Never Received | VCU10_100(0X30A): ALERT_MSGS | Isolation Fault Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x1A | Off |
| On/Off | Not Set | 1 | 1 | 0 | =0x1A | On |
- Variant: S237
- Stakeholder Requirement State: In Review
- System Requirement State: Draft
- Software Requirement State: Draft
- Primary Discipline: TBD
- Requirement Type: TBD

### MS22029826-74413: Go Slow (Flash) Chime (Heading)
- Variant: S237
- Stakeholder Requirement State: In Review
- System Requirement State: Draft
- Software Requirement State: Draft
- Primary Discipline: TBD
- Requirement Type: TBD

#### MS22029826-74414: Input Requirements (Heading)
- Variant: S237
- Stakeholder Requirement State: In Review
- System Requirement State: Draft
- Software Requirement State: Draft
- Primary Discipline: TBD
- Requirement Type: TBD

##### MS22029826-74418: IgnMode (Value: On, Off) (System Requirement)
- Variant: S237
- Stakeholder Requirement State: In Review
- System Requirement State: Draft
- Software Requirement State: Draft
- Primary Discipline: TBD
- Requirement Type: TBD

##### MS22029826-74420: LVSD/HVSD Flag (Value: Not Set, Set) (System Requirement)
- Variant: S237
- Stakeholder Requirement State: In Review
- System Requirement State: Draft
- Software Requirement State: Draft
- Primary Discipline: TBD
- Requirement Type: TBD

##### MS22029826-74421: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74422: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74423: Diag RW Go Slow (Flash) Chime Enable (Value: 0-Disable, 1-Enable) (System Requirement)
- Variant: S237
- Stakeholder Requirement State: In Review
- System Requirement State: Draft
- Software Requirement State: Draft
- Primary Discipline: TBD
- Requirement Type: TBD

#### MS22029826-74415: Output Requirements (Heading)
- Variant: S237
- Stakeholder Requirement State: In Review
- System Requirement State: Draft
- Software Requirement State: Draft
- Primary Discipline: TBD
- Requirement Type: TBD

##### MS22029826-74417: Go Slow (Flash) Chime Functional Logic (Value: Off, On) (System Requirement)
- Variant: S237
- Stakeholder Requirement State: In Review
- System Requirement State: Draft
- Software Requirement State: Draft
- Primary Discipline: TBD
- Requirement Type: TBD

#### MS22029826-74416: Performance Requirements (Heading)
- Variant: S237
- Stakeholder Requirement State: In Review
- System Requirement State: Draft
- Software Requirement State: Draft
- Primary Discipline: TBD
- Requirement Type: TBD

##### MS22029826-74419 (System Requirement)
Table - Go Slow (Flash) Chime Functional Logic
| Ign Mode | LVSD/HVSD Flag | VAR_CODING_VEHICLE_CONTROL_UNIT | Diag RW Go Slow (Flash) Chime Enable | CAN Signal Missing or Never Received | VCU10_100(0X30A): ALERT_MSGS | Go Slow (Flash) Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x1B | Off |
| On/Off | Not Set | 1 | 1 | 0 | =0x1B | On |
- Variant: S237
- Stakeholder Requirement State: In Review
- System Requirement State: Draft
- Software Requirement State: Draft
- Primary Discipline: TBD
- Requirement Type: TBD

### MS22029826-74424: Hill Hold Deactivate Chime (Heading)
- Variant: S237
- Stakeholder Requirement State: In Review
- System Requirement State: Draft
- Software Requirement State: Draft
- Primary Discipline: TBD
- Requirement Type: TBD

#### MS22029826-74425: Input Requirements (Heading)
- Variant: S237
- Stakeholder Requirement State: In Review
- System Requirement State: Draft
- Software Requirement State: Draft
- Primary Discipline: TBD
- Requirement Type: TBD

##### MS22029826-74429: IgnMode (Value: On, Off) (System Requirement)
- Variant: S237
- Stakeholder Requirement State: In Review
- System Requirement State: Draft
- Software Requirement State: Draft
- Primary Discipline: TBD
- Requirement Type: TBD

##### MS22029826-74431: LVSD/HVSD Flag (Value: Not Set, Set) (System Requirement)
- Variant: S237
- Stakeholder Requirement State: In Review
- System Requirement State: Draft
- Software Requirement State: Draft
- Primary Discipline: TBD
- Requirement Type: TBD

##### MS22029826-74432: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74433: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74434: Diag RW Hill Hold Deactivate Chime Enable (Value: 0-Disable, 1-Enable) (System Requirement)
- Variant: S237
- Stakeholder Requirement State: In Review
- System Requirement State: Draft
- Software Requirement State: Draft
- Primary Discipline: TBD
- Requirement Type: TBD

#### MS22029826-74426: Output Requirements (Heading)
- Variant: S237
- Stakeholder Requirement State: In Review
- System Requirement State: Draft
- Software Requirement State: Draft
- Primary Discipline: TBD
- Requirement Type: TBD

##### MS22029826-74428: Hill Hold Deactivate Chime Functional Logic (Value: Off, On) (System Requirement)
- Variant: S237
- Stakeholder Requirement State: In Review
- System Requirement State: Draft
- Software Requirement State: Draft
- Primary Discipline: TBD
- Requirement Type: TBD

#### MS22029826-74427: Performance Requirements (Heading)
- Variant: S237
- Stakeholder Requirement State: In Review
- System Requirement State: Draft
- Software Requirement State: Draft
- Primary Discipline: TBD
- Requirement Type: TBD

##### MS22029826-74430 (System Requirement)
Table - Hill Hold Deactivate Chime Functional Logic
| Ign Mode | LVSD/HVSD Flag | VAR_CODING_VEHICLE_CONTROL_UNIT | Diag RW Hill Hold Deactivate Chime Enable | CAN Signal Missing or Never Received | VCU10_100(0X30A): ALERT_MSGS | Hill Hold Deactivate Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x1C | Off |
| On/Off | Not Set | 1 | 1 | 0 | =0x1C | On |
- Variant: S237
- Stakeholder Requirement State: In Review
- System Requirement State: Draft
- Software Requirement State: Draft
- Primary Discipline: TBD
- Requirement Type: TBD

### MS22029826-74436: EPT High Temp Chime (Heading)
- Variant: S237
- Stakeholder Requirement State: In Review
- System Requirement State: Draft
- Software Requirement State: Draft
- Primary Discipline: TBD
- Requirement Type: TBD

#### MS22029826-74437: Input Requirements (Heading)
- Variant: S237
- Stakeholder Requirement State: In Review
- System Requirement State: Draft
- Software Requirement State: Draft
- Primary Discipline: TBD
- Requirement Type: TBD

##### MS22029826-74441: IgnMode (Value: On, Off) (System Requirement)
- Variant: S237
- Stakeholder Requirement State: In Review
- System Requirement State: Draft
- Software Requirement State: Draft
- Primary Discipline: TBD
- Requirement Type: TBD

##### MS22029826-74443: LVSD/HVSD Flag (Value: Not Set, Set) (System Requirement)
- Variant: S237
- Stakeholder Requirement State: In Review
- System Requirement State: Draft
- Software Requirement State: Draft
- Primary Discipline: TBD
- Requirement Type: TBD

##### MS22029826-74444: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74445: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74446: Diag RW EPT High Temp Chime Enable (Value: 0-Disable, 1-Enable) (System Requirement)
- Variant: S237
- Stakeholder Requirement State: In Review
- System Requirement State: Draft
- Software Requirement State: Draft
- Primary Discipline: TBD
- Requirement Type: TBD

#### MS22029826-74438: Output Requirements (Heading)
- Variant: S237
- Stakeholder Requirement State: In Review
- System Requirement State: Draft
- Software Requirement State: Draft
- Primary Discipline: TBD
- Requirement Type: TBD

##### MS22029826-74440: EPT High Temp Chime Functional Logic (Value: Off, On) (System Requirement)
- Variant: S237
- Stakeholder Requirement State: In Review
- System Requirement State: Draft
- Software Requirement State: Draft
- Primary Discipline: TBD
- Requirement Type: TBD

#### MS22029826-74439: Performance Requirements (Heading)
- Variant: S237
- Stakeholder Requirement State: In Review
- System Requirement State: Draft
- Software Requirement State: Draft
- Primary Discipline: TBD
- Requirement Type: TBD

##### MS22029826-74442 (System Requirement)
Table - EPT High Temp Chime Functional Logic
| Ign Mode | LVSD/HVSD Flag | VAR_CODING_VEHICLE_CONTROL_UNIT | Diag RW EPT High Temp Chime Enable | CAN Signal Missing or Never Received | VCU10_100(0X30A): ALERT_MSGS | EPT High Temp Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x1D | Off |
| On/Off | Not Set | 1 | 1 | 0 | =0x1D | On |
- Variant: S237
- Stakeholder Requirement State: In Review
- System Requirement State: Draft
- Software Requirement State: Draft
- Primary Discipline: TBD
- Requirement Type: TBD

### MS22029826-74447: HV Battery High Temperature Chime /Thermal Runaway (Heading)
- Variant: S237
- Stakeholder Requirement State: In Review
- System Requirement State: Draft
- Software Requirement State: Draft
- Primary Discipline: TBD
- Requirement Type: TBD

#### MS22029826-74448: Input Requirements (Heading)
- Variant: S237
- Stakeholder Requirement State: In Review
- System Requirement State: Draft
- Software Requirement State: Draft
- Primary Discipline: TBD
- Requirement Type: TBD

##### MS22029826-74452: IgnMode (Value: On, Off) (System Requirement)
- Variant: S237
- Stakeholder Requirement State: In Review
- System Requirement State: Draft
- Software Requirement State: Draft
- Primary Discipline: TBD
- Requirement Type: TBD

##### MS22029826-74454: LVSD/HVSD Flag (Value: Not Set, Set) (System Requirement)
- Variant: S237
- Stakeholder Requirement State: In Review
- System Requirement State: Draft
- Software Requirement State: Draft
- Primary Discipline: TBD
- Requirement Type: TBD

##### MS22029826-74455: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74456: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74457: Diag RW HV Battery High Temperature Chime Enable (Value: 0-Disable, 1-Enable) (System Requirement)
- Variant: S237
- Stakeholder Requirement State: In Review
- System Requirement State: Draft
- Software Requirement State: Draft
- Primary Discipline: TBD
- Requirement Type: TBD

#### MS22029826-74449: Output Requirements (Heading)
- Variant: S237
- Stakeholder Requirement State: In Review
- System Requirement State: Draft
- Software Requirement State: Draft
- Primary Discipline: TBD
- Requirement Type: TBD

##### MS22029826-74451: HV Battery High Temperature Chime Functional Logic (Value: Off, On) (System Requirement)
- Variant: S237
- Stakeholder Requirement State: In Review
- System Requirement State: Draft
- Software Requirement State: Draft
- Primary Discipline: TBD
- Requirement Type: TBD

#### MS22029826-74450: Performance Requirements (Heading)
- Variant: S237
- Stakeholder Requirement State: In Review
- System Requirement State: Draft
- Software Requirement State: Draft
- Primary Discipline: TBD
- Requirement Type: TBD

##### MS22029826-74453 (System Requirement)
Table - HV Battery High Temperature Chime Functional Logic
| Ign Mode | LVSD/HVSD Flag | VAR_CODING_VEHICLE_CONTROL_UNIT | Diag RW HV Battery High Temperature Chime Enable | CAN Signal Missing or Never Received | VCU10_100(0X30A): ALERT_MSGS | HV Battery High Temperature Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x1E | Off |
| On/Off | Not Set | 1 | 1 | 0 | =0x1E | On |
- Variant: S237
- Stakeholder Requirement State: In Review
- System Requirement State: Draft
- Software Requirement State: Draft
- Primary Discipline: TBD
- Requirement Type: TBD

### MS22029826-74458: Charging Chime (Heading)
- Variant: S237
- Stakeholder Requirement State: In Review
- System Requirement State: Draft
- Software Requirement State: Draft
- Primary Discipline: TBD
- Requirement Type: TBD

#### MS22029826-74459: Input Requirements (Heading)
- Variant: S237
- Stakeholder Requirement State: In Review
- System Requirement State: Draft
- Software Requirement State: Draft
- Primary Discipline: TBD
- Requirement Type: TBD

##### MS22029826-74463: IgnMode (Value: On, Off) (System Requirement)
- Variant: S237
- Stakeholder Requirement State: In Review
- System Requirement State: Draft
- Software Requirement State: Draft
- Primary Discipline: TBD
- Requirement Type: TBD

##### MS22029826-74465: LVSD/HVSD Flag (Value: Not Set, Set) (System Requirement)
- Variant: S237
- Stakeholder Requirement State: In Review
- System Requirement State: Draft
- Software Requirement State: Draft
- Primary Discipline: TBD
- Requirement Type: TBD

##### MS22029826-74466: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74467: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74468: Diag RW Charging Chime Enable (Value: 0-Disable, 1-Enable) (System Requirement)
- Variant: S237
- Stakeholder Requirement State: In Review
- System Requirement State: Draft
- Software Requirement State: Draft
- Primary Discipline: TBD
- Requirement Type: TBD

#### MS22029826-74460: Output Requirements (Heading)
- Variant: S237
- Stakeholder Requirement State: In Review
- System Requirement State: Draft
- Software Requirement State: Draft
- Primary Discipline: TBD
- Requirement Type: TBD

##### MS22029826-74462: Charging Chime Functional Logic (Value: Off, On) (System Requirement)
- Variant: S237
- Stakeholder Requirement State: In Review
- System Requirement State: Draft
- Software Requirement State: Draft
- Primary Discipline: TBD
- Requirement Type: TBD

#### MS22029826-74461: Performance Requirements (Heading)
- Variant: S237
- Stakeholder Requirement State: In Review
- System Requirement State: Draft
- Software Requirement State: Draft
- Primary Discipline: TBD
- Requirement Type: TBD

##### MS22029826-74464: Table - Charging Chime Functional Logic (System Requirement)
Table - Charging Chime Functional Logic
| Ign Mode | LVSD/HVSD Flag | VAR_CODING_VEHICLE_CONTROL_UNIT | Diag RW Charging Chime Enable | CAN Signal Missing or Never Received | VCU10_100(0X30A): ALERT_MSGS | Charging Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x20 | Off |
| On/Off | Not Set | 1 | 1 | 0 | =0x20 | On |
- Variant: S237
- Stakeholder Requirement State: In Review
- System Requirement State: Draft
- Software Requirement State: Draft
- Primary Discipline: TBD
- Requirement Type: TBD

### MS22029826-74469: Engage Park Chime (Heading)
- Variant: S237
- Stakeholder Requirement State: In Review
- System Requirement State: Draft
- Software Requirement State: Draft
- Primary Discipline: TBD
- Requirement Type: TBD

#### MS22029826-74470: Input Requirements (Heading)
- Variant: S237
- Stakeholder Requirement State: In Review
- System Requirement State: Draft
- Software Requirement State: Draft
- Primary Discipline: TBD
- Requirement Type: TBD

##### MS22029826-74474: IgnMode (Value: On, Off) (System Requirement)
- Variant: S237
- Stakeholder Requirement State: In Review
- System Requirement State: Draft
- Software Requirement State: Draft
- Primary Discipline: TBD
- Requirement Type: TBD

##### MS22029826-74476: LVSD/HVSD Flag (Value: Not Set, Set) (System Requirement)
- Variant: S237
- Stakeholder Requirement State: In Review
- System Requirement State: Draft
- Software Requirement State: Draft
- Primary Discipline: TBD
- Requirement Type: TBD

##### MS22029826-74477: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74478: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74479: Diag RW Engage Park Chime Enable (Value: 0-Disable, 1-Enable) (System Requirement)
- Variant: S237
- Stakeholder Requirement State: In Review
- System Requirement State: Draft
- Software Requirement State: Draft
- Primary Discipline: TBD
- Requirement Type: TBD

#### MS22029826-74471: Output Requirements (Heading)
- Variant: S237
- Stakeholder Requirement State: In Review
- System Requirement State: Draft
- Software Requirement State: Draft
- Primary Discipline: TBD
- Requirement Type: TBD

##### MS22029826-74473: Engage Park Chime Functional Logic (Value: Off, On) (System Requirement)
- Variant: S237
- Stakeholder Requirement State: In Review
- System Requirement State: Draft
- Software Requirement State: Draft
- Primary Discipline: TBD
- Requirement Type: TBD

#### MS22029826-74472: Performance Requirements (Heading)
- Variant: S237
- Stakeholder Requirement State: In Review
- System Requirement State: Draft
- Software Requirement State: Draft
- Primary Discipline: TBD
- Requirement Type: TBD

##### MS22029826-74475 (System Requirement)
Table - Engage Park Chime Functional Logic
| Ign Mode | LVSD/HVSD Flag | VAR_CODING_VEHICLE_CONTROL_UNIT | Diag RW Engage Park Chime Enable | CAN Signal Missing or Never Received | VCU10_100(0X30A): ALERT_MSGS | Engage Park Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x21 | Off |
| On/Off | Not Set | 1 | 1 | 0 | =0x21 | On |
- Variant: S237
- Stakeholder Requirement State: In Review
- System Requirement State: Draft
- Software Requirement State: Draft
- Primary Discipline: TBD
- Requirement Type: TBD

### MS22029826-74610: Preconditioning Chime (Heading)
- Variant: S237
- Stakeholder Requirement State: In Review
- System Requirement State: Draft
- Software Requirement State: Draft
- Primary Discipline: TBD
- Requirement Type: TBD

#### MS22029826-74611: Input Requirements (Heading)
- Variant: S237
- Stakeholder Requirement State: In Review
- System Requirement State: Draft
- Software Requirement State: Draft
- Primary Discipline: TBD
- Requirement Type: TBD

##### MS22029826-74615: IgnMode (Value: On, Off) (System Requirement)
- Variant: S237
- Stakeholder Requirement State: In Review
- System Requirement State: Draft
- Software Requirement State: Draft
- Primary Discipline: TBD
- Requirement Type: TBD

##### MS22029826-74617: LVSD/HVSD Flag (Value: Not Set, Set) (System Requirement)
- Variant: S237
- Stakeholder Requirement State: In Review
- System Requirement State: Draft
- Software Requirement State: Draft
- Primary Discipline: TBD
- Requirement Type: TBD

##### MS22029826-74618: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74619: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74620: Diag RW Preconditioning Chime Enable (Value: 0-Disable, 1-Enable) (System Requirement)
- Variant: S237
- Stakeholder Requirement State: In Review
- System Requirement State: Draft
- Software Requirement State: Draft
- Primary Discipline: TBD
- Requirement Type: TBD

#### MS22029826-74612: Output Requirements (Heading)
- Variant: S237
- Stakeholder Requirement State: In Review
- System Requirement State: Draft
- Software Requirement State: Draft
- Primary Discipline: TBD
- Requirement Type: TBD

##### MS22029826-74614: Preconditioning Chime Functional Logic (Value: Off, On) (System Requirement)
- Variant: S237
- Stakeholder Requirement State: In Review
- System Requirement State: Draft
- Software Requirement State: Draft
- Primary Discipline: TBD
- Requirement Type: TBD

#### MS22029826-74613: Performance Requirements (Heading)
- Variant: S237
- Stakeholder Requirement State: In Review
- System Requirement State: Draft
- Software Requirement State: Draft
- Primary Discipline: TBD
- Requirement Type: TBD

##### MS22029826-74616 (System Requirement)
Table – Preconditioning Chime Functional Logic
| Ign Mode | LVSD/HVSD Flag | VAR_CODING_VEHICLE_CONTROL_UNIT | Diag RW Preconditioning Chime Enable | CAN Signal Missing or Never Received | VCU10_100(0X30A): ALERT_MSGS | Preconditioning Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x22 | Off |
| On/Off | Not Set | 1 | 1 | 0 | =0x22 | On |
- Variant: S237
- Stakeholder Requirement State: In Review
- System Requirement State: Draft
- Software Requirement State: Draft
- Primary Discipline: TBD
- Requirement Type: TBD

### MS22029826-74621: HVIL FAULT Chime (Heading)
Coolant Low Temp Chime
- Variant: S237
- Stakeholder Requirement State: In Review
- System Requirement State: Draft
- Software Requirement State: Draft
- Primary Discipline: TBD
- Requirement Type: TBD

#### MS22029826-74622: Input Requirements (Heading)
- Variant: S237
- Stakeholder Requirement State: In Review
- System Requirement State: Draft
- Software Requirement State: Draft
- Primary Discipline: TBD
- Requirement Type: TBD

##### MS22029826-74626: IgnMode (Value: On, Off) (System Requirement)
- Variant: S237
- Stakeholder Requirement State: In Review
- System Requirement State: Draft
- Software Requirement State: Draft
- Primary Discipline: TBD
- Requirement Type: TBD

##### MS22029826-74628: LVSD/HVSD Flag (Value: Not Set, Set) (System Requirement)
- Variant: S237
- Stakeholder Requirement State: In Review
- System Requirement State: Draft
- Software Requirement State: Draft
- Primary Discipline: TBD
- Requirement Type: TBD

##### MS22029826-74629: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74630: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74631: Diag RW HVIL FAULT Chime Enable (Value: 0-Disable, 1-Enable) (System Requirement)
- Variant: S237
- Stakeholder Requirement State: In Review
- System Requirement State: Draft
- Software Requirement State: Draft
- Primary Discipline: TBD
- Requirement Type: TBD

#### MS22029826-74623: Output Requirements (Heading)
- Variant: S237
- Stakeholder Requirement State: In Review
- System Requirement State: Draft
- Software Requirement State: Draft
- Primary Discipline: TBD
- Requirement Type: TBD

##### MS22029826-74625: HVIL FAULT Chime Functional Logic (Value: Off, On) (System Requirement)
- Variant: S237
- Stakeholder Requirement State: In Review
- System Requirement State: Draft
- Software Requirement State: Draft
- Primary Discipline: TBD
- Requirement Type: TBD

#### MS22029826-74624: Performance Requirements (Heading)
- Variant: S237
- Stakeholder Requirement State: In Review
- System Requirement State: Draft
- Software Requirement State: Draft
- Primary Discipline: TBD
- Requirement Type: TBD

##### MS22029826-74627 (System Requirement)
Table – HVIL FAULT Chime Functional Logic
| Ign Mode | LVSD/HVSD Flag | VAR_CODING_VEHICLE_CONTROL_UNIT | Diag RW HVIL FAULT Chime Enable | CAN Signal Missing or Never Received | VCU10_100(0X30A): ALERT_MSGS | HVIL FAULT Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x23 | Off |
| On/Off | Not Set | 1 | 1 | 0 | =0x23 | On |
- Variant: S237
- Stakeholder Requirement State: In Review
- System Requirement State: Draft
- Software Requirement State: Draft
- Primary Discipline: TBD
- Requirement Type: TBD

### MS22029826-74514: Turn Ign Key to start vehicle Chime (Heading)
- Variant: S237
- Stakeholder Requirement State: In Review
- System Requirement State: Draft
- Software Requirement State: Draft
- Primary Discipline: TBD
- Requirement Type: TBD

#### MS22029826-74515: Input Requirements (Heading)
- Variant: S237
- Stakeholder Requirement State: In Review
- System Requirement State: Draft
- Software Requirement State: Draft
- Primary Discipline: TBD
- Requirement Type: TBD

##### MS22029826-74519: IgnMode (Value: On, Off) (System Requirement)
- Variant: S237
- Stakeholder Requirement State: In Review
- System Requirement State: Draft
- Software Requirement State: Draft
- Primary Discipline: TBD
- Requirement Type: TBD

##### MS22029826-74521: LVSD/HVSD Flag (Value: Not Set, Set) (System Requirement)
- Variant: S237
- Stakeholder Requirement State: In Review
- System Requirement State: Draft
- Software Requirement State: Draft
- Primary Discipline: TBD
- Requirement Type: TBD

##### MS22029826-74522: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74523: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74524: Diag RW Turn Ign Key to start vehicle Chime Enable (Value: 0-Disable, 1-Enable) (System Requirement)
- Variant: S237
- Stakeholder Requirement State: In Review
- System Requirement State: Draft
- Software Requirement State: Draft
- Primary Discipline: TBD
- Requirement Type: TBD

#### MS22029826-74516: Output Requirements (Heading)
- Variant: S237
- Stakeholder Requirement State: In Review
- System Requirement State: Draft
- Software Requirement State: Draft
- Primary Discipline: TBD
- Requirement Type: TBD

##### MS22029826-74518: Turn Ign Key to start vehicle Chime Functional Logic (Value: Off, On) (System Requirement)
- Variant: S237
- Stakeholder Requirement State: In Review
- System Requirement State: Draft
- Software Requirement State: Draft
- Primary Discipline: TBD
- Requirement Type: TBD

#### MS22029826-74517: Performance Requirements (Heading)
- Variant: S237
- Stakeholder Requirement State: In Review
- System Requirement State: Draft
- Software Requirement State: Draft
- Primary Discipline: TBD
- Requirement Type: TBD

##### MS22029826-74520 (System Requirement)
Table - Turn Ign Key to start vehicle Chime Functional Logic
| Ign Mode | LVSD/HVSD Flag | VAR_CODING_VEHICLE_CONTROL_UNIT | Diag RW Turn Ign Key to start vehicle Chime Enable | CAN Signal Missing or Never Received | VCU10_100(0X30A): ALERT_MSGS | Turn Ign Key to start vehicle Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x24 | Off |
| On/Off | Not Set | 1 | 1 | 0 | =0x24 | On |
- Variant: S237
- Stakeholder Requirement State: In Review
- System Requirement State: Draft
- Software Requirement State: Draft
- Primary Discipline: TBD
- Requirement Type: TBD

### MS22029826-74525: Press Start stop switch to start Chime (Heading)
- Variant: S237
- Stakeholder Requirement State: In Review
- System Requirement State: Draft
- Software Requirement State: Draft
- Primary Discipline: TBD
- Requirement Type: TBD

#### MS22029826-74526: Input Requirements (Heading)
- Variant: S237
- Stakeholder Requirement State: In Review
- System Requirement State: Draft
- Software Requirement State: Draft
- Primary Discipline: TBD
- Requirement Type: TBD

##### MS22029826-74530: IgnMode (Value: On, Off) (System Requirement)
- Variant: S237
- Stakeholder Requirement State: In Review
- System Requirement State: Draft
- Software Requirement State: Draft
- Primary Discipline: TBD
- Requirement Type: TBD

##### MS22029826-74532: LVSD/HVSD Flag (Value: Not Set, Set) (System Requirement)
- Variant: S237
- Stakeholder Requirement State: In Review
- System Requirement State: Draft
- Software Requirement State: Draft
- Primary Discipline: TBD
- Requirement Type: TBD

##### MS22029826-74533: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74534: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74535: Diag RW Press Start stop switch to start Chime Enable (Value: 0-Disable, 1-Enable) (System Requirement)
- Variant: S237
- Stakeholder Requirement State: In Review
- System Requirement State: Draft
- Software Requirement State: Draft
- Primary Discipline: TBD
- Requirement Type: TBD

#### MS22029826-74527: Output Requirements (Heading)
- Variant: S237
- Stakeholder Requirement State: In Review
- System Requirement State: Draft
- Software Requirement State: Draft
- Primary Discipline: TBD
- Requirement Type: TBD

##### MS22029826-74529: Press Start stop switch to start Chime Functional Logic (Value: Off, On) (System Requirement)
- Variant: S237
- Stakeholder Requirement State: In Review
- System Requirement State: Draft
- Software Requirement State: Draft
- Primary Discipline: TBD
- Requirement Type: TBD

#### MS22029826-74528: Performance Requirements (Heading)
- Variant: S237
- Stakeholder Requirement State: In Review
- System Requirement State: Draft
- Software Requirement State: Draft
- Primary Discipline: TBD
- Requirement Type: TBD

##### MS22029826-74531 (System Requirement)
Table - Press Start stop switch to start Chime Functional Logic
| Ign Mode | LVSD/HVSD Flag | VAR_CODING_VEHICLE_CONTROL_UNIT | Diag RW Press Start stop switch to start Chime Enable | CAN Signal Missing or Never Received | VCU10_100(0X30A): ALERT_MSGS | Press Start stop switch to start Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x25 | Off |
| On/Off | Not Set | 1 | 1 | 0 | =0x25 | On |
- Variant: S237
- Stakeholder Requirement State: In Review
- System Requirement State: Draft
- Software Requirement State: Draft
- Primary Discipline: TBD
- Requirement Type: TBD

### MS22029826-74536: Press Brake Chime (Heading)
- Variant: S237
- Stakeholder Requirement State: In Review
- System Requirement State: Draft
- Software Requirement State: Draft
- Primary Discipline: TBD
- Requirement Type: TBD

#### MS22029826-74537: Input Requirements (Heading)
- Variant: S237
- Stakeholder Requirement State: In Review
- System Requirement State: Draft
- Software Requirement State: Draft
- Primary Discipline: TBD
- Requirement Type: TBD

##### MS22029826-74541: IgnMode (Value: On, Off) (System Requirement)
- Variant: S237
- Stakeholder Requirement State: In Review
- System Requirement State: Draft
- Software Requirement State: Draft
- Primary Discipline: TBD
- Requirement Type: TBD

##### MS22029826-74543: LVSD/HVSD Flag (Value: Not Set, Set) (System Requirement)
- Variant: S237
- Stakeholder Requirement State: In Review
- System Requirement State: Draft
- Software Requirement State: Draft
- Primary Discipline: TBD
- Requirement Type: TBD

##### MS22029826-74544: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74545: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74546: Diag RW Press Brake Chime Enable (Value: 0-Disable, 1-Enable) (System Requirement)
- Variant: S237
- Stakeholder Requirement State: In Review
- System Requirement State: Draft
- Software Requirement State: Draft
- Primary Discipline: TBD
- Requirement Type: TBD

#### MS22029826-74538: Output Requirements (Heading)
- Variant: S237
- Stakeholder Requirement State: In Review
- System Requirement State: Draft
- Software Requirement State: Draft
- Primary Discipline: TBD
- Requirement Type: TBD

##### MS22029826-74540: Press Brake Chime Functional Logic (Value: Off, On) (System Requirement)
- Variant: S237
- Stakeholder Requirement State: In Review
- System Requirement State: Draft
- Software Requirement State: Draft
- Primary Discipline: TBD
- Requirement Type: TBD

#### MS22029826-74539: Performance Requirements (Heading)
- Variant: S237
- Stakeholder Requirement State: In Review
- System Requirement State: Draft
- Software Requirement State: Draft
- Primary Discipline: TBD
- Requirement Type: TBD

##### MS22029826-74542 (System Requirement)
Table - Press Brake Chime Functional Logic
| Ign Mode | LVSD/HVSD Flag | VAR_CODING_VEHICLE_CONTROL_UNIT | Diag RW Press Brake Chime Enable | CAN Signal Missing or Never Received | VCU10_100(0X30A): ALERT_MSGS | Press Brake Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x26 | Off |
| On/Off | Not Set | 1 | 1 | 0 | =0x26 | On |
- Variant: S237
- Stakeholder Requirement State: In Review
- System Requirement State: Draft
- Software Requirement State: Draft
- Primary Discipline: TBD
- Requirement Type: TBD

### MS22029826-74547: Park Motor Failure Chime (Heading)
- Variant: S237
- Stakeholder Requirement State: In Review
- System Requirement State: Draft
- Software Requirement State: Draft
- Primary Discipline: TBD
- Requirement Type: TBD

#### MS22029826-74548: Input Requirements (Heading)
- Variant: S237
- Stakeholder Requirement State: In Review
- System Requirement State: Draft
- Software Requirement State: Draft
- Primary Discipline: TBD
- Requirement Type: TBD

##### MS22029826-74552: IgnMode (Value: On, Off) (System Requirement)
- Variant: S237
- Stakeholder Requirement State: In Review
- System Requirement State: Draft
- Software Requirement State: Draft
- Primary Discipline: TBD
- Requirement Type: TBD

##### MS22029826-74554: LVSD/HVSD Flag (Value: Not Set, Set) (System Requirement)
- Variant: S237
- Stakeholder Requirement State: In Review
- System Requirement State: Draft
- Software Requirement State: Draft
- Primary Discipline: TBD
- Requirement Type: TBD

##### MS22029826-74555: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74556: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74557: Diag RW Park Motor Failure Chime Enable (Value: 0-Disable, 1-Enable) (System Requirement)
- Variant: S237
- Stakeholder Requirement State: In Review
- System Requirement State: Draft
- Software Requirement State: Draft
- Primary Discipline: TBD
- Requirement Type: TBD

#### MS22029826-74549: Output Requirements (Heading)
- Variant: S237
- Stakeholder Requirement State: In Review
- System Requirement State: Draft
- Software Requirement State: Draft
- Primary Discipline: TBD
- Requirement Type: TBD

##### MS22029826-74551: Park Motor Failure Chime Functional Logic (Value: Off, On) (System Requirement)
- Variant: S237
- Stakeholder Requirement State: In Review
- System Requirement State: Draft
- Software Requirement State: Draft
- Primary Discipline: TBD
- Requirement Type: TBD

#### MS22029826-74550: Performance Requirements (Heading)
- Variant: S237
- Stakeholder Requirement State: In Review
- System Requirement State: Draft
- Software Requirement State: Draft
- Primary Discipline: TBD
- Requirement Type: TBD

##### MS22029826-74553 (System Requirement)
Table -Park Motor Failure Chime Functional Logic
| Ign Mode | LVSD/HVSD Flag | VAR_CODING_VEHICLE_CONTROL_UNIT | Diag RW Park Motor Failure Chime Enable | CAN Signal Missing or Never Received | VCU10_100(0X30A): ALERT_MSGS | Park Motor Failure Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x27 | Off |
| On/Off | Not Set | 1 | 1 | 0 | =0x27 | On |
- Variant: S237
- Stakeholder Requirement State: In Review
- System Requirement State: Draft
- Software Requirement State: Draft
- Primary Discipline: TBD
- Requirement Type: TBD

### MS22029826-74559: Stay In Park Chime (Heading)
- Variant: S237
- Stakeholder Requirement State: In Review
- System Requirement State: Draft
- Software Requirement State: Draft
- Primary Discipline: TBD
- Requirement Type: TBD

#### MS22029826-74560: Input Requirements (Heading)
- Variant: S237
- Stakeholder Requirement State: In Review
- System Requirement State: Draft
- Software Requirement State: Draft
- Primary Discipline: TBD
- Requirement Type: TBD

##### MS22029826-74564: IgnMode (Value: On, Off) (System Requirement)
- Variant: S237
- Stakeholder Requirement State: In Review
- System Requirement State: Draft
- Software Requirement State: Draft
- Primary Discipline: TBD
- Requirement Type: TBD

##### MS22029826-74566: LVSD/HVSD Flag (Value: Not Set, Set) (System Requirement)
- Variant: S237
- Stakeholder Requirement State: In Review
- System Requirement State: Draft
- Software Requirement State: Draft
- Primary Discipline: TBD
- Requirement Type: TBD

##### MS22029826-74567: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74568: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74569: Diag RW Stay In Park Chime Enable (Value: 0-Disable, 1-Enable) (System Requirement)
- Variant: S237
- Stakeholder Requirement State: In Review
- System Requirement State: Draft
- Software Requirement State: Draft
- Primary Discipline: TBD
- Requirement Type: TBD

#### MS22029826-74561: Output Requirements (Heading)
- Variant: S237
- Stakeholder Requirement State: In Review
- System Requirement State: Draft
- Software Requirement State: Draft
- Primary Discipline: TBD
- Requirement Type: TBD

##### MS22029826-74563: Stay In Park Chime Functional Logic (Value: Off, On) (System Requirement)
- Variant: S237
- Stakeholder Requirement State: In Review
- System Requirement State: Draft
- Software Requirement State: Draft
- Primary Discipline: TBD
- Requirement Type: TBD

#### MS22029826-74562: Performance Requirements (Heading)
- Variant: S237
- Stakeholder Requirement State: In Review
- System Requirement State: Draft
- Software Requirement State: Draft
- Primary Discipline: TBD
- Requirement Type: TBD

##### MS22029826-74565 (System Requirement)
Table - Stay In Park Chime Functional Logic
| Ign Mode | LVSD/HVSD Flag | VAR_CODING_VEHICLE_CONTROL_UNIT | Diag RW Stay In Park Chime Enable | CAN Signal Missing or Never Received | VCU10_100(0X30A): ALERT_MSGS | Stay In Park Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x28 | Off |
| On/Off | Not Set | 1 | 1 | 0 | =0x28 | On |
- Variant: S237
- Stakeholder Requirement State: In Review
- System Requirement State: Draft
- Software Requirement State: Draft
- Primary Discipline: TBD
- Requirement Type: TBD

### MS22029826-74570: Battery Low Temp Chime (Heading)
- Variant: S237
- Stakeholder Requirement State: In Review
- System Requirement State: Draft
- Software Requirement State: Draft
- Primary Discipline: TBD
- Requirement Type: TBD

#### MS22029826-74571: Input Requirements (Heading)
- Variant: S237
- Stakeholder Requirement State: In Review
- System Requirement State: Draft
- Software Requirement State: Draft
- Primary Discipline: TBD
- Requirement Type: TBD

##### MS22029826-74575: IgnMode (Value: On, Off) (System Requirement)
- Variant: S237
- Stakeholder Requirement State: In Review
- System Requirement State: Draft
- Software Requirement State: Draft
- Primary Discipline: TBD
- Requirement Type: TBD

##### MS22029826-74577: LVSD/HVSD Flag (Value: Not Set, Set) (System Requirement)
- Variant: S237
- Stakeholder Requirement State: In Review
- System Requirement State: Draft
- Software Requirement State: Draft
- Primary Discipline: TBD
- Requirement Type: TBD

##### MS22029826-74578: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74579: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74580: Diag RW Battery Low Temp Chime Enable (Value: 0-Disable, 1-Enable) (System Requirement)
- Variant: S237
- Stakeholder Requirement State: In Review
- System Requirement State: Draft
- Software Requirement State: Draft
- Primary Discipline: TBD
- Requirement Type: TBD

#### MS22029826-74572: Output Requirements (Heading)
- Variant: S237
- Stakeholder Requirement State: In Review
- System Requirement State: Draft
- Software Requirement State: Draft
- Primary Discipline: TBD
- Requirement Type: TBD

##### MS22029826-74574: Battery Low Temp Chime Functional Logic (Value: Off, On) (System Requirement)
- Variant: S237
- Stakeholder Requirement State: In Review
- System Requirement State: Draft
- Software Requirement State: Draft
- Primary Discipline: TBD
- Requirement Type: TBD

#### MS22029826-74573: Performance Requirements (Heading)
- Variant: S237
- Stakeholder Requirement State: In Review
- System Requirement State: Draft
- Software Requirement State: Draft
- Primary Discipline: TBD
- Requirement Type: TBD

##### MS22029826-74576 (System Requirement)
Table - Battery Low Temp Chime Functional Logic
| Ign Mode | LVSD/HVSD Flag | VAR_CODING_VEHICLE_CONTROL_UNIT | Diag RW Battery Low Temp Chime Enable | CAN Signal Missing or Never Received | VCU10_100(0X30A): ALERT_MSGS | Battery Low Temp Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x2A | Off |
| On/Off | Not Set | 1 | 1 | 0 | =0x2A | On |
- Variant: S237
- Stakeholder Requirement State: In Review
- System Requirement State: Draft
- Software Requirement State: Draft
- Primary Discipline: TBD
- Requirement Type: TBD

### MS22029826-74581: Coolant Leakage Park & Leave Vehicle Chime (Heading)
- Variant: S237
- Stakeholder Requirement State: In Review
- System Requirement State: Draft
- Software Requirement State: Draft
- Primary Discipline: TBD
- Requirement Type: TBD

#### MS22029826-74582: Input Requirements (Heading)
- Variant: S237
- Stakeholder Requirement State: In Review
- System Requirement State: Draft
- Software Requirement State: Draft
- Primary Discipline: TBD
- Requirement Type: TBD

##### MS22029826-74586: IgnMode (Value: On, Off) (System Requirement)
- Variant: S237
- Stakeholder Requirement State: In Review
- System Requirement State: Draft
- Software Requirement State: Draft
- Primary Discipline: TBD
- Requirement Type: TBD

##### MS22029826-74588: LVSD/HVSD Flag (Value: Not Set, Set) (System Requirement)
- Variant: S237
- Stakeholder Requirement State: In Review
- System Requirement State: Draft
- Software Requirement State: Draft
- Primary Discipline: TBD
- Requirement Type: TBD

##### MS22029826-74589: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74590: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74591: Diag RW Coolant Leakage Park & Leave Vehicle Chime Enable (Value: 0-Disable, 1-Enable) (System Requirement)
- Variant: S237
- Stakeholder Requirement State: In Review
- System Requirement State: Draft
- Software Requirement State: Draft
- Primary Discipline: TBD
- Requirement Type: TBD

#### MS22029826-74583: Output Requirements (Heading)
- Variant: S237
- Stakeholder Requirement State: In Review
- System Requirement State: Draft
- Software Requirement State: Draft
- Primary Discipline: TBD
- Requirement Type: TBD

##### MS22029826-74585: Coolant Leakage Park & Leave Vehicle Chime Functional Logic (Value: Off, On) (System Requirement)
- Variant: S237
- Stakeholder Requirement State: In Review
- System Requirement State: Draft
- Software Requirement State: Draft
- Primary Discipline: TBD
- Requirement Type: TBD

#### MS22029826-74584: Performance Requirements (Heading)
- Variant: S237
- Stakeholder Requirement State: In Review
- System Requirement State: Draft
- Software Requirement State: Draft
- Primary Discipline: TBD
- Requirement Type: TBD

##### MS22029826-74587 (System Requirement)
Table - Coolant Leakage Park & Leave Vehicle Chime Functional Logic
| Ign Mode | LVSD/HVSD Flag | VAR_CODING_VEHICLE_CONTROL_UNIT | Diag RW Coolant Leakage Park & Leave Vehicle Chime Enable | CAN Signal Missing or Never Received | VCU10_100(0X30A): ALERT_MSGS | Coolant Leakage Park & Leave Vehicle Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x2B | Off |
| On/Off | Not Set | 1 | 1 | 0 | =0x2B | On |
- Variant: S237
- Stakeholder Requirement State: In Review
- System Requirement State: Draft
- Software Requirement State: Draft
- Primary Discipline: TBD
- Requirement Type: TBD

### MS22029826-74592: Coolant Low Temp Chime (Heading)
- Variant: S237
- Stakeholder Requirement State: In Review
- System Requirement State: Draft
- Software Requirement State: Draft
- Primary Discipline: TBD
- Requirement Type: TBD

#### MS22029826-74593: Input Requirements (Heading)
- Variant: S237
- Stakeholder Requirement State: In Review
- System Requirement State: Draft
- Software Requirement State: Draft
- Primary Discipline: TBD
- Requirement Type: TBD

##### MS22029826-74597: IgnMode (Value: On, Off) (System Requirement)
- Variant: S237
- Stakeholder Requirement State: In Review
- System Requirement State: Draft
- Software Requirement State: Draft
- Primary Discipline: TBD
- Requirement Type: TBD

##### MS22029826-74599: LVSD/HVSD Flag (Value: Not Set, Set) (System Requirement)
- Variant: S237
- Stakeholder Requirement State: In Review
- System Requirement State: Draft
- Software Requirement State: Draft
- Primary Discipline: TBD
- Requirement Type: TBD

##### MS22029826-74600: VAR_CODING_VEHICLE_CONTROL_UNIT (Value: 0-Not Present, 1-Present) (System Requirement)
- Variant: S237
- Stakeholder Requirement State: In Review
- System Requirement State: Draft
- Software Requirement State: Draft
- Primary Discipline: TBD
- Requirement Type: TBD

##### MS22029826-74601: VCU10_100(0X30A):ALERT_MSGS (System Requirement)
VCU10_100(0X30A):ALERT_MSGS (0X0 No message/Default value, 0x1-Charge Fault, 0x2-Charge Complete, 0x3-Charge Terminate, 0X4-Go Slow, 0x5-Stop CAR, 0X6-Reserved, 0x7-Safe Mode, 0x8-Drive Fault, 0x9-Restart, 0xA-Resreved, 0xB-Service Due, 0xC-Stopping, 0xD-Insert Plug Full, 0xE-Power save mode, 0xF-Shift Gear to N, 0x10-Release Throttle, 0x11-Unplug CAR, 0X12-Turn ON Mains, 0x13~0x14 -Reserved, 0x15-Charge CAR, 0x16-Activate Revive, 0x17-Revive, 0x18-Revive Mode, 0x19-Revive Unsuccessful, 0x1A-Isolation Fault, 0x1B-GO slow(Flash), 0x1C-Hill Hold Deactivate, 0x1D-EPT High Temp, 0x1E-HV BATT High Temp, 0x1F-Reserved, 0x20-Charging, 0x21-Engage Park, 0x22-Preconditioning, 0x23-HVIL FAULT, 0X24-Turn Ign Key to start Vehicle, 0x25 Press Start stop to start, 0x26-Press Brake, 0x27-Park Motor Failure, 0x28-Stay in Park, 0x29-Reserved, 0x2A-Battey Low Temperature, 0x2B-Coolant Leakage Park & Leave Vehicle, 0x2C-Coolant low Temperature, 0x2D~0xFF-Reserved)
- Variant: S237
- Stakeholder Requirement State: In Review
- System Requirement State: Draft
- Software Requirement State: Draft
- Primary Discipline: TBD
- Requirement Type: TBD

##### MS22029826-74602: Diag RW Coolant Low Temp Chime Enable (Value: 0-Disable, 1-Enable) (System Requirement)
- Variant: S237
- Stakeholder Requirement State: In Review
- System Requirement State: Draft
- Software Requirement State: Draft
- Primary Discipline: TBD
- Requirement Type: TBD

#### MS22029826-74594: Output Requirements (Heading)
- Variant: S237
- Stakeholder Requirement State: In Review
- System Requirement State: Draft
- Software Requirement State: Draft
- Primary Discipline: TBD
- Requirement Type: TBD

##### MS22029826-74596: Coolant Low Temp Chime Functional Logic (Value: Off, On) (System Requirement)
- Variant: S237
- Stakeholder Requirement State: In Review
- System Requirement State: Draft
- Software Requirement State: Draft
- Primary Discipline: TBD
- Requirement Type: TBD

#### MS22029826-74595: Performance Requirements (Heading)
- Variant: S237
- Stakeholder Requirement State: In Review
- System Requirement State: Draft
- Software Requirement State: Draft
- Primary Discipline: TBD
- Requirement Type: TBD

##### MS22029826-74598 (System Requirement)
Table - Coolant Low Temp Chime Functional Logic
| Ign Mode | LVSD/HVSD Flag | VAR_CODING_VEHICLE_CONTROL_UNIT | Diag RW Coolant Low Temp Chime Enable | CAN Signal Missing or Never Received | VCU10_100(0X30A): ALERT_MSGS | Coolant Low Temp Chime Functional Logic |
| --- | --- | --- | --- | --- | --- | --- |
| On/Off | Set | X | X | X | X | Off |
| On/Off | Not Set | 0 | X | X | X | Off |
| On/Off | Not Set | 1 | 0 | X | X | Off |
| On/Off | Not Set | 1 | 1 | 1 | X | Off |
| On/Off | Not Set | 1 | 1 | 0 | !=0x2C | Off |
| On/Off | Not Set | 1 | 1 | 0 | =0x2C | On |
- Variant: S237
- Stakeholder Requirement State: In Review
- System Requirement State: Draft
- Software Requirement State: Draft
- Primary Discipline: TBD
- Requirement Type: TBD

### MS22029826-103748: Seatbelt Chime - Silver Box Adaptation (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

#### MS22029826-103749: Input Requirements (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-103752: IgnMode (Value: Off, On) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103755: LVSD/HVSD Flag (Value: Not Set, Set) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103758: VAR_CODING_SUPPLEMENTARY_RESTRAINT_SYSTEM(Value: 0-Not Present, 1-Present) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103762: VAR_CODING_MAHINDRA_BODY_FUNCTION_MODULE (Value: 0-Not Present, 1-Present) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103766: FEATURE_CODE_CODRIVER_SBR_CONFIG (Value: 0- Disabled, 1- Enabled) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103769: FEATURE_CODE_REARSEATBELT_INPUT_SEL (Value: 0 - SBRM 1- MBFM) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103771: FEATURE_CODE_REAR_SEAT_COMBINATION (Value: 0 ,1 - Option1, 2 - Option2, 3 - Option3) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103773 (System Requirement)
SRS1_20: STS_SEAT_BLT_DRV (Value: 0x0-Not Buckled,0x1-Buckled, 0x2-Buckle Faulty,0x3-
Reserved)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103774: SRS1_20:SRS_CRC(Value:0x0 to 0xFF) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103776 (System Requirement)
SRS1_20: STS_SEAT_BLT_PSGR (Value: 0x0-Not Buckled,0x1-Buckled, 0x2-Buckle Faulty,0x3-
Reserved)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103778 (System Requirement)
EMS1_10: CURRENT GEAR_MT (Value: Value: 0-Neutral, 1-1st gear, 2-2nd gear, 3-3rd gear, 4-4th
gear,5-5th gear, 6-6th gear, 7-Reverse, 8~0xE-Reserved,0xF-Invalid)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103780 (System Requirement)
TCU6_20: TGS_LEVER (Value: Value: 0~5-Reserved,0x6-Drive, 0x7-Neutral 0x8-Reverse 0x7-Neutral
0x8-Reverse, 0x9-Park, 0x9-Park, 0xA-Trip+,0xB-Trip-0xC-M-forward drive 0xD-Default Value ,0xE-Middle position,0xF-Signal Invalid)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103784: Engine Running St (Value: Yes, No) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103786: Vehicle Moving St (Value: Yes, No) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103787: VSpd Ind (Refer Speedometer) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103782 (System Requirement)
MBFM9_500: PSGR_REAR_SEAT_BELT (Value:0x0-0x3F)
BIT 0:- Rear Left Passenger(0-Not Buckled,1-Buckled)
BIT 1:- Rear Middle Passenger(0-Not Buckled,1-Buckled)
BIT 2:- Rear Right Passenger(0-Not Buckled,1-Buckled)
BIT 3:- Rear 3rd RowLeft Passenger(0-Not Buckled,1-Buckled)
BIT 4:- Rear 3rd Row Middle Passenger(0-Not Buckled,1-Buckled)
BIT 5:- Rear 3rd Row Right Passenger(0-Not Buckled,1-Buckled)
0x0:-Not Buckled/DV
0x1:-Buckled
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103783: SBRM1_100: PSGR_REAR_SEAT_BELT (System Requirement)
SBRM1_100: PSGR_REAR_SEAT_BELT
BIT 0:- Rear Left Passenger
BIT 1:- Rear Middle Passenger
BIT 2:- Rear Right Passenger
BIT 3:- Rear 3rd RowLeft Passenger
BIT 4:- Rear 3rd Row Middle Passenger
BIT 5:- Rear 3rd Row Right Passenger
0x0:-Not Buckled/DV
0x1:-Buckled
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103788: Odo Out (Refer odometer) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103789: Diag RW SeatBelt Chime Enable (Value: 0-Disable, 1-Enable) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103790: Diag RW Rear PSGR SeatBelt Chime Enable (Value: 0-Disable, 1-Enable) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103791: Diag RW Seatbelt FW Signal Resume (Default-10km/h) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103793: Configurable table for Front (Drv,Psgr) (System Requirement)
|  | Engine RPM time check (Diag RW SBR Eng Running Time) | Forward motion time check. (Diag RW SBR Moving Time) | ODO distance (m) (Diag RW SBR Moving Distance) | Vehicle speed check for final trigger (Diag RW SBR Speed Threshold) | Chime duration (Diag RW SBR Final Chime Duration) |
| --- | --- | --- | --- | --- | --- |
| Final signal | 59 sec | 59 sec | 490 | >=24 kmph | 95 sec |
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103794: Configurable table for Rear: (System Requirement)
|  | Chime duration (Diag RW Rear SBR Final Chime Duration) |
| --- | --- |
| Final signal | 35 sec |
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-103750: Output Requirements (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-103753: SeatBelt Chime Functional Logic (Value: Off, On) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103756: Rear Seat Belt Final Condition St (Value: No, Yes) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103760: SeatBelt Final Condition St (Value: No, Yes) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103761: IC2_200:SEAT_BELT_REMAINDER_FL_REAR( Value: 0-Default, 1-Pattern 3, 2-Reserved, 3-Reserved) (System Requirement)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-103751: Performance Requirements (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-103754: Table- Seat Belt Drv Chime Configuration (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-103796: VAR_CODING_SUPPLIMENTARY_RESTRAINT_SYSTEM (System Requirement)
| VAR_CODING_SUPPLIMENTARY_RESTRAINT_SYSTEM | Diag RW Seat Belt Drv Chime Enable | Drv SeatBelt Chime Configuration |
| --- | --- | --- |
| 0 | X | 0 |
| 1 | 0 | 0 |
| 1 | 1 | 1 |
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103757: Table- Psgr Seat Belt Chime Configuration (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-103803: VAR_CODING_SUPPLIMENTARY_RESTRAINT_SYSTEM (System Requirement)
| VAR_CODING_SUPPLIMENTARY_RESTRAINT_SYSTEM | FEATURE_CODE_CODRIVER_SBR_CONFIG​ | Diag RW Seat Belt Drv Chime Enable | Psgr SeatBelt Chime Configuration |
| --- | --- | --- | --- |
| 0 | X | X | 0 |
| 1 | 0 | X | 0 |
| 1 | 1 | 0 | 0 |
| 1 | 1 | 1 | 1 |
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103763: Table- Seat Belt Final Condition St (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-103798 (System Requirement)
After ignition ON and anyone of the seatbelt is not buckled and vehicle should achieve anyone of the below conditions to start the final signal (chime).
| 1.Engine Running St >= Diag RW SBR Eng Running RPM for Diag RW SBR Eng Running Time | 2.Vehicle Moving St >= Diag RW SBR Moving Threshold for Diag RW SBR Moving Time | 1. ODO Out >= Vehicle Covered Diag RW SBR Moving Distance in forward motion | 4.VSpd Ind >= Diag RW SBR Speed Threshold in forward motion | SeatBelt Final Condition St |
| --- | --- | --- | --- | --- |
| No | No | No | No | No |
| X | X | X | Yes | Yes |
| X | X | Yes | X | Yes |
| X | Yes | X | X | Yes |
| Yes | X | X | X | Yes |
Note: Point 1~3 Timer to be restarted to meet the final condition. Point 4 to be met while revaluating the final condition.
Once condition evaluated and met then all conditions to be restarted again from next buckle change
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103764: Table-Rear Seat belt Final Condition St (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-103799: VSpd Ind >= Diag RW SBR Speed Threshold in forward motion (System Requirement)
| VSpd Ind >= Diag RW SBR Speed Threshold in forward motion | Rear Seat Belt Final Condition St |
| --- | --- |
| No | No |
| Yes | Yes |
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103767: Table- Seat Belt Chime Driver St (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-103800: . (System Requirement)
| Drv SeatBelt Chime Configuration | CAN Signal Missing/ Never Received | SRS1_20:SRS_CRC SRS1_20:STS_SEAT_BELT_DRV |  | Drv Chime SBR St |
| --- | --- | --- | --- | --- |
| 0 | X | X | X | Off |
| 1 | 1 | X | X | Off |
| 1 | 0 | Invalid | X | Off |
| 1 | 0 | Valid | 0x0(Not Buckled/Default) | On |
| 1 | 0 | Valid | 0x1(Buckled) | Off |
| 1 | 0 | Valid | 0x2(Buckle faulty) | Off |
| 1 | 0 | Valid | 0x3(reserved) | Off |
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103768: Table- Seat Belt Chime Psgr St (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-103801: PSGR SeatBelt Chime Configuration (System Requirement)
| PSGR SeatBelt Chime Configuration | CAN Signal Missing/ Never Received | SRS1_20:SRS_CRC | SRS1_20: | Psgr Chime SBR St |
| --- | --- | --- | --- | --- |
| PSGR SeatBelt Chime Configuration | CAN Signal Missing/ Never Received | SRS1_20:SRS_CRC | STS_SEAT_BELT_PSGR | Psgr Chime SBR St |
| 0 | X | X | X | Off |
| 1 | 1 | X | X | Off |
| 1 | 0 | Invalid | X | Off |
| 1 | 0 | Valid | 0x0(Not Buckled/Default) | On |
| 1 | 0 | Valid | 0x1(Buckled) | Off |
| 1 | 0 | Valid | 0x2(Buckle faulty) | Off |
| 1 | 0 | Valid | 0x3(reserved) | Off |
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103770: Table- Rear Chime SeatBelt St (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-103802 (System Requirement)
If FEATURE_CODE_REAR_SEAT_COMBINATION = 0 OR 1
| Diag RW Rear PSGR SeatBelt Chime Enable | FEATURE_CODE _REARSEATBELT _SEL | VAR_CODING_MAHINDRA _BODY_FUNCTION_MODULE | CAN Signal Missing/ Never Received | MBFM9_500: PSGR_REAR_SEAT_BE LT |  |  | SBRM1_100: PSGR_REAR_SEAT_BE LT |  |  | Rear Chime SBR St |
| --- | --- | --- | --- | --- | --- | --- | --- | --- | --- | --- |
| Diag RW Rear PSGR SeatBelt Chime Enable | FEATURE_CODE _REARSEATBELT _SEL | VAR_CODING_MAHINDRA _BODY_FUNCTION_MODULE | CAN Signal Missing/ Never Received | Bit 2 | Bit 1 | Bit 0 | Bit 2 | Bit 1 | Bit 0 | Rear Chime SBR St |
| 0 | x | x | x | x |  |  | X |  |  | Off |
| 1 | 1 | 0 | x | x |  |  | x |  |  | Off |
| 1 | 1 | 1 | 1 | x |  |  | x |  |  | Off |
| 1 | 1 | 1 | 0 | 1 | 1 | 1 | x |  |  | Off |
| 1 | 1 | 1 | 0 | X | x | 0 | x |  |  | on |
| 1 | 1 | 1 | 0 | x | 0 | x | x |  |  | on |
| 1 | 1 | 1 | 0 | 0 | x | x | x |  |  | on |
| 1 | 0 | x | x | x |  |  | x |  |  | Off |
| 1 | 0 | x | 1 | x |  |  | x |  |  | Off |
| 1 | 0 | x | 0 | x |  |  | 1 | 1 | 1 | off |
| 1 | 0 | x | 0 | x |  |  | X | x | 0 | On |
| 1 | 0 | x | 0 | x |  |  | x | 0 | X | On |
| 1 | 0 | x | 0 | x |  |  | 0 | x | x | On |
Note:
Appropriate CAN signal shall be used based on MBFM/SBRM
Note: VC check not required for SBRM node as in few variants update done from SBRM and few variants
from MBFM. As per M&M input ONLY Feature code shall be used in case on Enable/Disable
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-103815 (System Requirement)
If FEATURE_CODE_REAR_SEAT_COMBINATION = 2,
| Diag RW Rear PSGR SeatBelt Chime Enable | FEATURE_CODE _REARSEATBELT _SEL | VAR_CODING_MAHINDRA _BODY_FUNCTION_MODULE | CAN Signal Missing/ Never Received | MBFM9_500: PSGR_REAR_SEAT_BE LT |  |  |  |  | SBRM1_100: PSGR_REAR_SEAT_BE LT |  |  |  |  | Rear Chime SBR St |
| --- | --- | --- | --- | --- | --- | --- | --- | --- | --- | --- | --- | --- | --- | --- |
| Diag RW Rear PSGR SeatBelt Chime Enable | FEATURE_CODE _REARSEATBELT _SEL | VAR_CODING_MAHINDRA _BODY_FUNCTION_MODULE | CAN Signal Missing/ Never Received | Bit 5 | Bit 3 | Bit 2 | Bit 1 | Bit 0 | Bit 5 | Bit 3 | Bit 2 | Bit 1 | Bit 0 | Rear Chime SBR St |
| 0 | x | x | x | x |  |  |  |  | X |  |  |  |  | Off |
| 1 | 1 | 0 | x | x |  |  |  |  | X |  |  |  |  | Off |
| 1 | 1 | 1 | 1 | x |  |  |  |  | X |  |  |  |  | Off |
| 1 | 1 | 1 | 0 | 1 | 1 | 1 | 1 | 1 |  |  |  |  |  | Off |
| 1 | 1 | 1 | 0 | X | X | x | x | 0 |  |  |  |  |  | on |
| 1 | 1 | 1 | 0 | X | X | x | 0 | x |  |  |  |  |  | on |
| 1 | 1 | 1 | 0 | X | X | 0 | x | x |  |  |  |  |  | on |
| 1 | 1 | 1 | 0 | X | 0 | X | X | x |  |  |  |  |  | on |
| 1 | 1 | 1 | 0 | 0 | x | x | X | x |  |  |  |  |  | on |
| 1 | 0 | x | x | x |  |  |  |  | x |  |  |  |  | Off |
| 1 | 0 | x | 1 | x |  |  |  |  | x |  |  |  |  | Off |
| 1 | 0 | x | 0 | x |  |  |  |  | 1 | 1 | 1 | 1 | 1 | off |
| 1 | 0 | x | 0 | x |  |  |  |  | X | X | x | X | 0 | On |
| 1 | 0 | x | 0 | x |  |  |  |  | X | x | X | 0 | X | On |
| 1 | 0 | x | 0 | x |  |  |  |  | x | x | 0 | X | x | On |
| 1 | 0 | x | 0 | x |  |  |  |  | x | 0 | X | X | x | On |
| 1 | 0 | x | 0 | x |  |  |  |  | 0 | X | x | X | x | On |
Note:
Appropriate CAN signal shall be used based on MBFM/SBRM
Note: VC check not required for SBRM node as in few variants update done from SBRM and few variants
from MBFM. As per M&M input ONLY Feature code shall be used in case on Enable/Disable.
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-103816 (System Requirement)
If FEATURE_CODE_REAR_SEAT_COMBINATION = 3,
| Diag RW Rear PSGR SeatBelt Chime Enable | FEATURE_CODE _REARSEATBELT _SEL | VAR_CODING_MAHINDRA _BODY_FUNCTION_MODULE | CAN Signal Missing/ Never Received | MBFM9_500: PSGR_REAR_SEAT_BE LT |  |  |  | SBRM1_100: PSGR_REAR_SEAT_BE LT |  |  |  | Rear Chime SBR St |
| --- | --- | --- | --- | --- | --- | --- | --- | --- | --- | --- | --- | --- |
| Diag RW Rear PSGR SeatBelt Chime Enable | FEATURE_CODE _REARSEATBELT _SEL | VAR_CODING_MAHINDRA _BODY_FUNCTION_MODULE | CAN Signal Missing/ Never Received | Bit 5 | Bit 3 | Bit 2 | Bit 0 | Bit 5 | Bit 3 | Bit 2 | Bit 0 | Rear Chime SBR St |
| 0 | x | x | x | x |  |  |  | X |  |  |  | Off |
| 1 | 1 | 0 | x | x |  |  |  | x |  |  |  | Off |
| 1 | 1 | 1 | 1 | x |  |  |  | x |  |  |  | Off |
| 1 | 1 | 1 | 0 | 1 | 1 | 1 | 1 | x |  |  |  | Off |
| 1 | 1 | 1 | 0 | X | X | x | 0 | x |  |  |  | on |
| 1 | 1 | 1 | 0 | X | X | 0 | x | x |  |  |  | on |
| 1 | 1 | 1 | 0 | X | 0 | x | x | x |  |  |  | on |
| 1 | 1 | 1 | 0 | 0 | X | x | x | x |  |  |  | on |
| 1 | 0 | x | x | x |  |  |  | x |  |  |  | Off |
| 1 | 0 | x | 1 | x |  |  |  | x |  |  |  | Off |
| 1 | 0 | x | 0 | x |  |  |  | 1 | 1 | 1 | 1 | off |
| 1 | 0 | x | 0 | x |  |  |  | X | X | x | 0 | On |
| 1 | 0 | x | 0 | x |  |  |  | X | x | 0 | X | On |
| 1 | 0 | x | 0 | x |  |  |  | x | 0 | x | x | On |
| 1 | 0 | x | 0 | x |  |  |  | 0 | x | x | x | On |
Note:
Appropriate CAN signal shall be used based on MBFM/SBRM
Note: VC check not required for SBRM node as in few variants update done from SBRM and few variants
from MBFM. As per M&M input ONLY Feature code shall be used in case on Enable/Disable.
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103772: Table- Seat Belt Chime Functional Logic (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-103804: . (System Requirement)
| IgnMode | LVSD/HVSD Flag | Drv Chime SBR St | Psgr Chime SBR St | CAN Signal missing for #Gear Signal | CURRENT_GEAR_MT (or) TGS_LEVER | SeatBelt Final Condition St | Drv /Psgr SeatBelt Chime Logic |
| --- | --- | --- | --- | --- | --- | --- | --- |
| Off | X | X | X | X | X | X | Off |
| On | Set | X | X | X | X | X | Off |
| On | Not Set | Off | Off | X | X | X | Off |
| On | Not Set | Any One ON |  | 1 | X | X | Off |
| On | Not Set | Any One ON |  | 0 | Reverse | X | Off |
| On | Not Set | On | X | 0 | ^#Not Reverse | No | Off |
| On | Not Set | On | X | 0 | ^#Not Reverse | Yes | On |
| On | Not Set | X | On | 0 | ^#Not Reverse | Yes | On |
Note:
1.Appropriate gear signal shall be used based on MT/AT
1. Reverse Usecase:
When Forward gear is re-selected and forward motion commences (>10 km/h (Diag RW Seatbelt FW
Signal Resume), the Final Signal must resume again (Note: Only Elapsed duration chime shall Play)
1. Whenever there is a change in either or both ‘Drv Chime SBR St = On’ or ‘PSGR Chime SBR St = On’
or ‘from Off, the ‘SeatBelt Final Condition St’ shall be evaluated from start and the chime shall be
retriggered when ‘SeatBelt Final Condition St=TRUE’.
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103775: Table-Rear Seatbelt Chime Functional Logic (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-103795: Ign Mode (System Requirement)
| Ign Mode | LVDS/HV SD Flag | Rear Chim e SBR St | CAN Signal missi ng for ^#1Gear | CURRENT_GEAR _MT (or) TGS_LEVER | Rear Seat Belt Final Conditi | Rear Chime Logic |
| --- | --- | --- | --- | --- | --- | --- |
|  |  |  |  |  | on St |  |
| Off | X | X | X | X | X | Off |
| On | Set | X | X | X | X | Off |
| On | Not set | Off | X | X | X | Off |
| On | Not set | On | 1 | X | X | Off |
| On | Not Set | On | 0 | Reverse | X | Off |
| On | Not Set | On | 0 | ^#1Not Reverse | Not Met | Off |
| On | Not Set | On | 0 | ^#1Not Reverse | Met | On |
Note:
1.Appropriate gear signal shall be used based on MT/AT
1. Reverse Use case:
When Forward gear is re-selected and forward motion commences (>10 km/h (Diag RW Seatbelt FW
Signal Resume), the Final Signal must resume again (Note: Only Elapsed duration chime shall Play)
3.Whenever there is a change in ‘Rear Chime SBR St = On’ ‘from Off, the ‘ Rear SeatBelt Final Condition
St’ shall be evaluated from start and the chime shall be retriggered when ‘Rear Seat Belt Final Condition
St =TRUE’.
4.IC2_100: SEAT_BELT_REMAINDER_FL_REAR: Shall be Set to 1 when Rear chime is played for 35
Sec (Diag RW SBR Final Chime Duration)
It shall change 1->0 when reverse gear engaged. It will send 1 again for remaining period once more
than 10km speed met.
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-103809: Drv /Psgr SeatBelt Chime Logic (System Requirement)
| Drv /Psgr SeatBelt Chime Logic | Rear SeatBelt Chime Logic | Seatbelt Chime Functional logic |
| --- | --- | --- |
| Off | Off | Off |
| On | Off | Chime play for 95sec (Diag RW SBR Final Chime Duration) |
| Off | On | Chime play for 35sec (Diag RW Rear SBR Final Chime Duration) |
| On | On | ^# Chime play for FOR REQUIRED duration |
Note: In case both DRV AND REAR ARE ON chime needs play for required calibration
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-103810 (System Requirement)
Ex:
1.Drv/Psgr unbuckled -> Chime to Play 95 sec. chime started and 80 sec is completed.
2.Rear unbuckled->chime to play for 35 sec.
3. Total duration of chime play is 80+35sec =115s (This meets 95 sec +35 sec)
In case unbuckle of any seatbelt in between Timer shall be restarted
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-103811: --When the trigger 'SeatBelt Chime Functional Logic == TRUE' i-- (Information)
---When the trigger 'SeatBelt Chime Functional Logic == TRUE' is met, the chime 'Seat Belt warning - Part1'-
-shall be triggered immediately whereas the other chime 'Seat Belt warning - Part2' shall be triggered with-
a specific delay of 12sec (equals the duration of Part1 WAV duration x no. of cycles).
This is done such that Part2 chime shall ideally playback right after elapse of Part1 chime/
The priority shall be defined such that Part1 is higher priority than Part2 so that Part1 always plays first
before Part2--
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-103777: CAN Tx -Based on CO - Driver /Rear Seatbelt logic (Heading)
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: TBD
- Requirement Type: TBD

###### MS22029826-103797: CAN Tx Based on CODRIVER/ REAR (System Requirement)
CAN Tx Based on CODRIVER/ REAR
| FEATURE_CODE_CODRIVER_SBR_TT_CONFIG | Diag RW Rear PSGR SeatBelt Chime Enable | PSGR SeatBelt Chime Logic | Rear SeatBelt Chime Logic | IC2_200:SEAT_BELT_REMAINDER_FL_REAR |
| --- | --- | --- | --- | --- |
| 0 | X | OFF | X | 0 |
| 0 | X | ON | X | 1 |
| 1 | 0 | X | X | 0 |
| 1 | 1 | X | OFF | 0 |
| 1 | 1 | X | ON | 1 |
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-103806 (System Requirement)
When SBR chime is being played in a channel, no other chime shall be played although the other channel is free.
Once played, SBR chime shall NOT be played again the same IGN cycle unless there is a change in Buckle status.
In case of change from Buckle > Unbuckle, the final condition shall be set to False and re-evaluated again from start.
- Variant: S220_SB_ADP_W601-V1, S220_SB_ADP_W601-V2, Z112_SB_ADP_Z101-V5, Z112_SB_ADP_Z101-V6, Z112_SB_ADP_Z101-V7
- Stakeholder Requirement State: In Review
- System Requirement State: Draft
- Software Requirement State: Draft
- Primary Discipline: SW
- Requirement Type: Functional

### MS22029826-104805: FVSA Chime (Heading)
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

#### MS22029826-104806: Input Requirements (Heading)
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-104810: IgnMode (Value: On, Off) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-104812: LVSD/HVSD Flag (Value: Not Set, Set) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-104813: FEATURE_CODE_FVSA (Values: 0 - Not Present; 1 - Present) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-104814: VAR_CODING_FRONT_CAMERA_MODULE (Values: 0 - Not Present; 1 - Present) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-104815: Diag RW FVSA Chime Enable (Value: 0-Disable, 1-Enable) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-104816: FCM_TSR_100: FVSA_WARN (Values: 0x0 - No warning, 0x1 - FVSA Warning, 0x2 - Reserved) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

#### MS22029826-104807: Output Requirements (Heading)
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-104809: FVSA Chime Functional Logic (Value: Off, On) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

#### MS22029826-104808: Performance Requirements (Heading)
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-104811: Table - FVSA Chime Configuration (System Requirement)
| VAR_CODING_FRONT_CAMERA_MODULE | FEATURE_CODE_FVSA | Diag RW FVSA Chime Enable | FVSA Chime Configuration |
| --- | --- | --- | --- |
| 0 | X | X | 0 |
| 1 | 0 | X | 0 |
| 1 | 1 | 0 | 0 |
| 1 | 1 | 1 | 1 |
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

##### MS22029826-104819: Table - FVSA Chime Functional Logic (System Requirement)
| IgnMode | LVSD/HVSD Flag | FVSA Chime Configuration | CAN missing/never received | FCM_TSR_100: FVSA_WARN | FVSA Chime Functional Logic |
| --- | --- | --- | --- | --- | --- |
| Off | X | X | X | X | OFF |
| On | Set | X | X | X | OFF |
| On | Not Set | 0 | X | X | OFF |
| On | Not Set | 1 | 1 | X | OFF |
| On | Not Set | 1 | 0 | 0x1 | ON: FVSA_AUDIO_CHIME_1 |
| On | Not Set | 1 | 0 | !=(0x1) | OFF |
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

### MS22029826-105131: IACC Chime (Heading)
- Variant: S220, S237, W502, Z112_SB_ADP_Z101-V5, Z112_SB_ADP_Z101-V6, Z112_SB_ADP_Z101-V7
- Stakeholder Requirement State: In Review
- System Requirement State: Draft
- Software Requirement State: Draft
- Primary Discipline: TBD
- Requirement Type: TBD

#### MS22029826-105132: Input Requirements (Heading)
- Variant: S220, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-105135: Ign Mode (Value: Off, On) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-105138: LVSD / HVSD Flag (Value: Not set, Set) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-105139: FCM_TSR_100: IACC_SYS_MSG_CHIME(Value: 0x0- No Chime, 0x1- Chime_5, 0x2- Chime_6 , 0x3- Reserved) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-105142: Diag RW INTELL_ACC_Chime Enable (Value: 0-Disable, 1-Enable) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-105470: VAR_CODING_FRONT_CAMERA_MODULE(Value: 0-Not Present, 1-Present) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-106828: FEATURE_CODE_IACC(Values: 0 - Not Present; 1 - Present) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-105133: Output Requirements (Heading)
- Variant: S220, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-105136: IACC Chime Functional Logic (Value: 0x1 - ON, 0x2 -ON, OFF) (System Requirement)
- Variant: S220, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

#### MS22029826-105134: Performance Requirements (Heading)
- Variant: S220, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

##### MS22029826-105137: IACC Chime Functional Logic (Heading)
- Variant: S220, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-105140: VARIANT (System Requirement)
| VARIANT_CODING_FRONT_CAMERA_MODULE | FEATURE_CODE_IACC | Diag RW INTELL_ACC_Chime Enable | Intelligent ACC chime Configuration |
| --- | --- | --- | --- |
| 0 | X | X | 0 |
| 1 | 0 | X | 0 |
| 1 | 1 | 0 | 0 |
| 1 | 1 | 1 | 1 |
- Variant: S220, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

###### MS22029826-105141: IACC Chime Functional Logic (System Requirement)
| IgnMode | LVSD / HVSD Flag | Intelligent ACC chime Configuration | CAN missing/never received | FCM_TSR_100: IACC_SYS_MSG_CHIME | IACC Chime Functional Logic |
| --- | --- | --- | --- | --- | --- |
| Off | X | X | X | X | OFF |
| On | Set | X | X | X | OFF |
| On | No Set | 0 | X | X | OFF |
| On | Not Set | 1 | 1 | X | OFF |
| On | Not Set | 1 | 0 | 0x0 | OFF |
| On | Not Set | 1 | 0 | 0x1 | On |
| On | Not Set | 1 | 0 | 0x2 | On |
| On | Not Set | 1 | 0 | 0x3 | OFF |
- Variant: S220, S237, W502, Z112_SB_ADP_Z101-V5, Z112_SB_ADP_Z101-V6, Z112_SB_ADP_Z101-V7
- Stakeholder Requirement State: In Review
- System Requirement State: Draft
- Software Requirement State: Draft
- Primary Discipline: SW
- Requirement Type: Functional

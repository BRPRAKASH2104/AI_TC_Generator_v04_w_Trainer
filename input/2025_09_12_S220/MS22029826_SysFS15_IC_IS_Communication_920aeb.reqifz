# Json2ReqIF Transformation

# Specification: SysFS15_IC_IS_Communication
- JDA Snapshot Date: 2025-08-21 12:56:13

## MS22029826-35852: IVI to IC Communication (System Requirement)
- Variant: S220, S237, W502
- Stakeholder Requirement State: In Review
- System Requirement State: Draft
- Software Requirement State: Draft
- Primary Discipline: SW
- Requirement Type: TBD

### MS22029826-35854: IVI to IC communication shall happen internally not via CAN for the below features (System Requirement)
- Variant: S220, S237, W502
- Stakeholder Requirement State: In Review
- System Requirement State: Draft
- Software Requirement State: Draft
- Primary Discipline: SW
- Requirement Type: TBD

### MS22029826-35856: AAP/CP Certification requirements to be complied (System Requirement)
- Variant: S220, S237, W502
- Stakeholder Requirement State: In Review
- System Requirement State: Draft
- Software Requirement State: Draft
- Primary Discipline: SW
- Requirement Type: TBD

### MS22029826-35858: For audio, phone and navigation Along with APP/CP , native infotainment meta data shall also be considered (System Requirement)
- Variant: S220, S237, W502
- Stakeholder Requirement State: In Review
- System Requirement State: Draft
- Software Requirement State: Draft
- Primary Discipline: SW
- Requirement Type: TBD

### MS22029826-35860: Source Info (Heading)
- Variant: S220, S237, W502
- Stakeholder Requirement State: In Review
- System Requirement State: Draft
- Software Requirement State: Draft
- Primary Discipline: TBD
- Requirement Type: TBD

#### MS22029826-43655: Source type (System Requirement)
| Source type |
| --- |
| USB |
| AAP |
| CP |
| Bluetooth |
| ipod |
| Tuner |
| MyDrive |
| Alexa |
- Variant: S220, S237, W502
- Stakeholder Requirement State: In Review
- System Requirement State: Draft
- Software Requirement State: Draft
- Primary Discipline: SW
- Requirement Type: TBD

### MS22029826-35861: Phone Info (Heading)
- Variant: S220, S237, W502
- Stakeholder Requirement State: In Review
- System Requirement State: Draft
- Software Requirement State: Draft
- Primary Discipline: TBD
- Requirement Type: TBD

#### MS22029826-43657: If FEATURE_CODE_PHONE DISPLAY =1 & VAR_CODING_INFOTAINMENT_SYSTEM =1 then the display shall be available (System Requirement)
- Variant: S220, S237, W502
- Verification Method: TBD
- Stakeholder Requirement State: In Review
- System Requirement State: Draft
- Secondary Disciplines: TBD
- Software Requirement State: Draft
- Primary Discipline: SW
- Requirement Type: TBD

#### MS22029826-43659: If FEATURE_CODE_PHONE DISPLAY =1 & VAR_CODING_INFOTAINMENT_SYSTEM =1 then the display shall be available (System Requirement)
- Variant: S220, S237, W502
- Verification Method: TBD
- Stakeholder Requirement State: In Review
- System Requirement State: Draft
- Secondary Disciplines: TBD
- Software Requirement State: Draft
- Primary Discipline: SW
- Requirement Type: TBD

#### MS22029826-43661: SourceCall State (System Requirement)
| Source | Call State | Contact Name A / B | Call Duration (Minutes & Seconds &Hour ) | Contact Picture A / B | Connection Status | Device Name |
| --- | --- | --- | --- | --- | --- | --- |
| AAP | X | X | X | X | X | X |
| CP | X | X | X | X | X | X |
| Bluetooth | X | X | X | X | X | X |
Call State: Active Call, Active Call On Hold, Conference Call, Call Ended
Contact Name A: Name received from the source shall be displayed during active call or active call on Hold. If Name is not available from the source, then contact number shall be displayed.
Contact Name B: During Conference call or Conference call on Hold, Number of participants shall be displayed.
Call Duration: Duration of call shall be displayed with Minutes and seconds. If call exceeds more than 60 minutes, then hour also shall be displayed along with minutes and seconds.
Contact Picture A: During Active call or Call on Hold, Image received from AA / CP source shall be displayed. If Image is not available from the source, then static image shall be displayed as per the HMI Requirement.
Contact Picture B: During Conference call or Conference call On Hold, Static image shall be displayed as per the HMI Requirement.
Connection Status: Phone Connected, Phone Not Connected
Device Name: Device Name to show when no Active call and Phone is Connected
Device from which Phone source is connected.
Connected Source: Android Auto, Car Play, Bluetooth
- Variant: S220, S237, W502
- Stakeholder Requirement State: In Review
- System Requirement State: Draft
- Software Requirement State: Draft
- Primary Discipline: SW
- Requirement Type: TBD

### MS22029826-35863: Audio Info (Heading)
- Variant: S220, S237, W502
- Stakeholder Requirement State: In Review
- System Requirement State: Draft
- Software Requirement State: Draft
- Primary Discipline: TBD
- Requirement Type: TBD

#### MS22029826-43663: If FEATURE_CODE_MEDIA DISPLAY =1 &VAR_CODING_INFOTAINMENT_SYSTEM =1, then the display shall be available (System Requirement)
- Variant: S220, S237, W502
- Verification Method: TBD
- Stakeholder Requirement State: In Review
- System Requirement State: Draft
- Secondary Disciplines: TBD
- Software Requirement State: Draft
- Primary Discipline: SW
- Requirement Type: TBD

#### MS22029826-43665: Source (System Requirement)
| Primary Source |  | Tuner Playing |  |  |  | Source Playing |  |  |  |  |  |
| --- | --- | --- | --- | --- | --- | --- | --- | --- | --- | --- | --- |
| Primary Source |  | Tuner Type | Tuner State | Tuner station name | Tuner Station Frequency | Album Art | Tack name | Tack info Album Name | MSP Icon | Playback state | Elapsed time of track |
| Primary Source | USB Audio | NA | NA | NA | NA | X | X | X | NA | X | X |
| Primary Source | AAP | NA | NA | NA | NA | X | X | X | NA | X | X |
| Primary Source | CP | NA | NA | NA | NA | X | X | X | NA | X | X |
| Primary Source | Bluetooth | NA | NA | NA | NA | X | X | X | NA | X | X |
| Primary Source | ipod | NA | NA | NA | NA | X | X | X | NA | X | X |
| Primary Source | MyDrive Audio | NA | NA | NA | NA | X | X | X | NA | X | X |
| Primary Source | Alexa | NA | NA | NA | NA | X | X | X | X | NA | NA |
| Primary Source | Unknown(3rd party Audio Apps) | NA | NA | NA | NA | NA | NA | NA | NA | NA | NA |
| Primary Source | USB /MyDrive Video | NA | NA | NA | NA | NA | NA | NA | NA | NA | NA |
| Tuner | Tuner | X | X | X | X | NA | NA | NA | NA | NA | NA |
Note:
When Source is USB /My Drive Video - static text to be shown -Refer HMI SRD.I
Other audio interrupts(Secondary Source) are not considered above.Ex: Navigation prompts, Alexa VR, VMS
- Variant: S220, S237, W502
- Stakeholder Requirement State: In Review
- System Requirement State: Draft
- Software Requirement State: Draft
- Primary Discipline: SW
- Requirement Type: TBD

### MS22029826-35865: Navigation (Heading)
- Variant: S220, S237, W502
- Stakeholder Requirement State: In Review
- System Requirement State: Draft
- Software Requirement State: Draft
- Primary Discipline: TBD
- Requirement Type: TBD

#### MS22029826-43667: Module Configuration (Heading)
- Variant: S220, S237, W502
- Stakeholder Requirement State: In Review
- System Requirement State: Draft
- Software Requirement State: Draft
- Primary Discipline: TBD
- Requirement Type: TBD

##### MS22029826-53599: VAR_CODING_INFOTAINMENT_SYSTEM =1 only then NAV feature shall be available (System Requirement)
- Variant: S220, S237, W502
- Verification Method: TBD
- Stakeholder Requirement State: In Review
- System Requirement State: Draft
- Secondary Disciplines: TBD
- Software Requirement State: Draft
- Primary Discipline: SW
- Requirement Type: TBD

##### MS22029826-53600: FEATURE_CODE_NAV_AA- (System Requirement)
FEATURE_CODE_NAV_AA- If this feature code value=1 Android Auto maps are enabled. If value=0 Android Auto maps are disabled
FEATURE_CODE_NAV_CP -If this feature code value=1 Car Play maps are enabled. If value=0 Car Play maps are disabled
FEATURE_CODE_NAV_NATIVE - If this feature code value=1 Native maps are enabled. If value=0 Native maps are disabled
Note: This configuration should be considered for displaying the Navigation data in the Navigation menu page.
- Variant: S220, S237, W502
- Stakeholder Requirement State: In Review
- System Requirement State: Draft
- Software Requirement State: Draft
- Primary Discipline: SW
- Requirement Type: TBD

##### MS22029826-53601: Data Received from IVI: (System Requirement)
Data Received from IVI:
1. Route Set (STS_NAV_ROUTE -
0x0-No Active Route (Default)
0x1-Native NAV Route set
0x2-Android Auto NAV Route set
0x3-Carplay NAV Route set
2. 'MapContext' : Value -( Native, CP, AA, Invalid)
3.Re Routing Value-(0x0 -No rerouting ,0x1- Rerouting)
- Variant: S220, S237, W502
- Stakeholder Requirement State: In Review
- System Requirement State: Draft
- Software Requirement State: Draft
- Primary Discipline: SW
- Requirement Type: Functional

##### MS22029826-72789: State chart (Stakeholder Requirement)
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- Variant: S220, S237, W502
- Stakeholder Requirement State: In Review
- System Requirement State: Draft
- Software Requirement State: Draft
- Primary Discipline: TBD
- Requirement Type: TBD

##### MS22029826-53603: When AAP,CP & Native are disabled - Remove Nav Info page (System Requirement)
· When AAP,CP & Native are disabled - Remove Nav Info page
· When only AAP Nav is enabled and when No route set - Show Set Route screen
· When atleast 1 Nav is enabled, Route is set but corresponding Nav is disabled - Show Error screen
· When atleast 1 Nav is enabled, Route is not set, 'MapContext'corresponding Nav is disabled - Show Error screen
· When route is set and corresponding Nav is enabled - Display MAP screen with TBT in title for Native/CP/AA. Display TBT alone for AAP
· When route is not set and corresponding Nav is enabled - Display 'MapContext' without TBT info (This is applicable only for Native Nav -Default map)
· When atleast 1 Nav is enabled, When route is not set and 'MapContext' is Not Set / Timeout - Show Set Route Screen (This is applicable only for CP and AA)
· For First battery Connect/First IGN Cycle - When route is not set and corresponding Nav is enabled -Show Set Route Screen until route is set for Native/AA/CP
· IC will request map mode to IVI when user enter into Nav menu and will retry until source connect
· IC need to know connected source from IVI before requesting map mode as Map area changes based on source.
- Variant: S220, S237, W502
- Stakeholder Requirement State: In Review
- System Requirement State: Draft
- Software Requirement State: Draft
- Primary Discipline: SW
- Requirement Type: Functional

#### MS22029826-35867: Full Map View Display (Heading)
- Variant: S220, S237, W502
- Stakeholder Requirement State: In Review
- System Requirement State: Draft
- Software Requirement State: Draft
- Primary Discipline: TBD
- Requirement Type: TBD

##### MS22029826-43669 (System Requirement)
In partial map view - On Long Press of OK Switch Press (Full Screen Request by switch), Request Full Map Aspect Ratio and Display Full Map:
| Previous HMI Interface | Full Screen Request by Switch | Request Map Aspect ratio | Display Map Aspect Ratio | HMI Interface |
| --- | --- | --- | --- | --- |
| City_partial \|\| sport_partial \|\| Minimal_partial | Yes | Full Map Aspect Ratio - (1920*720) | 1920*720 | Full_Map_View |
| Dynamic_partial \|\| Info_partial | Yes | Full Map Aspect Ratio - (1920*720) | 1920*720 | Full_Map_View |
- Variant: S220, S237, W502
- Stakeholder Requirement State: In Review
- System Requirement State: Draft
- Software Requirement State: Draft
- Primary Discipline: SW
- Requirement Type: TBD

#### MS22029826-35868: Partial/ Full View Map: (Heading)
- Variant: S220, S237, W502
- Stakeholder Requirement State: In Review
- System Requirement State: Draft
- Software Requirement State: Draft
- Primary Discipline: TBD
- Requirement Type: TBD

##### MS22029826-43671: Two Aspect ratio of map shall be requested by cluster (Partial Map and Full Map View) (System Requirement)
- Variant: S220, S237, W502
- Stakeholder Requirement State: In Review
- System Requirement State: Draft
- Software Requirement State: Draft
- Primary Discipline: SW
- Requirement Type: TBD

##### MS22029826-43673: navigation_display (System Requirement)
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- Variant: S220, S237, W502
- Stakeholder Requirement State: In Review
- System Requirement State: Draft
- Software Requirement State: Draft
- Primary Discipline: SW
- Requirement Type: TBD

##### MS22029826-43675 (System Requirement)
Description for the Terms used in Flow chart:
Navigation Menu Exit: Menu Button Press in Full Map/Partial Map
Partial Screen requested by Switch: OK Long Press
Full Screen requested by Switch: OK Long Press
- Variant: S220, S237, W502
- Stakeholder Requirement State: In Review
- System Requirement State: Draft
- Software Requirement State: Draft
- Primary Discipline: SW
- Requirement Type: TBD

##### MS22029826-43677 (System Requirement)
Only One Resolution of map is requested by cluster (Partial Map View)
IC need to know connected source from IVI before requesting map mode as Map area changes based on source.
- Variant: S220, S237, W502
- Stakeholder Requirement State: In Review
- System Requirement State: Draft
- Software Requirement State: Draft
- Primary Discipline: SW
- Requirement Type: TBD

##### MS22029826-43679: Partial Map View Display (Heading)
0-1.0-7.0-3.1. Partial Map View Display
- Variant: S220, S237, W502
- Stakeholder Requirement State: In Review
- System Requirement State: Draft
- Software Requirement State: Draft
- Primary Discipline: TBD
- Requirement Type: TBD

###### MS22029826-53605 (System Requirement)
IVI to IC: Route set: 0x00 - No Route, 0x01- Native, 0x02- AA, 0x03 - CP
IC to IVI: Request Map Resolution: 0x00- No Request, 0x01 - Partial Map request, 0x02 - Full Map request, 0x03 - Reserved
Based on the Route Set data received from IVI, request for Map Resolution with Size is sent from IC to IVI based on modes.
| Route Set: | Mode | Request Map Resolution | HMI Interface |
| --- | --- | --- | --- |
| AA route set: | - | No Request | - |
| No Route set \|\| Native Route Set \|\| CP Route Set | City | Partial Map Resolution 1- (800*480) | City_partial |
| No Route set \|\| Native Route Set \|\| CP Route Set | Sport | Partial Map Resolution 1- (800*480) | Sport_partial |
| No Route set \|\| Native Route Set \|\| CP Route Set | Minimal | Partial Map Resolution 1- (800*480) | Minimal_partial |
| No Route set \|\| Native Route Set \|\| CP Route Set | Dynamic | Partial Map Resolution 2- (1280*480) | Dynamic_partial |
| No Route set \|\| Native Route Set \|\| CP Route Set | Info | Full Map Resolution - (1920*512) | Info_partial |
- Variant: S220, S237, W502
- Stakeholder Requirement State: In Review
- System Requirement State: Draft
- Software Requirement State: Draft
- Primary Discipline: SW
- Requirement Type: TBD

###### MS22029826-53606: In full map view display - On Long Press of OK Switch (Partial Screen Request by switch), Request for Partial Map / Full Map aspect ratio and display Partial Map based on the table in ReqId:2895248 (System Requirement)
- Variant: S220, S237, W502
- Stakeholder Requirement State: In Review
- System Requirement State: Draft
- Software Requirement State: Draft
- Primary Discipline: SW
- Requirement Type: TBD

###### MS22029826-53608 (System Requirement)
IVI to IC: Route set: 0x00 - No Route, 0x01- Native, 0x02- AA, 0x03 - CP
Based on the Route Set data received from IVI, request for Map type is sent from IC to IVI: 0x00- No Request, 0x01 - Partial Map request, 0x02 - Full Map request, 0x03 - Reserved
| Route Set: | Request Map Aspect Ratio | Display Map Aspect Ratio | HMI Interface |
| --- | --- | --- | --- |
| AA route set: | No Request | - | - |
| No Route set \|\| Native Route Set \|\| CP Route set | Partial Map View - (640*240) | 640 x240 | Map_view |
- Variant: S220, S237, W502
- Stakeholder Requirement State: In Review
- System Requirement State: Draft
- Software Requirement State: Draft
- Primary Discipline: SW
- Requirement Type: TBD

###### MS22029826-53610: There will be a delay in the update of Map data rendered in display (Tolerance shall be finalized during development) (System Requirement)
- Variant: S220, S237, W502
- Stakeholder Requirement State: In Review
- System Requirement State: Draft
- Software Requirement State: Draft
- Primary Discipline: SW
- Requirement Type: TBD

### MS22029826-35870: Cluster AFE Reset (Heading)
- Variant: S220, W502
- Stakeholder Requirement State: In Review
- System Requirement State: Draft
- Software Requirement State: Draft
- Primary Discipline: TBD
- Requirement Type: TBD

#### MS22029826-43681: Description (System Requirement)
| Description | Value |
| --- | --- |
| RESET_AFE | 0-No Reset, 1-Reset |
- Variant: S220, W502
- Stakeholder Requirement State: In Review
- System Requirement State: Draft
- Software Requirement State: Draft
- Primary Discipline: SW
- Requirement Type: TBD

### MS22029826-35871: Green Drive AFE Reset triggered from IS (Heading)
- Variant: S220, W502
- Stakeholder Requirement State: In Review
- System Requirement State: Draft
- Software Requirement State: Draft
- Primary Discipline: TBD
- Requirement Type: TBD

#### MS22029826-43683: Description (System Requirement)
| Description | Value |
| --- | --- |
| REQ_TRIP_RESET | 0-No Reset, 1-Reset |
- Variant: S220, W502
- Stakeholder Requirement State: In Review
- System Requirement State: Draft
- Software Requirement State: Draft
- Primary Discipline: SW
- Requirement Type: TBD

### MS22029826-35872: Illumination Setting (Heading)
- Variant: S220, S237, W502
- Stakeholder Requirement State: In Review
- System Requirement State: Draft
- Software Requirement State: Draft
- Primary Discipline: TBD
- Requirement Type: TBD

#### MS22029826-43685: Description (System Requirement)
| Description | Value |
| --- | --- |
| ILLUMINATION_LEVEL | 0-Default, 1~8: Valid, 9~0xE-Reserved, 0xF- Invalid |
- Variant: S220, S237, W502
- Stakeholder Requirement State: In Review
- System Requirement State: Draft
- Software Requirement State: Draft
- Primary Discipline: SW
- Requirement Type: TBD

### MS22029826-35874: Clock (Heading)
- Variant: S220, S237, W502
- Stakeholder Requirement State: In Review
- System Requirement State: Draft
- Software Requirement State: Draft
- Primary Discipline: TBD
- Requirement Type: TBD

#### MS22029826-43687: Signal name (System Requirement)
| Signal name | Factor | Value Description |
| --- | --- | --- |
| CLOCK_HOUR | 1 | 0~23: Hour value |
| CLOCK_MIN | 1 | 0~59: Minute value |
| CLOCK_FORMAT | 1 | 0x0 – 12h mode / Default 0x1 – 24h mode |
- Variant: S220, S237, W502
- Stakeholder Requirement State: In Review
- System Requirement State: Draft
- Software Requirement State: Draft
- Primary Discipline: SW
- Requirement Type: TBD

### MS22029826-35876: Calendar (Heading)
- Variant: S220, S237, W502
- Stakeholder Requirement State: In Review
- System Requirement State: Draft
- Software Requirement State: Draft
- Primary Discipline: TBD
- Requirement Type: TBD

#### MS22029826-43689: Signal name (System Requirement)
| Signal name | Factor | Value Description |
| --- | --- | --- |
| CLOCK_DATE | 1 | 0~31: Date value |
| CLOCK_MONTH | 1 | 1~12: Month Value |
| CLOCK_YEAR | 1 | 2019 – 2063:Year Value |
- Variant: S220, S237, W502
- Stakeholder Requirement State: In Review
- System Requirement State: Draft
- Software Requirement State: Draft
- Primary Discipline: SW
- Requirement Type: TBD

### MS22029826-35877: Ecoscore (Heading)
- Variant: S220, W502
- Stakeholder Requirement State: In Review
- System Requirement State: Draft
- Software Requirement State: Draft
- Primary Discipline: TBD
- Requirement Type: TBD

#### MS22029826-43691: Description (System Requirement)
| Description | Value |
| --- | --- |
| ECO INDEX | 0x64-Default , 0x7F-Signal Invalid |
| INST_ECO INDEX | 0x64-Default , 0x7F-Signal Invalid |
- Variant: S220, W502
- Stakeholder Requirement State: In Review
- System Requirement State: Draft
- Software Requirement State: Draft
- Primary Discipline: SW
- Requirement Type: TBD

### MS22029826-35879: Unit (Heading)
- Variant: S220, S237, W502
- Stakeholder Requirement State: In Review
- System Requirement State: Draft
- Software Requirement State: Draft
- Primary Discipline: TBD
- Requirement Type: TBD

#### MS22029826-43693: Feature (System Requirement)
| Feature | UK setting | US setting | Spec used |
| --- | --- | --- | --- |
| Temperature | Deg C | Deg F | OAT (Display feature), TPMS |
| Pressure | kPa | Psi | TPMS (Display feature) |
- Variant: S220, S237, W502
- Stakeholder Requirement State: In Review
- System Requirement State: Draft
- Software Requirement State: Draft
- Primary Discipline: SW
- Requirement Type: TBD

### MS22029826-35881: DriveMode (Heading)
- Variant: S220, W502
- Stakeholder Requirement State: In Review
- System Requirement State: Draft
- Software Requirement State: Draft
- Primary Discipline: TBD
- Requirement Type: TBD

#### MS22029826-43695: Values sent from IC to IVI (Heading)
- Variant: S220, W502
- Stakeholder Requirement State: In Review
- System Requirement State: Draft
- Software Requirement State: Draft
- Primary Discipline: TBD
- Requirement Type: TBD

##### MS22029826-53612: Drive mode received from EMS (System Requirement)
Drive mode received from EMS
payload[0] : ENGINE_DRIVE_MODE (Value: 0-Mode1, 1- Mode2, 2- Mode3, 3- Mode4, 4- Mode5,5- Mode6, 6- Mode7, 7-Invalid)
Drive mode status from EMS
Payload[1] : STS_EMS_DRV_ADV_MODE (Value: 0-Not Active, 1-Active, 2- In Progress, 3-Ready to Enter)
Custom Mode status from EMS
Payload[3] : DRV_MODE_CUSTOM(Value:0x0-Custom Mode Off, 0x1-Custom Mode On)
Note: IC gateway the CAN messages
- Variant: S220, W502
- Stakeholder Requirement State: In Review
- System Requirement State: Draft
- Software Requirement State: Draft
- Primary Discipline: SW
- Requirement Type: TBD

##### MS22029826-53614: Drive Mode Alert to be displayed in IVI (System Requirement)
Drive Mode Alert to be displayed in IVI
Drive mode inhibit status from EMS
Payload[2] : EMS_DRIVE_ALERT (Value: 0-No Alert, 1-Drive Mode Not Possible, 2~3-Reserved)
- Variant: S220, W502
- Stakeholder Requirement State: In Review
- System Requirement State: Draft
- Software Requirement State: Draft
- Primary Discipline: SW
- Requirement Type: TBD

#### MS22029826-43698: Values received from IVI to IC (Heading)
- Variant: S220, W502
- Stakeholder Requirement State: In Review
- System Requirement State: Draft
- Software Requirement State: Draft
- Primary Discipline: TBD
- Requirement Type: TBD

##### MS22029826-53616 (System Requirement)
Drive_Menu_Sel (Mode1, Mode 2, Mode 3, Mode4, Mode 5) - Received from IVI -W502
Drive_Menu_Sel (Mode1, Mode 2, Mode 3) - Received from IVI -S220
- Variant: S220, W502
- Stakeholder Requirement State: In Review
- System Requirement State: Draft
- Software Requirement State: Draft
- Primary Discipline: SW
- Requirement Type: TBD

### MS22029826-35883: Turn By Turn (Heading)
- Variant: S220, S237, W502
- Stakeholder Requirement State: In Review
- System Requirement State: Draft
- Software Requirement State: Draft
- Primary Discipline: TBD
- Requirement Type: TBD

#### MS22029826-43699: Refer Alert Section for the Requirement .Artifact ID:44121 (System Requirement)
Refer Alert Section for the Requirement .Artifact ID: 44121
- Variant: S220, S237, W502
- Verification Method: TBD
- Stakeholder Requirement State: In Review
- System Requirement State: Draft
- Secondary Disciplines: TBD
- Software Requirement State: Draft
- Primary Discipline: SW
- Requirement Type: TBD

### MS22029826-35885: MAMS Setting (System Requirement)
- Variant: S220, S237, W502
- Stakeholder Requirement State: In Review
- System Requirement State: Draft
- Software Requirement State: Draft
- Primary Discipline: SW
- Requirement Type: Functional

#### MS22029826-43701 (System Requirement)
Refer Setting MAMS Setting , Artifact ID : 35659
When there is user request to change the setting in HMI ( Enabled ->Disabled OR Disabled ->Enabled) MAMS_STS_IVI 0x1 shall sent to IVI for 1 frame .
After that 0x0 Shall be sent by default.
- Variant: S220, S237, W502
- Stakeholder Requirement State: In Review
- System Requirement State: Draft
- Software Requirement State: Draft
- Primary Discipline: SW
- Requirement Type: Functional

#### MS22029826-44214 (System Requirement)
Based on the information sent by IC, IVI Shall share the ON change value to the APA module
Refer 45612 (23710 DNG Requirements)
- Variant: S220, S237, W502
- Stakeholder Requirement State: In Review
- System Requirement State: Draft
- Software Requirement State: Draft
- Primary Discipline: SW
- Requirement Type: Functional

### MS22029826-35886: Language Selection/Multi-Lingual Support (Heading)
- Variant: S220, S237, W502
- Stakeholder Requirement State: In Review
- System Requirement State: Draft
- Software Requirement State: Draft
- Primary Discipline: TBD
- Requirement Type: TBD

#### MS22029826-44215 (System Requirement)
The system shall support multi-lingual texts.
The system shall provide the user an option to choose the Display Language in the Infotainment and the change in language shall reflect in both cluster and infotainment.
- Variant: S220, S237, W502
- Stakeholder Requirement State: In Review
- System Requirement State: Draft
- Software Requirement State: Draft
- Primary Discipline: SW
- Requirement Type: TBD

#### MS22029826-44217: The language selection shall be retained on Battery reconnect. (System Requirement)
- Variant: S220, S237, W502
- Stakeholder Requirement State: In Review
- System Requirement State: Draft
- Software Requirement State: Draft
- Primary Discipline: SW
- Requirement Type: TBD

#### MS22029826-44219 (System Requirement)
The following languages shall be supported by the system:
- English
- Spanish
- Chile Spanish
- Portuguese
- Arabic
- Italian (protected)
- Reserved (protected)
- Variant: S220, S237, W502
- Stakeholder Requirement State: In Review
- System Requirement State: Draft
- Software Requirement State: Draft
- Primary Discipline: SW
- Requirement Type: TBD

#### MS22029826-44221: The translations for English strings for each language shall be provided in a separate table and the system shall display the corresponding translation from the same based on current language selection (System Requirement)
- Variant: S220, S237, W502
- Stakeholder Requirement State: In Review
- System Requirement State: Draft
- Software Requirement State: Draft
- Primary Discipline: SW
- Requirement Type: TBD

#### MS22029826-44223 (System Requirement)
The default language shall be selected based on the target market of the vehicle based on the below table.
| Region | Language |
| --- | --- |
| India | English |
| Sri Lanka | English |
| Nepal | English |
| Bhutan | English |
| Bangladesh | English |
| Thailand | English |
| Malaysia | English |
| Indonesia | English |
| Philippines | English |
| Vietnam | English |
| Australia | English |
| New Zealand | English |
| Bolivia | Chile Spanish |
| Columbia | Chile Spanish |
| Ecuador | Chile Spanish |
| Porta Rico | Chile Spanish |
| Chile | Chile Spanish |
| Peru | Chile Spanish |
| Saudi Arabia | Arabic |
| Kuwait | Arabic |
| Qatar | Arabic |
| UAE | Arabic |
| South Africa | English |
| Algeria | Arabic |
| Egypt | Arabic |
| Mozambique | Portuguese |
| Kenya | English |
| Uganda | English |
| Morocco | Arabic |
- Variant: S220, S237, W502
- Stakeholder Requirement State: In Review
- System Requirement State: Draft
- Software Requirement State: Draft
- Primary Discipline: SW
- Requirement Type: TBD

## MS22029826-35888: IC to IVI Communication (Heading)
- Variant: S220, W502
- Stakeholder Requirement State: In Review
- System Requirement State: Draft
- Software Requirement State: Draft
- Primary Discipline: TBD
- Requirement Type: TBD

### MS22029826-44225: Refer IVI SRD (System Requirement)
- Variant: S220, W502
- Stakeholder Requirement State: In Review
- System Requirement State: Draft
- Software Requirement State: Draft
- Primary Discipline: SW
- Requirement Type: TBD

### MS22029826-44227: FEATURE_CODE_FUEL_TYPE (0-Gasoline, 1- Diesel) -Cluster to share fuel feature code to IVI (System Requirement)
- Variant: S220, W502
- Stakeholder Requirement State: In Review
- System Requirement State: Draft
- Software Requirement State: Draft
- Primary Discipline: SW
- Requirement Type: TBD

### MS22029826-35891: Power Torque (Information)
- Variant: S220, W502
- Stakeholder Requirement State: In Review
- System Requirement State: Draft
- Software Requirement State: Draft
- Primary Discipline: TBD
- Requirement Type: TBD

#### MS22029826-44242: Cluster shall share % POWER and %TORQUE information to IVI for display in Adventure statistics (System Requirement)
- Variant: S220, W502
- Stakeholder Requirement State: In Review
- System Requirement State: Draft
- Software Requirement State: Draft
- Primary Discipline: SW
- Requirement Type: Functional

### MS22029826-35893: Digital Speed (System Requirement)
- Variant: S220, W502
- Stakeholder Requirement State: In Review
- System Requirement State: Draft
- Software Requirement State: Draft
- Primary Discipline: SW
- Requirement Type: Functional

#### MS22029826-44244: Cluster shall share HmiDigiSpd - for Digital Speed Display to IVI for display in Adventure statistics (System Requirement)
- Variant: S220, W502
- Stakeholder Requirement State: In Review
- System Requirement State: Draft
- Software Requirement State: Draft
- Primary Discipline: SW
- Requirement Type: Functional

### MS22029826-35890: Trip Information (Heading)
- Variant: S220, W502
- Stakeholder Requirement State: In Review
- System Requirement State: Draft
- Software Requirement State: Draft
- Primary Discipline: TBD
- Requirement Type: TBD

#### MS22029826-44229 (Information)
Cluster shall share TRIP -A [ Distance, Drive Time, Average Speed] info to IVI for display in Adventure statistics
Cluster shall share TRIP -B [ Distance, Drive Time, Average Speed] info to IVI for display in Adventure statistics
Cluster shall share the TRIP_PAGE_INFO to IVI
TRIP_INFO_PAGE = Values 0- Trip A, 1-Trip B.
TRIP_INFO_PAGE shall be set to Trip A if the current display menu in IC is TRIP A.
TRIP_INFO_PAGE shall be set to Trip B if the current display menu in IC is TRIP B.
To avoid unintended browse between Trip A/B,TRIP_INFO_PAGE value shall be updated only
if TRIPA/B is current screen for display for >=2sec
- Variant: S220, W502
- Stakeholder Requirement State: In Review
- System Requirement State: Draft
- Software Requirement State: Draft
- Primary Discipline: TBD
- Requirement Type: TBD

### MS22029826-35898: Engine Temparature (Information)
- Variant: S220, W502
- Stakeholder Requirement State: In Review
- System Requirement State: Draft
- Software Requirement State: Draft
- Primary Discipline: TBD
- Requirement Type: TBD

#### MS22029826-44251 (System Requirement)
Cluster shall share Engine Temparature information to IVI [ECT Gauge Disp %]
Cluster shall share the RED and Blink state to IVI
- Variant: S220, W502
- Stakeholder Requirement State: In Review
- System Requirement State: Draft
- Software Requirement State: Draft
- Primary Discipline: SW
- Requirement Type: Functional

### MS22029826-35900: Roll & Pitch (Heading)
- Variant: S220, W502
- Stakeholder Requirement State: In Review
- System Requirement State: Draft
- Software Requirement State: Draft
- Primary Discipline: SW
- Requirement Type: Functional

#### MS22029826-44253 (System Requirement)
Cluster shall share Roll & Pitch Angle information to IVI for display in Adventure statistics
Cluster shall share Roll &Pitch Alert information to IVI for display in Adventure statistics
- Variant: S220, W502
- Stakeholder Requirement State: In Review
- System Requirement State: Draft
- Software Requirement State: Draft
- Primary Discipline: SW
- Requirement Type: Functional

### MS22029826-35895: Tachometer (Information)
- Variant: S220, W502
- Stakeholder Requirement State: In Review
- System Requirement State: Draft
- Software Requirement State: Draft
- Primary Discipline: TBD
- Requirement Type: TBD

#### MS22029826-44247 (System Requirement)
Cluster shall share Tachometer - RPM value to IVI
FEATURE_CODE_FUEL_TYPE =0 (W502 GSL)
Upper Limit red band -7000rpm
Lower Limit red band- 5500 rpm
FEATURE_CODE_FUEL_TYPE =1 (W502 DSL)
Upper Limit red band -7000rpm
- Variant: S220, W502
- Stakeholder Requirement State: In Review
- System Requirement State: Draft
- Software Requirement State: Draft
- Primary Discipline: SW
- Requirement Type: Functional

### MS22029826-35897: Odometer (System Requirement)
- Variant: S220, W502
- Stakeholder Requirement State: In Review
- System Requirement State: Draft
- Software Requirement State: Draft
- Primary Discipline: SW
- Requirement Type: Functional

#### MS22029826-44249: Cluster shall share odometer value to IVI for display in Adventure statistics (System Requirement)
- Variant: S220, W502
- Stakeholder Requirement State: In Review
- System Requirement State: Draft
- Software Requirement State: Draft
- Primary Discipline: SW
- Requirement Type: Functional

### MS22029826-53621: Gear Indicator (System Requirement)
- Variant: S220, W502
- Stakeholder Requirement State: In Review
- System Requirement State: Draft
- Software Requirement State: Draft
- Primary Discipline: SW
- Requirement Type: TBD

#### MS22029826-53618 (System Requirement)
Cluster shall share below
Gear St (Major Gear St, Minor Gear St)
Gear shift indication (Shift Up St, Shift Down St) to IVI for Adventure statistics
- Variant: S220, W502
- Stakeholder Requirement State: In Review
- System Requirement State: Draft
- Software Requirement State: Draft
- Primary Discipline: SW
- Requirement Type: TBD

### MS22029826-53622: Fuel Percentage (System Requirement)
- Variant: S220, W502
- Stakeholder Requirement State: In Review
- System Requirement State: Draft
- Software Requirement State: Draft
- Primary Discipline: SW
- Requirement Type: TBD

#### MS22029826-53619: Cluster shall share Fuel Percentage info to IVI for AA MD. (System Requirement)
- Variant: S220, W502
- Stakeholder Requirement State: In Review
- System Requirement State: Draft
- Software Requirement State: Draft
- Primary Discipline: SW
- Requirement Type: TBD

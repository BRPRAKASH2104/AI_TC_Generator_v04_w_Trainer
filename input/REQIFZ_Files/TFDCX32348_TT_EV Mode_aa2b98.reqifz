# Json2ReqIF Transformation

# Specification: TT_EV Mode
- JDA Snapshot Date: 2025-10-29 07:16:26

## TFDCX32348-9815: TT_EV Mode (Heading)

## TFDCX32348-9818: History (Heading)

### TFDCX32348-14044: Version Date Name Description of chan... (Information)
| Version | Date | Name | Description of change | SRD Baseline |
| --- | --- | --- | --- | --- |
| 1.0 | 03/Nov/2022 | ttakaba | [SYS][38xD][RTT] EV Mode (1777258) First release. | BL_20221104_02 |
| 1.1 | 06/Mar/2025 | Syuta Matsuoka | Applicable to 12.3 FDC Change PTSysTypeFlag Value [SYS-Task] TFDCX32348-72795: [SYS][12.3FDC][APP][Telltale] Hybrid system (EV mode) | BL_20250328_01 |

## TFDCX32348-9819: Overview (Heading)

### TFDCX32348-73209: This SRD defines Telltale for Hybrid system(EV mode). (Information)

## TFDCX32348-73206: Reference Document (Heading)

### TFDCX32348-73207: MET-H_EVMOD-CSTD-A0-01-A-C0.xlsm (Information)
MET-H_EVMOD-CSTD-A0-01-A-C0.xlsm
DMS_MET-H_EVMOD-CSTD-A0-01-A-C0.xlsx

## TFDCX32348-9821: Input Requirements (Heading)

### TFDCX32348-14046: InternalSignal - IgnMode (System Interface)

### TFDCX32348-14048: CANSignal - EVM_MSG (Message Label: ... (System Interface)
CANSignal - EVM_MSG (Message Label: EHV1F04)

### TFDCX32348-14050: InternalSignal - PTSysTypeFlag (System Interface)

## TFDCX32348-9823: Output Requirements (Heading)

### TFDCX32348-14052: HMI - EVModeTelltale (System Interface)
HMI - EVModeTelltale
Meaning: This parameter indicates the display status of EV mode telltale.
Range: OFF, ON, BLINK1, BLINK2, BLINK3, BLINK4

## TFDCX32348-9825: Performance Requirements (Heading)

### TFDCX32348-14054: Display Symbol (Heading)

#### TFDCX32348-17687: 1. Symbol (Information)
1. Symbol
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2. Color: Green

### TFDCX32348-14056: Bulb Check (Heading)

#### TFDCX32348-17688: None (System Requirement)
- Verification Criteria: Verify by code review
- Verification Method: System Qualification Test, Unit Test
- Verification Owner: SW
- System Requirement State: Approved
- Primary Discipline: SW
- ASIL Rating: QM

### TFDCX32348-14057: Initial Process (Heading)

#### TFDCX32348-17690: When IgnMode turns OFF -> ON, the tel... (System Requirement)
When IgnMode turns OFF -> ON, the telltale shall not turn ON until the triggering signal is received.
- Verification Criteria: Verify by code review
- Verification Owner: SW
- System Requirement State: Approved
- Primary Discipline: SW
- ASIL Rating: QM

### TFDCX32348-14059: Telltale Control (Heading)

#### TFDCX32348-17692: # Input Output Remar... (System Requirement)
| # | Input |  |  |  | Output | Remarks |
| --- | --- | --- | --- | --- | --- | --- |
| # | Internal Signal - PTSysTypeFlag | Internal Signal - IgnMode | CAN Signal Status - EVM_MSG | CAN Signal - EVM_MSG | HMI - HMI_EVModeTelltale | Remarks |
| 1 | Other than 0011b 0001b or 0010b (CONV) | x | x | x | OFF |  |
| 2 | 0011b Other than (0001b or 0010b) (HEV) | OFF | X | X | OFF |  |
| 3 | 0011b Other than (0001b or 0010b) (HEV) | ON | Communication starting Never Received: 1 Communication Failure: 0 | X | OFF |  |
| 4 | 0011b Other than (0001b or 0010b) (HEV) | ON | Communication establishment Never Received: 0 Communication Failure: 0 | 0000b | OFF | TT turns OFF immeidiately |
| 5 | 0011b Other than (0001b or 0010b) (HEV) | ON | Communication establishment Never Received: 0 Communication Failure: 0 | 1011b | ON | TT turns ON immediately |
| 6 | 0011b Other than (0001b or 0010b) (HEV) | ON | Communication establishment Never Received: 0 Communication Failure: 0 | (Other than 0111b) to 0111b | BLINK1 | Start 3 times blinking. Refer to TFDCX32348-17694 |
| 7 | 0011b Other than (0001b or 0010b) (HEV) | ON | Communication establishment Never Received: 0 Communication Failure: 0 | (Other than 1000b) to 1000b | BLINK2 | Start 3 times blinking. Refer to TFDCX32348-17694 |
| 8 | 0011b Other than (0001b or 0010b) (HEV) | ON | Communication establishment Never Received: 0 Communication Failure: 0 | (Other than 1001b) to 1001b | BLINK3 | Start 3 times blinking. Refer to TFDCX32348-17694 |
| 9 | 0011b Other than (0001b or 0010b) (HEV) | ON | Communication establishment Never Received: 0 Communication Failure: 0 | (Other than 1010b) to 1010b | BLINK4 | Start 3 times blinking. Refer to TFDCX32348-17694 |
| 10 | 0011b Other than (0001b or 0010b) (HEV) | ON | Communication establishment Never Received: 0 Communication Failure: 0 | Other than above | OFF |  |
| 11 | 0011b Other than (0001b or 0010b) (HEV) | ON | Communication abnormality Never Received: x Communication Failure: 1 | x | No change | Maintain last status |
- Verification Criteria: Verify by executing test cases
- Verification Owner: FV
- System Requirement State: Approved
- Primary Discipline: SW
- ASIL Rating: QM

### TFDCX32348-14061: Telltale Blinking Control (Heading)

#### TFDCX32348-17694: Overview (System Requirement)
(1) Immediately turn OFF the indicator if HMI_EVModeTelltale becoms OFF even if the indicator is blinking.
(2) Immediately turn ON the indicator if HMI_EVModeTelltale becoms ON even if the indicator is blinking.
(3) In blinking mode, the indicator shall turn OFF after 3 times blinking. (Common for BLINK1, BLINK2, BLINK3, and BLINK4)
(4) Blink period is 1 seconds and the duty is 50%. (Common for BLINK1, BLINK2, BLINK3, and BLINK4)
(5) A blinking cycle starts with OFF state. (Common for BLINK1, BLINK2, BLINK3, and BLINK4)
(6) If the blinking trigger cause is changed (for example from BLINK1 to BLINK2), restart blinking control cycle immediately.
- Verification Criteria: Verify by executing test cases
- Verification Owner: FV
- System Requirement State: Approved
- Primary Discipline: SW
- ASIL Rating: QM

#### TFDCX32348-17695: Expected behaviour (Information)
Expected behavior
Unsupported JIRA markdown detected: taskList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

# Json2ReqIF Transformation

# Specification: TT_LTA (Lane Tracing Assist)
- JDA Snapshot Date: 2025-10-29 07:17:30

## TFDCX32348-9881: TT_LTA (Lane Tracing Assist) (Heading)

## TFDCX32348-9883: History (Heading)

### TFDCX32348-13868: Version Date Name Description of chan... (Information)
| Version | Date | Name | Description of change | Baseline |
| --- | --- | --- | --- | --- |
| 0.1 | 14/July/2022 | UMEMOTO, Soma | Newly create SYS-Task 1685298: [SYS][38xD][RTT] LTA TT (#211,#213,#215,#264) | BL_20220728_03 |
| 0.2 | 17/October/2022 | UMEMOTO, Soma | Enhancement SYS-TASK: 1777257: [SYS][38xD][Enhancement][RTT] Lane Tracing Assist warning Removed fn_reset_LTA_existence() Update State Transition Diagram( T38XD29284-46371) Reset condition for NVM_LTA_Existence() is replaced. |  |
| 0.3 | 7/March/2023 | Hayashi, Keiichi | [SYS-Task] 1945278: [SYS][38xD][Defect][APP] Exist flag judgement Function presence Update | BL_20230315_08 |
| 0.4 | 23/Oct/2024 | Syuta Matsuoka | [SYS-Task] TFDCX32348-26153: [SYS][12.3FDC][APP][Telltale] LTA (Lane Tracing Assist) Dropped Drec_Telltale and advancedDrive_Telltale | BL_20240830_01 |
| 0.5 | 13/Feb/2025 | Syuta Matsuoka | Set performance requirements ”Legal” [SYS-Task] TFDCX32348-64404: [SYS][12.3FDC][R4][APP][Telltale] LTA (Lane tracing assist) | BL_20250220_01 |

## TFDCX32348-10753: Reference Document (Heading)

### TFDCX32348-13870: MET-S_LTA-CSTD-2-02-A-C0.xlsm (Information)

### TFDCX32348-13871: (DMS(In))MET-S_LTA-CSTD-2-02-A-C0.xlsx (Information)

## TFDCX32348-10756: Overview (Heading)

### TFDCX32348-13873: This SRD defines Telltale of Lane Tra... (Information)
This SRD defines Telltale of Lane Tracing Assist (LTA) and Advanced Drive.

## TFDCX32348-10758: Input Requirements (Heading)

### TFDCX32348-13875: Internal Signal – IgnMode (System Interface)
- Verification Criteria: Verify by design review

### TFDCX32348-14267: CAN Signal – LTAINDI (Message Label: ... (System Interface)
CAN Signal – LTAINDI (Message Label: DS12F03)
- Verification Criteria: Verify by design review

### TFDCX32348-14269: CAN Signal – LTAEXIST (Message Label:... (System Interface)
CAN Signal – LTAEXIST (Message Label: DS12F03)
- Verification Criteria: Verify by design review

## TFDCX32348-10760: Output Requirements (Heading)

### TFDCX32348-14275: HMI – LTA_Telltale Meaning: This ind... (System Interface)
HMI – LTA_Telltale
Meaning: This indicates the status of LTA telltale.
Range: OFF, WHITE, GREEN, AMBER
Initial Value: OFF
- Verification Criteria: Verify by design review

## TFDCX32348-68491: NVM Requirements (Heading)
- System Requirement State: Draft
- Primary Discipline: TBD
- ASIL Rating: TBD

### TFDCX32348-14273: NVM – NVM_LTA_Exist_Flag Meaning: Th... (System Interface)
NVM – NVM_LTA_Exist_Flag
Meaning: This indicates whether LTA system is equipped or not.
Range: Unequipped, Equipped
Initial Value: Unequipped
- Verification Criteria: Verify by design review

## TFDCX32348-10762: Function Entry (Heading)

### TFDCX32348-14279: Function Entry - fn_reset_LTA_existen... (System Requirement)
Function Entry - fn_reset_LTA_existence()
This function shall be called when Diag command ($31 $11FF) is received.
- Verification Criteria: Verify by code review
- Verification Method: Unit Test
- Verification Owner: SW
- System Requirement State: Approved
- Primary Discipline: SW
- ASIL Rating: QM

## TFDCX32348-10764: Performance Requirements (Heading)

### TFDCX32348-14281: Display Symbol (Heading)

#### TFDCX32348-17747: LTA Symbol (Information)
(1) Display Symbol:
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(2) Color: WHITE, GREEN, AMBER

### TFDCX32348-14283: Bulb Check (Heading)

#### TFDCX32348-17749: None (System Requirement)
- ASIL Rating: QM

### TFDCX32348-14284: Initial Process (Heading)

#### TFDCX32348-17751: When the ON of the internal signal Ig... (System Requirement)
When the ON of the internal signal IgnMode is detected, the Telltales are initially turned OFF.
- Verification Criteria: Verify by executing test cases
- Verification Method: Software Qualification Test, System Qualification Test, Unit Test
- Verification Owner: FV, SW
- System Requirement State: Approved
- Primary Discipline: SW
- ASIL Rating: QM

### TFDCX32348-14286: Telltale Control (Heading)

#### TFDCX32348-17753: Logic Table – LTA_Telltale (Heading)

##### TFDCX32348-20645: Table- Logic Table – LTA_Telltale (System Requirement)
| No. | Input |  |  |  | Output | System Status |
| --- | --- | --- | --- | --- | --- | --- |
| No. | NVM - NVM_LTA_Exist_Flag | Internal Signal – IgnMode | CAN Signal Communication Status - LTAINDI | CAN Signal value - LTAINDI | HMI – LTA_Telltale | System Status |
| 1 | Unequipped | x | x | x | OFF |  |
| 2 | Equipped | OFF | x | x | OFF |  |
| 3 | Equipped | ON | Communication starting Never Received: 1 Communication Failure: 0 | x | OFF |  |
| 4 | Equipped | ON | Communication establishment Never Received: 0 Communication Failure: 0 | 000b | OFF | LTA OFF |
| 5 | Equipped | ON | Communication establishment Never Received: 0 Communication Failure: 0 | 001b | WHITE | LTA standby |
| 6 | Equipped | ON | Communication establishment Never Received: 0 Communication Failure: 0 | 010b | GREEN | LTA control |
| 7 | Equipped | ON | Communication establishment Never Received: 0 Communication Failure: 0 | 011b | GREEN | LTA control |
| 8 | Equipped | ON | Communication establishment Never Received: 0 Communication Failure: 0 | 100b | AMBER | LTA malfunction |
| 9 | Equipped | ON | Communication establishment Never Received: 0 Communication Failure: 0 | Other than above | OFF |  |
| 10 | Equipped | ON | Communication abnormality Never Received: x Communication Failure: 1 | x | AMBER |  |
Note:
Never Received and Communication Failure listed in CAN General SRD.
Please check the CAN General SRD for details.
- Verification Criteria: Verify by executing test cases
- Verification Method: Software Qualification Test, System Qualification Test, Unit Test
- Verification Owner: FV, SW
- System Requirement State: Approved
- Primary Discipline: SW
- ASIL Rating: QM

### TFDCX32348-14288: Determining the equipment of LTA system (Heading)

#### TFDCX32348-18314: The equipment of LTA system is determ... (System Requirement)
The equipment of LTA system is determined based on the following state transition diagram:
(Note)
(1) As soon as LTAEXIST = 1b is received 2 consecutive times within 2100ms,
set NVM_LTA_Exist_Flag = 'Equipped'.
(2) As soon as LTAEXIST = 0b is received 2 consecutive times within 210mms,
set NVM_LTA_Exist_Flag = 'Unequipped'.
| No. | Input |  |  | Output |
| --- | --- | --- | --- | --- |
| No. | InternalSignal – IgnMode | NVM – NVM_LTA_Exist_Flag | CAN Signal LTAEXIST | NVM – NVM_LTA_Exist_Flag |
| 1 | OFF | x | x | No Change |
| 2 | ON | 0 [Unequipped] | Received 2 consecutive signals 1b within 2100ms | 1 [Equipped] |
| 3 | ON | 1 [Equipped] | Received 2 consecutive signals other than 1b within 2100ms | 0 [Unequipped] |
| 4 | ON | Other than above |  | No Change |
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Reset Table
| Function Entry | NVM_LTA_Exist_Flag |
| --- | --- |
| fn_reset_LTA_existence() | 0 [Unequipped] |
- Verification Criteria: Verify by executing test cases
- Verification Method: Software Qualification Test, System Qualification Test, Unit Test
- Verification Owner: FV, SW
- System Requirement State: Approved
- Primary Discipline: SW
- ASIL Rating: QM

### TFDCX32348-14290: Processing for fail (Heading)

#### TFDCX32348-18316: Table-Processing for fail (System Requirement)
| No. | Input | Judgement Condition | Process | Recovery Condition |
| --- | --- | --- | --- | --- |
| 1 | NVM_LTA_Exist_Flag | When failure in reading NVM happens. | Consider that LTA is unequipped. | When normal data is read from NVM at the next IG-ON. |
- Verification Criteria: Verify by code review
- Verification Method: Unit Test
- Verification Owner: SW
- System Requirement State: Approved
- Primary Discipline: SW
- ASIL Rating: QM

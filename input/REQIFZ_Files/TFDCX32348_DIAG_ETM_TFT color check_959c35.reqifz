# Json2ReqIF Transformation

# Specification: DIAG_ETM_TFT color check
- JDA Snapshot Date: 2025-09-04 02:40:00

## TFDCX32348-1294: DIAG_ETM_TFT color check (Heading)
TFT color check
- System Requirement State: Draft
- Primary Discipline: TBD
- ASIL Rating: TBD

## TFDCX32348-1297: History (Heading)
- System Requirement State: Draft
- Primary Discipline: TBD
- ASIL Rating: TBD

### TFDCX32348-3014: Version Date Description of change SR... (Information)
| Version | Date | Name | Description of change | SRD Baseline |
| --- | --- | --- | --- | --- |
| 0.1 | 2024/04/09 | Takeshi Yamane | New created TFDCX32348-23231 [SYS][12.3FDC][APP] ETM | BL_20240521_01 |
| 0.2 | 2024/09/26 | Mathieu Lenoble | Update of the button to navigate through the buzzer. https://visteon.atlassian.net/browse/TFDCX32348-41765 | BL_20241018_01 |
| 0.3 | 2025/07/18 | Tejaswini Baviskar | Added TFT Illumination Image in ETM TFDCX32348-98279: [SYS][12.3FDC][APP][ETM] Add TT Illum Image and Reverse Buzzer in ETM | BL_20250721_01 |
- System Requirement State: Draft
- Primary Discipline: TBD
- ASIL Rating: TBD

## TFDCX32348-1299: Overview (Heading)
- System Requirement State: Draft
- Primary Discipline: TBD
- ASIL Rating: TBD

### TFDCX32348-3016: This SRD defines the requirement for ... (Information)
This SRD defines the requirement for TFT color check functionality.
This functional is executed in ETM mode.
- System Requirement State: Draft
- Primary Discipline: TBD
- ASIL Rating: TBD

## TFDCX32348-1300: Input Requirements (Heading)
- System Requirement State: Draft
- Primary Discipline: TBD
- ASIL Rating: TBD

### TFDCX32348-3018: Switch Input (Heading)
- System Requirement State: Draft
- Primary Discipline: TBD
- ASIL Rating: TBD

#### TFDCX32348-5405: H/W DI - ODO_TripKnobInput (System Interface)
- Verification Criteria: Verify by design review
- Verification Method: TBD
- Verification Owner: SW
- System Requirement State: Approved
- Secondary Disciplines: TBD
- ASIL Rating: QM

### TFDCX32348-3022: Internal I/F (Heading)
- System Requirement State: Draft
- Primary Discipline: TBD
- ASIL Rating: TBD

#### TFDCX32348-5409: InternalSignal - IgnMode (System Interface)
- Verification Criteria: Verify by design review
- Verification Method: TBD
- Verification Owner: SW
- System Requirement State: Approved
- Secondary Disciplines: TBD
- ASIL Rating: QM

## TFDCX32348-1302: Output Requirements (Heading)
- System Requirement State: Draft
- Primary Discipline: TBD
- ASIL Rating: TBD

### TFDCX32348-3024: HMI (Heading)
- System Requirement State: Draft
- Primary Discipline: TBD
- ASIL Rating: TBD

#### TFDCX32348-5411: HMI - HMI_IN_TFTTestPattern (System Interface)
- Verification Criteria: Verify by design review
- Verification Method: TBD
- Verification Owner: SW
- System Requirement State: Approved
- Secondary Disciplines: TBD
- ASIL Rating: QM

## TFDCX32348-1304: Performance Requirements (Heading)
- System Requirement State: Draft
- Primary Discipline: TBD
- ASIL Rating: TBD

### TFDCX32348-3025: This function control the TFT check. ... (System Requirement)
This function control the TFT check.
This function change the color pattern by pressing the ODO button on the test box.
More detail process is following.
- Verification Criteria: Verify by executing test cases
- Verification Method: System Qualification Test, Unit Test
- Verification Owner: FV, SW
- System Requirement State: Approved
- Secondary Disciplines: FV, SW
- Primary Discipline: SW
- ASIL Rating: QM

### TFDCX32348-3027: Figure - TFT Color Check Process Flow (Heading)
- System Requirement State: Draft
- Primary Discipline: TBD
- ASIL Rating: TBD

#### TFDCX32348-5413: TFT Color Flow (System Requirement)
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- Verification Criteria: Verify by executing test cases
- Verification Method: Functional Verification / Validation
- Verification Owner: FV
- System Requirement State: Approved
- Secondary Disciplines: FV, SW
- Primary Discipline: SW
- ASIL Rating: QM

#### TFDCX32348-5415: Figure - Manual transition TFT Color ... (Heading)
Figure - Manual transition TFT Color Check
- System Requirement State: Draft
- Primary Discipline: TBD
- ASIL Rating: TBD

##### TFDCX32348-6893: TFT Patterns (System Requirement)
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- Verification Criteria: Verify by executing test cases
- Verification Method: Functional Verification / Validation
- Verification Owner: FV
- System Requirement State: Approved
- ASIL Rating: QM

#### TFDCX32348-5417: Table - Set paramter for HMI_IN_TFTTe... (Heading)
Table - Set paramter for HMI_IN_TFTTestPattern
- System Requirement State: Draft
- Primary Discipline: TBD
- ASIL Rating: TBD

##### TFDCX32348-6895: HMI_IN_TFTTestPattern Display in TFT ... (System Requirement)
| HMI_IN_TFTTestPattern | Display in TFT | Remarks |
| --- | --- | --- |
| Test Red | Red display | Backlight illumination = 100% |
| Test Blue | Blue display | Backlight illumination = 100% |
| Test Green | Green display | Backlight illumination = 100% |
| Test White | White display | Backlight illumination = 100% |
| Test Black | Black display | Backlight illumination = 100% |
| Test Mura Calibration | Mura Display | Backlight illumination = 100% |
| Test Lattice | Lattice display | Backlight illumination = 100% |
| Test GrayScale1 | GrayScale1 | Backlight illumination = 100% |
| Test GrayScale2 | GrayScale2 | Backlight illumination = 100% |
| Test Lattice and Circles | Lattice and Circles | Backlight illumination = 100% |
| Test Telltale Full Illumination | Telltale Full Illumination | Backlight illumination = 100% |
| Off | No Request | Backlight illumination = 100% |
- Verification Criteria: Verify by executing test cases
- Verification Method: Functional Verification / Validation
- Verification Owner: FV
- System Requirement State: Approved
- Secondary Disciplines: FV, SW
- Primary Discipline: SW
- ASIL Rating: QM

#### TFDCX32348-5419: Table - Color Pattern (Heading)
- System Requirement State: Draft
- Primary Discipline: TBD
- ASIL Rating: TBD

##### TFDCX32348-6898: Color Pattern Graphics Red Blue Green... (System Requirement)
| Color Pattern | Graphics |
| --- | --- |
| Red |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 |
| Blue |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 |
| Green |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 |
| White |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 |
| Black |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 |
| Mura Calibration |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 |
| Lattice |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 |
| GlayScale1 |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 |
| GlayScale2 |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 |
| Lattice and Circles |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 |
| Telltale Full Illumination |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 |
- Verification Criteria: Verify by executing test cases
- Verification Method: Software Qualification Test, System Qualification Test, Unit Test
- Verification Owner: FV, SW
- System Requirement State: Approved
- Secondary Disciplines: FV, SW
- Primary Discipline: SW
- ASIL Rating: QM

##### TFDCX32348-6901: Backup of embedded file _5f376157-c... (Information)
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- Verification Criteria: Verify by executing test cases
- Verification Method: Software Qualification Test, System Qualification Test, Unit Test
- Verification Owner: FV
- System Requirement State: Approved
- Primary Discipline: SW
- ASIL Rating: QM

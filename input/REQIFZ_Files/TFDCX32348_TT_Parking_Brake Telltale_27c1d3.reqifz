# Json2ReqIF Transformation

# Specification: TT_Parking_Brake Telltale
- JDA Snapshot Date: 2025-10-29 07:17:58

## TFDCX32348-1029: TT_Parking_Brake Telltale (Heading)

## TFDCX32348-1031: History (Heading)

### TFDCX32348-1571: Version Date Name Description of chan... (Information)
| Version | Date | Name | Description of change | Baseline |
| --- | --- | --- | --- | --- |
| 0.1 | JUN/14/2024 | Kazuya Nagata | Newly create (Based on 38XD) TFDCX32348-23778 [SYS][12.3FDC][APP][Telltale] EPB(TT+BZR+MID) Change point: 1. TFDCX32348-28201/TFDCX32348-3105: Added “AppMode“ 2. TFDCX32348-1581/TFDCX32348-3105: Removed All_Telltale_ON test | BL_20240620_01 |
| 0.2 | Oct/30/2024 | Takuya Tamura | TFDCX32348-54350: [SYS][12.3FDC][APP][Telltale] Change telltale icons by country code Added InternalSignal - TT_DESTVali and determination | BL_20241106_01 |
| 0.3 | Mar/06/2025 | Syuta Matsuoka | Add EPB_AUTO_OFF_Telltale [SYS-Task] TFDCX32348-72794: [SYS][12.3FDC][APP][Telltale] EPB(TT+BZR+MID) for added the EPB auto off | BL_20250328_01 |
| 0.4 | Aug/26/2025 | Syuta Matsuoka | Change in symbol determination method Move TT priority logic from GUI [SYS-Task] TFDCX32348-89338: [SYS][12.3FDC][R6.1][D3576][APP][Telltale] Destination variation list (Telltale) | BL_20250828_01 |

## TFDCX32348-1032: Reference Document (Heading)

### TFDCX32348-1573: MET-C_EPB-CSTD-0-05-A-C0.xlsm (Information)

### TFDCX32348-1574: DMS_MET-C_EPB-CSTD-0-05-A-C0.xlsx (Information)

### TFDCX32348-28203: MET-M_DESTVARI-CSTD-A0-11-A-C0.xlsx (Information)

## TFDCX32348-1034: Overview (Heading)

### TFDCX32348-1576: This SRD defines Telltale of Parking ... (Information)
This SRD defines Telltale of Parking Brake Warning.

## TFDCX32348-1036: Input Requirements (Heading)

### TFDCX32348-1578: InternalSignal - IgnMode (System Interface)

### TFDCX32348-28201: InternalSignal - AppMode (System Interface)

### TFDCX32348-54228: InternalSignal - TT_DESTVali (System Interface)

### TFDCX32348-1579: CANSignal - B_PKBLP (Message Label: E... (System Interface)
CANSignal - B_PKBLP (Message Label: EPB1F01)

### TFDCX32348-73156: CANSignal - B_ATLP (Message Label: E... (System Interface)
CANSignal - B_ATLP (Message Label: EPB1F01)

### TFDCX32348-106522: InternalSignal - PKB_operation_Telltale_jdg (System Interface)

### TFDCX32348-106523: InternalSignal - DESTID0028 (System Interface)

## TFDCX32348-1038: Output Requirements (Heading)

### TFDCX32348-1583: TT – ParkingBrakeWarningTelltale Me... (System Interface)
TT – ParkingBrakeWarningTelltale
Meaning: This parameter indicates the display state of Parking Brake Warning Telltale.
Range: OFF, Txt, Txt_Blinking1, Txt_Blinking2, Txt_Blinking3, Img, Img_Blinking1, Img_Blinking2, Img_Blinking3
Initial Value: OFF

### TFDCX32348-73157: HMI - EPB_AUTO_OFF_Telltale (System Interface)
HMI - EPB_AUTO_OFF_Telltale
Range: OFF, AMBER
Initial Value: OFF

## TFDCX32348-1040: Performance Requirements (Heading)

### TFDCX32348-1585: Display Symbol (Heading)

#### TFDCX32348-1587: ParkingBrakeWarningTelltale Text Symbol (Heading)

##### TFDCX32348-3104: Display Symbol: Display Color: Red D... (Information)
1. Display Symbol:
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2. Display Color: Red
3. Destination: FMVSS Applicable [North America(CONV)_USA, North America(HEV)_USA]

#### TFDCX32348-1589: ParkingBrakeWarningTelltale Image Symbol (Heading)

##### TFDCX32348-3099: Display Symbol: Display Color: Red D... (Information)
1. Display Symbol:
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2. Display Color: Red
3. Destination: Other than FMVSS [North America(CONV)_CANADA, Middle East(CONV), General(CONV), Australia(HEV), Middle East(HEV), General(HEV)]

#### TFDCX32348-73160: EPB_AUTO_OFF_Telltale Symbol (Heading)

##### TFDCX32348-73161: 1.Display Symbol (Information)
1.Display Symbol:
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2.Display Color: Amber
3.Destination:All

### TFDCX32348-1590: Bulb Check (Heading)

#### TFDCX32348-3101: None (System Requirement)
- ASIL Rating: ASIL B

### TFDCX32348-1592: Initial Process (Heading)

#### TFDCX32348-3103: When the ON of the internal signal Ig... (System Requirement)
When the ON of the internal signal IgnMode is detected, the telltale is turn off until a lighting signal is received.
- Verification Criteria: Verify by executing test cases
- Verification Method: System Qualification Test, Unit Test
- Verification Owner: FV, SW
- System Requirement State: Approved
- Primary Discipline: SW
- ASIL Rating: ASIL B

### TFDCX32348-106526: Destination check (Heading)

#### TFDCX32348-106527: No. (System Requirement)
| No. | Input |  | Output |
| --- | --- | --- | --- |
| No. | InternalSignal - DESTID0028 | InternalSignal - TT_DESTVali | LocalParameter - Parking_Brake_Destination |
| 1 | 0 | x | UNR |
| 2 | 1 | x | FMVSS |
| 3 | Other than above | 0 | FMVSS |
| 4 | Other than above | 1 | UNR |
- Verification Criteria: Verify by executing test cases
- Verification Method: System Qualification Test, Unit Test
- Verification Owner: FV, SW
- System Requirement State: Approved
- Primary Discipline: SW
- ASIL Rating: QM

### TFDCX32348-1594: CAN Signal B_PKBLP Determination (Heading)

#### TFDCX32348-3105: CAN Signal B_PKBLP Processing (System Requirement)
| No. | Input |  |  |  | Output | Remark |
| --- | --- | --- | --- | --- | --- | --- |
| No. | InternalSignal - AppMode | InternalSignal - IgnMode | CAN Signal Communication Status – B_PKBLP | CAN Signal - B_PKBLP Received Value | InternalSignal - ParkingBrakeWarningTelltale_jdg | Remark |
| 1 | Normal Network Mode | x | Communication starting Never Received: 1 Communication Failure: 0 | x | No Change |  |
| 2 | Normal Network Mode | x | Communication establishment Never Received: 0 Communication Failure: 0 | 000b | OFF |  |
| 3 | Normal Network Mode | x | Communication establishment Never Received: 0 Communication Failure: 0 | 001b | ON |  |
| 4 | Normal Network Mode | x | Communication establishment Never Received: 0 Communication Failure: 0 | 011b | Blink1 | Vehicle speed unknown PKB status/ EPB inoperable status/ EPB continuous operation status |
| 5 | Normal Network Mode | x | Communication establishment Never Received: 0 Communication Failure: 0 | 100b | Blink2 | EPB Test Mode |
| 6 | Normal Network Mode | x | Communication establishment Never Received: 0 Communication Failure: 0 | 010b | Blink3 | EPB not completely applied status |
| 7 | Normal Network Mode | x | Communication establishment Never Received: 0 Communication Failure: 0 | Other than above | OFF |  |
| 8 | Normal Network Mode | ON | Communication abnormality Never Received: x Communication Failure: 1 | x | No change |  |
| 9 | Normal Network Mode | OFF | Communication abnormality Never Received: x Communication Failure: 1 | x | OFF |  |
| 10 | Normal Standalone Mode | x | x | x | No Change |  |
| 11 | Other than above | x | x | x | OFF |  |
Note:
Never Received and Communication Failurelisted in CAN General SRD.
Please check the CAN General SRD for details.
| # | Input |  |  | Output |
| --- | --- | --- | --- | --- |
| # | InternalSignal - ParkingBrakeWarningTelltale_jdg | InternalSignal - PKB_operation_Telltale_jdg | LocalParameter - Parking_Warning_Destination InternalSignal - TT_DestVali | TT - ParkingBrakeWarningTelltale |
| 1 | ON | x | FMVSS | Txt |
| 2 | ON | x | UNR | Img |
| 3 | Blinking1 | x | FMVSS | Txt_Blinking1 |
| 4 | Blinking1 | x | UNR | Img_Blinking1 |
| 5 | Blinking2 | x | FMVSS | Txt_Blinking2 |
| 6 | Blinking2 | x | UNR | Img_Blinking2 |
| 7 | Blinking3 | x | FMVSS | Txt_Blinking3 |
| 8 | Blinking3 | x | UNR | Img_Blinking3 |
| 9 | OFF | ON | FMVSS | Txt |
| 10 | OFF | ON | UNR | Img |
| 11 | OFF | OFF | x | OFF |
- Verification Criteria: Verify by executing test cases
- Verification Method: System Qualification Test, Unit Test
- Verification Owner: FV, SW
- System Requirement State: Approved
- Primary Discipline: SW
- ASIL Rating: ASIL B

### TFDCX32348-73158: CAN Signal B_ATLP Determination (Heading)

#### TFDCX32348-73159: CAN Signal B_ATLP Processing (System Requirement)
| No. | Input |  |  | Output |
| --- | --- | --- | --- | --- |
| No. | InternalSignal - AppMode | CAN Signal Communication Status – B_ATLP | CAN Signal - B_ATLP Received Value | InternalSignal - EPB_AUTO_OFF_Telltale |
| 1 | (Initialization at CPU reset or wakeup) |  |  | OFF |
| 2 | Normal Network Mode | Communication starting Never Received: 1 Communication Failure: 0 | x | No Change |
| 3 | Normal Network Mode | Communication establishment Never Received: 0 Communication Failure: 0 | 01b or 10b | AMBER |
| 4 | Normal Network Mode | Communication establishment Never Received: 0 Communication Failure: 0 | Other than above | OFF |
| 5 | Normal Network Mode | Communication abnormality Never Received: x Communication Failure: 1 | x | OFF |
| 6 | Normal Standalone Mode | x | x | No Change |
| 7 | Other than above | x | x | OFF |
- Verification Criteria: Verify by executing test cases
- Verification Method: System Qualification Test, Unit Test
- Verification Owner: FV, SW
- System Requirement State: Approved
- Primary Discipline: SW
- ASIL Rating: QM

### TFDCX32348-1596: Blinking Control (Heading)

#### TFDCX32348-3106: ON Duty Ratio (Heading)

##### TFDCX32348-5472: ON duty ratio is 50%. (System Requirement)
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ON duty ratio is 50%.
- Verification Criteria: Verify by executing test cases
- Verification Method: System Qualification Test, Unit Test
- Verification Owner: FV, SW
- System Requirement State: Approved
- Primary Discipline: SW
- ASIL Rating: ASIL B

#### TFDCX32348-3108: Blinking Pattern (Heading)

##### TFDCX32348-5474: Blinking Pattern1 (Vehicle speed unkn... (Heading)
Blinking Pattern1 (Vehicle speed unknown PKB status/ EPB inoperable status/ EPB continuous operation status)

###### TFDCX32348-5476 (System Requirement)
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- Verification Criteria: Verify by executing test cases
- Verification Method: System Qualification Test, Unit Test
- Verification Owner: FV, SW
- System Requirement State: Approved
- Primary Discipline: SW
- ASIL Rating: ASIL B

##### TFDCX32348-5478: Blinking Pattern2 (EPB Test Mode) (Heading)

###### TFDCX32348-5480 (System Requirement)
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- Verification Criteria: Verify by executing test cases
- Verification Method: System Qualification Test, Unit Test
- Verification Owner: FV, SW
- System Requirement State: Approved
- Primary Discipline: SW
- ASIL Rating: ASIL B

##### TFDCX32348-5482: Blinking Pattern3 (EPB not completely... (Heading)
Blinking Pattern3 (EPB not completely applied status/ Initial lamp check mode)

###### TFDCX32348-5484 (System Requirement)
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- Verification Criteria: Verify by executing test cases
- Verification Method: System Qualification Test, Unit Test
- Verification Owner: FV, SW
- System Requirement State: Approved
- Primary Discipline: SW
- ASIL Rating: ASIL B

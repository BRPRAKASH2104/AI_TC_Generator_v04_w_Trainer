# Json2ReqIF Transformation

# Specification: TT_HEAD LIGHT Telltale
- JDA Snapshot Date: 2025-10-29 07:17:02

## TFDCX32348-1087: TT_HEAD LIGHT Telltale (Heading)

## TFDCX32348-1089: History (Heading)

### TFDCX32348-2326: Version Date Name Description of chan... (Information)
| Version | Date | Name | Description of change | Baseline |
| --- | --- | --- | --- | --- |
| 0.1 | APR/17/2024 | Takeshi Yamane | Newly create TFDCX32348-23710 [SYS][12.3FDC][APP][Telltale] HEAD indicator (CAN communication or linear connection) | BL_20240521_01 |
| 0.2 | Oct/29/2024 | Takuya Tamura | TFDCX32348-54350: [SYS][12.3FDC][APP][Telltale] Change telltale icons by country code Added InternalSignal - TT_DESTVali and determination | BL_20241106_01 |
| 0.3 | Aug/26/2025 | Syuta Matsuoka | Change in symbol determination method [SYS-Task] TFDCX32348-89338: [SYS][12.3FDC][R6.1][D3576][APP][Telltale] Destination variation list (Telltale) | BL_20250828_01 |

## TFDCX32348-1091: Reference Document (Heading)

### TFDCX32348-2328: MET-B_THEAD-CSTD-0-00-A-C1_ja.doc (Information)

### TFDCX32348-2329: MET-B_THEAD-CSTD-0-XX-X-C1-ALL-a.docx (Information)

### TFDCX32348-54219: MET-M_DESTVARI-CSTD-A0-11-A-C0.xlsx (Information)

## TFDCX32348-1093: Overview (Heading)

### TFDCX32348-2331: This SRD defines Telltale of HEAD Lamp (Information)

## TFDCX32348-1095: Input Requirements (Heading)

### TFDCX32348-2333: InternalSignal – IgnMode (System Interface)

### TFDCX32348-2335: InternalSignal – AppMode (System Interface)

### TFDCX32348-2337: CANSignal – HEDL (Message Label: BDB1... (System Interface)
CANSignal – HEDL (Message Label: BDB1S03)

### TFDCX32348-25508: InternalSignal - TT_DESTVali (System Interface)

### TFDCX32348-106481: InternalSignal - TLHD_Select (System Interface)

## TFDCX32348-1098: Output Requirements (Heading)

### TFDCX32348-2341: TT – HEADLamp_Telltale Meaning: Thi... (System Interface)
TT – HEADLamp_Telltale
Meaning: This parameter indicates the display state of the HEAD Lamp Telltale.
Range: OFF, ON
Initial Value: OFF

### TFDCX32348-2343: InternalSignal – Head_TT_State Mean... (System Interface)
InternalSignal – Head_TT_State
Meaning: This parameter indicates the display state of the HEAD Lamp Telltale.
Range: FALSE, TRUE
Initial Value: FALSE
Note: This internal signal is used for CAN bus wake-up/sleep control.

## TFDCX32348-1100: Performance Requirements (Heading)

### TFDCX32348-2344: Display Symbol (Heading)

#### TFDCX32348-3179: Display Symbol: Display Color: Pure ... (Information)
1. Display Symbol:
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2. Display Color: Pure Green
3. Destination: All [North America(CONV)_USA, North America(HEV)_USA, North America(CONV)_CANADA, Middle East(CONV), General(CONV), Australia(HEV), Middle East(HEV), General(HEV)]

### TFDCX32348-2346: Bulb Check (Heading)

#### TFDCX32348-3181: None (System Requirement)
- ASIL Rating: QM

### TFDCX32348-2348: Initial Process (Heading)

#### TFDCX32348-3183: When +B is connected or when Meter wa... (System Requirement)
When +B is connected or when Meter wake up:
Turn off the HEAD Lamp telltale until the lighting signal received.
- Verification Criteria: Verify by executing test cases
- Verification Method: System Qualification Test, Unit Test
- Verification Owner: FV, SW
- System Requirement State: Approved
- Secondary Disciplines: FV, SW
- Primary Discipline: SW
- ASIL Rating: QM

### TFDCX32348-2350: Telltale Control (Heading)

#### TFDCX32348-3185: CAN Signal HEDL Determination (Heading)

##### TFDCX32348-5607: No. (System Requirement)
| No. | Input |  |  |  |  | Output |  | Remark |
| --- | --- | --- | --- | --- | --- | --- | --- | --- |
| No. | InternalSignal - TLHD_Select InternalSignal - TT_DESTVali | InternalSignal - AppMode | InternalSignal - IgnMode | CAN Signal Communication Status – HEDL | CANSignal – HEDL Value | TT - HEADLamp_Telltale | InternalSignal – Head_TT_State | Remark |
| 1 | HEAD | Normal Network Mode | x | Communication starting Never Received: 1 Communication Failure: 0 | x | No Change | No Change |  |
| 2 | HEAD | Normal Network Mode | x | Communication establishment Never Received: 0 Communication Failure: 0 | 0b | OFF | FALSE |  |
| 3 | HEAD | Normal Network Mode | x | Communication establishment Never Received: 0 Communication Failure: 0 | 1b | ON | TRUE | Delaying the telltale ON by 300ms after receiving a CAN signal with telltale ON request. |
| 4 | HEAD | Normal Network Mode | ON | Communication abnormality Never Received: x Communication Failure: 1 | x | No Change | No Change |  |
| 5 | HEAD | Normal Network Mode | OFF | Communication abnormality Never Received: x Communication Failure: 1 | x | OFF | FALSE |  |
| 6 | HEAD | Normal Standalone Mode | - | - | - | No Change | No Change |  |
| 7 | HEAD | Other than above | - | - | - | OFF | FALSE |  |
| 8 | TAIL | - | - | - | - | OFF | FALSE |  |
Note:
Never Received and Communication Failurelisted in CAN General SRD.
Please check the CAN General SRD for details.
- Verification Criteria: Verify by executing test cases
- Verification Method: System Qualification Test, Unit Test
- Verification Owner: FV, SW
- System Requirement State: Approved
- Secondary Disciplines: FV, SW
- Primary Discipline: SW
- ASIL Rating: QM

# Json2ReqIF Transformation

# Specification: TT_PKB operation
- JDA Snapshot Date: 2025-10-29 07:17:49

## TFDCX32348-35329: TT_PKB operation (Heading)

## TFDCX32348-35332: History (Heading)

### TFDCX32348-35333: Version (Information)
| Version | date | Name | Description of change | Baseline |
| --- | --- | --- | --- | --- |
| 0.1 | 25/Jul/2024 | Syuta Matsuoka | Newly Created [SYS-Task] TFDCX32348-28145: [SYS][12.3FDC][APP][Telltale] PKB operation (Tel-Tale) | BL_20240731_01 |
| 0.2 | 30/Oct/2024 | Takuya Tamura | TFDCX32348-54350: [SYS][12.3FDC][APP][Telltale] Change telltale icons by country code Added InternalSignal - TT_DESTVali and determination | BL_20241106_01 |
| 0.3 | 26/Aug/2025 | Syuta Matsuoka | Change Output to Internal Signal Delete TT_DESTVali [SYS-Task] TFDCX32348-89338: [SYS][12.3FDC][R6.1][D3576][APP][Telltale] Destination variation list (Telltale) | BL_20250828_01 |

## TFDCX32348-35334: Reference Document (Heading)

### TFDCX32348-35335: MET-C_TPKBON-CSTD-0-01-B-C1.doc (Information)
MET-C_TPKBON-CSTD-0-01-B-C1.doc
DMS_MET-C_TPKBON-CSTD-0-01-B-C1.xlsx
MET-M_DESTVARI-CSTD-A0-11-A-C0.xlsx

## TFDCX32348-35336: Overview (Heading)

### TFDCX32348-35337: This SRD defines the requirements for telltale of PKB operation. (Information)

## TFDCX32348-35339: Input Requirements (Heading)

### TFDCX32348-35340: InternalSignal – IgnMode (System Interface)

### TFDCX32348-35341: CANSignal - PKB_BDB(Message Label: BDB1S01) (System Interface)

### TFDCX32348-35342: CANSignal - B_CPKB(Message Label: VSC1S95) (System Interface)

### TFDCX32348-54227: InternalSignal - TT_DESTVali (System Interface)

## TFDCX32348-35351: Output Requirements (Heading)

### TFDCX32348-35352: TT - PKB_operation_Telltale (System Interface)
TT - PKB_operation_Telltale
Range: OFF, Txt, Img

### TFDCX32348-106521 (System Interface)
InternalSignal - PKB_operation_Telltale_jdg
Range: {OFF,ON}

## TFDCX32348-35394: Performance Requirement (Heading)

### TFDCX32348-35398: Display Symbol (Heading)

#### TFDCX32348-35442: Display Symbol (Information)
1. Display Symbol:
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1. Display Color: Red
2. Destination: FMVSS Applicable [North America(CONV)_USA, North America(HEV)_USA]

#### TFDCX32348-35399: Display Symbol (Information)
1. Display Symbol:
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1. Display Color: Red
2. Destination: Other than FMVSS [North America(CONV)_CANADA, Middle East(CONV), General(CONV), Australia(HEV), Middle East(HEV), General(HEV)]

### TFDCX32348-35400: Bulb Check (Heading)

#### TFDCX32348-35401: None (System Requirement)

### TFDCX32348-35403: Telltale Control (Heading)

#### TFDCX32348-35408: CAN Signal PKB_DBD Determination (Heading)

##### TFDCX32348-35409: No. Input Output (System Requirement)
| No. | Input |  |  | Output |
| --- | --- | --- | --- | --- |
| No. | InternalSignal - IgnMode | CAN Signal Communication Status – PKB_DBD | CAN Signal - PKB_DBD Value | PKB_DBD Judgment Result |
| 1 | OFF | x | x | OFF |
| 2 | ON | Communication starting Never Received: 1 Communication Failure: 0 | x | OFF |
| 3 | ON | Communication establishment Never Received: 0 Communication Failure: 0 | 0b | OFF |
| 4 | ON | Communication establishment Never Received: 0 Communication Failure: 0 | 1b | ON |
| 5 | ON | Communication abnormality Never Received: x Communication Failure: 1 | x | no change |
Note: This Telltale does not determine if communication is interrupted.
- Verification Criteria: Verify by executing test cases
- Verification Method: System Qualification Test, Unit Test
- Verification Owner: FV, SW
- System Requirement State: Approved
- Primary Discipline: SW
- ASIL Rating: QM

#### TFDCX32348-35410: CAN Signal B_CPKB Determination (Heading)

##### TFDCX32348-35411: No. Input Output (System Requirement)
| No. | Input |  |  | Output |
| --- | --- | --- | --- | --- |
| No. | InternalSignal - IgnMode | CAN Signal Communication Status – B_CPKB | CAN Signal - B_CPKB Value | B_CPKB Judgment Result |
| 1 | OFF | x | x | OFF |
| 2 | ON | Communication starting Never Received: 1 Communication Failure: 0 | x | OFF |
| 3 | ON | Communication establishment Never Received: 0 Communication Failure: 0 | 0b | OFF |
| 4 | ON | Communication establishment Never Received: 0 Communication Failure: 0 | 1b | ON |
| 5 | ON | Communication abnormality Never Received: x Communication Failure: 1 | x | no change |
Note: This Telltale does not determine if communication is interrupted.
- Verification Criteria: Verify by executing test cases
- Verification Method: System Qualification Test, Unit Test
- Verification Owner: FV, SW
- System Requirement State: Approved
- Primary Discipline: SW
- ASIL Rating: QM

#### TFDCX32348-35404: Talltale Determination (Heading)

##### TFDCX32348-35412: No. Input (System Requirement)
| No. | Input |  |  | Output |
| --- | --- | --- | --- | --- |
| No. | InternalSignal - IgnMode | PKB_DBD Judgment Result | B_CPKB Judgment Result | InternalSignal - PKB_operation_Telltale_jdg |
| 1 | OFF | X | X | OFF |
| 2 | ON | OFF | OFF | OFF |
| 3 | ON | Other than above (One or more of the above 2 parameters are ON) |  | ON |
| # | Input |  | Output |
| --- | --- | --- | --- |
| # | InternalSignal - PKB_operation_Telltale_jdg | InternalSignal - TT_DESTVali | TT – PKB_operation_Telltale |
| 1 | ON | 0[FMVSS] | Txt |
| 2 | ON | 1[Other than FMVSS] | Img |
| 3 | OFF | x | OFF |
- Verification Criteria: Verify by executing test cases
- Verification Method: System Qualification Test, Unit Test
- Verification Owner: FV, SW
- System Requirement State: Approved
- Primary Discipline: SW
- ASIL Rating: QM

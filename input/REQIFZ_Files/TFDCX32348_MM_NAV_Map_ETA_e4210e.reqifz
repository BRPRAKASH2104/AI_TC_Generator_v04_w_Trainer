# Json2ReqIF Transformation

# Specification: MM_NAV_Map_ETA
- JDA Snapshot Date: 2025-09-04 03:04:51

## TFDCX32348-54174: MM_NAV_Map_ETA (Heading)

## TFDCX32348-54175: History (Heading)

### TFDCX32348-54181: Version Date Name Description of chan... (Information)
| Version | Date | Name | Description of change | Baseline |
| --- | --- | --- | --- | --- |
| 0.1 | 30/Oct/2024 | Ybai7 | Newly create TFDCX32348-41825: [SYS][12.3FDC][APP][MM] [Common] NAVI Coordination (MAP View - ETA) | BL_20241105_01 |
| 0.2 | 27/Feb/2025 | Ybai7 | TFDCX32348-69512: [SYS][12.3FDC][APP][HUD] HUD Interrupt - ETA Deleted HMI - HUD_MAP_View_ETA_Display_Status | BL_20250424_01 |

## TFDCX32348-54176: Reference Document (Heading)

### TFDCX32348-54182 (Information)
【別紙】4.7.2 到着予想時刻表示(車両連携Level2)_METXMM-NAVTIME-X23-050.doc
【Attached file】4.7.2 Predicted arrival time indication (level 2)_METXMM-NAVTIME-X23-050_en.docx

## TFDCX32348-54177: Overview (Heading)

### TFDCX32348-54183: This SRD defines the control for displaying ETA. (Information)

## TFDCX32348-54178: Input Requirements (Heading)

### TFDCX32348-54184: InternalSignal - ACCStatus (System Interface)
- Verification Criteria: Verify by code review
- Verification Method: Unit Test
- Verification Owner: SW
- System Requirement State: Approved
- Primary Discipline: SW
- ASIL Rating: QM

### TFDCX32348-54188: MMCANSignal - NAVTIME_F(Message Label: AVNMS58) (System Interface)
- Verification Criteria: Verify by code review
- Verification Method: Unit Test
- Verification Owner: SW
- System Requirement State: Approved
- Primary Discipline: SW
- ASIL Rating: QM

### TFDCX32348-54224: MMCANSignal - NAVTIME_VR(Message Label: AVNMS58) (System Interface)
- Verification Criteria: Verify by code review
- Verification Method: Unit Test
- Verification Owner: SW
- System Requirement State: Approved
- Primary Discipline: SW
- ASIL Rating: QM

### TFDCX32348-54225: MMCANSignal - NAVTIME_HR(Message Label: AVNMS58) (System Interface)
- Verification Criteria: Verify by code review
- Verification Method: Unit Test
- Verification Owner: SW
- System Requirement State: Approved
- Primary Discipline: SW
- ASIL Rating: QM

### TFDCX32348-54226: MMCANSignal - NAVTIME_MIN(Message Label: AVNMS58) (System Interface)
- Verification Criteria: Verify by code review
- Verification Method: Unit Test
- Verification Owner: SW
- System Requirement State: Approved
- Primary Discipline: SW
- ASIL Rating: QM

## TFDCX32348-54179: Output Requirements (Heading)

### TFDCX32348-54185: HMI - MET_MAP_View_ETA_Display_Status (System Interface)
HMI - MET_MAP_View_ETA_Display_Status
Range: (Invalid, Valid)
- Verification Criteria: Verify by code review
- Verification Method: Unit Test
- Verification Owner: SW
- System Requirement State: Approved
- Primary Discipline: SW
- ASIL Rating: QM

### TFDCX32348-54233: HMI - HUD_MAP_View_ETA_Display_Status (System Interface)
HMI - HUD_MAP_View_ETA_Display_Status
Range: OFF, ON

### TFDCX32348-54187: HMI – MAP_View_ETA_HR (System Interface)
HMI – MAP_View_ETA_HR
Range: OFF, 00h-17h, 1Eh, 1Fh
- Verification Criteria: Verify by code review
- Verification Method: Unit Test
- Verification Owner: SW
- System Requirement State: Approved
- Primary Discipline: SW
- ASIL Rating: QM

### TFDCX32348-54235: HMI – MAP_View_ETA_MIN (System Interface)
HMI – MAP_View_ETA_MIN
Range: OFF, 00h-3Bh, 3Eh, 3Fh
- Verification Criteria: Verify by code review
- Verification Method: Unit Test
- Verification Owner: SW
- System Requirement State: Approved
- Primary Discipline: SW
- ASIL Rating: QM

## TFDCX32348-54180: Performance Requirements (Heading)

### TFDCX32348-54186: Table - Logic table (Heading)

#### TFDCX32348-54190: Input Output (System Requirement)
| No. | Input |  |  |  |  |  | Output |  |  |  |
| --- | --- | --- | --- | --- | --- | --- | --- | --- | --- | --- |
| No. | InternalSignal -ACCStatus | Communication Status for NAVI signals(Refer to TFDCX32348-54191) | MMCANSignal - NAVTIME_F | MMCAN Signal - NAVTIME_VR | MMCAN Signal - NAVTIME_HR | MMCAN Signal - NAVTIME_MIN | HMI - MET_MAP_View_ETA_Display_Status | HMI - HUD_MAP_View_ETA_Display_Status | HMI – MAP_View_ETA_HR | HMI - MAP_View_ETA_MIN |
| 1 | (Initialization at CPU reset or wakeup) |  |  |  |  |  | Invalid | OFF | OFF | OFF |
| 2 | OFF | X | X | X | X | X | Invalid | OFF | OFF | OFF |
| 3 | ON | Starting | X | X | X | X | Invalid | OFF | OFF | OFF |
| 4 | ON | Failure | X | X | X | X | Invalid | OFF | OFF | OFF |
| 5 | ON | Established | 0b | X | X | X | Invalid | OFF | OFF | OFF |
| 6 | ON | Established | 1b | 1b | 00h - 17h, 1Eh, 1Fh X | 00h-3Bh, 3Eh, 3Fh X | Invalid | ON | Value of NAVTIME_HR OFF | Value of NAVTIME_MIN OFF |
| 7 | ON | Established | 1b | 1b | Other than above |  | Invalid | OFF | OFF | OFF |
| 8 | ON | Established | 1b | 0b | 00h - 17h, 1Eh, 1Fh | 00h-3Bh, 3Eh, 3Fh | Valid | OFF | Value of NAVTIME_HR | Value of NAVTIME_MIN |
| 9 | ON | Established | 1b | 0b | Other than above |  | Invalid | OFF | OFF | OFF |
| 10 | Other than above |  |  |  |  |  | Invalid | OFF | OFF | OFF |
- Verification Criteria: Verify by executing test cases
- Verification Method: Software Qualification Test, System Qualification Test, Unit Test
- Verification Owner: FV, SW
- System Requirement State: Approved
- Primary Discipline: SW
- ASIL Rating: QM

#### TFDCX32348-54191: Processing for fail (System Requirement)
| Input | Output |
| --- | --- |
| Communication Status for any of NAVI target Signals(*) (*) Applicable MMCAN signal NAVTIME_F(Message Label: AVNMS58) NAVTIME_VR(Message Label: AVNMS58) NAVTIME_HR(Message Label: AVNMS58) NAVTIME_MIN(Message Label: AVNMS58) Note: Strictly speaking, MMCAN Frame communication status should be checked. But MM CAN signals in each of the frame share the same timeout time (30s), You can check only the above four signals instead of MMCAN Frame. | Communication Status for NAVI signals |
| MM-CAN Never received status of any signal above is 1 AND MM-CAN Communication failure status of all of the signals listed above is 0 | Starting |
| MM-CAN Communication failure status of any signal above is 1 | Failure |
| MM-CAN Never received status of all signals above is 0 AND MM-CAN Communication failure status of all of the signals listed above is 0 | Established |
- Verification Criteria: Verify by executing test cases
- Verification Method: Software Qualification Test, System Qualification Test, Unit Test
- Verification Owner: FV, SW
- System Requirement State: Approved
- Primary Discipline: SW
- ASIL Rating: QM

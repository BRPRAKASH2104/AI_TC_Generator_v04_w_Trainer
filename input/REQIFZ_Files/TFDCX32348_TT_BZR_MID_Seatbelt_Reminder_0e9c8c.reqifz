# Json2ReqIF Transformation

# Specification: TT_BZR_MID_Seatbelt_Reminder
- JDA Snapshot Date: 2025-10-28 02:18:15

## TFDCX32348-943: TT_BZR_MID_Seatbelt_Reminder (Heading)

## TFDCX32348-945: History (Heading)

### TFDCX32348-2542: History (Information)
| Version | Date | Name | Description of change | SRD Baseline |
| --- | --- | --- | --- | --- |
| 1.3 (38xD) |  |  | Copied from 38xD as the base. | BL_20231214_01 (38xD) |
| 2.0 (12.3FDC) | 1/Jul/2024 | ttakaba | TFDCX32348-23781: [SYS][12.3FDC][APP][Telltale] SEAT BELT REMINDER(TT+BZR+MID) First release of the 12.3FDC SRD. | BL_20240724_01 |
|  | 17/Sep/2024 | ttakaba | Changed MCUCONST parameter form NVM to ROM const. |  |
| 2.1 | 27/May/2025 | mkubo1 | Updated for New FMVSS208 TFDCX32348-81880: [SYS][12.3FDC][R5][APP] Seatbelt Reminder (Support for FMVSS208) | BL_20250616_01 BL_20250628_01 |
| 2.2 | 9/July/2025 | mkubo1 | Update the logic fot Standard QA No.2549, 3203, 3520 TFDCX32348-96471: [SYS][12.3FDC][R5.2][STDQA2549][APP][Telltale] Add the judgment prioed for ABG1S01 frame TFDCX32348-96480: [SYS][12.3FDC][R5.2][STDQA3203][APP][Telltale] Added the judgment of second row seat to "state before confirmation" TFDCX32348-96821: [SYS][12.3FDC][R5.2][STDQA3520][APP][Telltale] Added the judgment of initial state for driver, passenger seat | BL_20250714_01 |
| 2.3 | 10/July/2025 | mkubo1 | Add the judgment of destination for legal items TFDCX32348-89336: [SYS][12.3FDC][R6.1][D3576][APP][Telltale] Destination variation list (Seat belt reminder) | BL_20250714_01 |
| 2.4 | 05/August/2025 | tbaviska | Updated Timestamp - YEAR range from 00-38 → 00-99 TFDCX32348-97737: [SYS][12.3FDC][R5.2][STDQA3160][STDQA3174][STDQA3178][STDQA3265][APP][Diagnostic] Update Phase 6 Diag System for Data Identifier | BL_20250808_01 |
| 2.5 | 10/Sep/2025 | mkubo1 | Change SP1 interface TFDCX32348-106946 | BL_20250919_01 |
| 2.6 | 25/Sep/2025 | mkubo1 | 1.Applicable the Lexus parameter ( changed Information to System Requrements.) 2.Changed the conditions ag, ah, and ai from edge judgment to level judgment for new FMVSS208 telltale. TFDCX32348-110123 | BL_20251017_01 |

## TFDCX32348-947: Overview (Heading)

### TFDCX32348-2545: Overview (Information)
This SRD defines the requirements for telltale (LED and TFT) and buzzer of 'Seatbelt Reminder'.
Current seat belt reminder logic supports various seat arrangement types, driver, passenger and front center seat, and also rear 1st, 2nd, and 3rd row seats.
All those seat belt statuses are transmitted from the external ECU through CAN, and if corresponding seats are not equipped, they are always transmitted as BUCKLED.
Therefore, the cluster performs seat belt reminder processing assuming that all seats (including the front center, and the 2nd, 3rd row rear seats) are present.
From the perspective of HMI, Meter controls output for the following items:
LED Telltale
Meter controls LED telltale for front seats (One common telltale for driver, passenger and front center seat).
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(Color: Red)
TFT (MID) Telltale
Meter displays warning telltales with 'REAR' text for rear seats in TFT (Below is a reference image).
Rear 1 row 2 seats:
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Rear 1 row 3 seats:
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Rear 2 rows 3 seats:
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Buzzer
Meter outputs 4 types (1xSingle shot, 3xIntermittent) of buzzers.

## TFDCX32348-35052: Reference Documents (Heading)

### TFDCX32348-35053: Reference Documents (Information)
Reference Documents
MET-B_SEAREM-CSTD-A0-06-A-C3
MET-M_MCUCONST-CSTD-A0-027-XXXX-X

## TFDCX32348-949: Input Requirements (Heading)

### TFDCX32348-2547: Internal Signal (Heading)

#### TFDCX32348-3215: Internal Signal - IgnMode (System Interface)
- Verification Criteria: Verify by design review
- Verification Method: Code/Design Review
- Verification Owner: SW
- System Requirement State: Approved
- Primary Discipline: SW
- ASIL Rating: QM

#### TFDCX32348-3221: Internal Signal - All_Telltale_ON test (ON/OFF) (Dropped) (System Interface)
- Verification Criteria: Verify by design review
- Verification Method: Code/Design Review
- Verification Owner: SW
- System Requirement State: Rejected
- Primary Discipline: SW
- ASIL Rating: QM

#### TFDCX32348-3223: Internal Signal - BuzzerTest_SBR (ON / OFF) (System Interface)
- Verification Criteria: Verify by design review
- Verification Method: Code/Design Review
- Verification Owner: SW
- System Requirement State: Approved
- Primary Discipline: SW
- ASIL Rating: QM

#### TFDCX32348-3217: Internal Signal - CountryCode (Dropped) (System Interface)
- Verification Criteria: Verify by design review
- Verification Method: Code/Design Review
- Verification Owner: SW
- System Requirement State: Rejected
- Primary Discipline: SW
- ASIL Rating: QM

#### TFDCX32348-3224: Cfg - region_Group (Dropped) (System Interface)
- Verification Criteria: Verify by design review
- Verification Method: Code/Design Review
- Verification Owner: SW
- System Requirement State: Rejected
- Primary Discipline: SW
- ASIL Rating: QM

#### TFDCX32348-31863: Internal Signal - CountryCodeFunc (System Interface)
- Verification Criteria: Verify by design review
- Verification Method: Code/Design Review
- Verification Owner: SW
- System Requirement State: Approved
- Primary Discipline: SW
- ASIL Rating: QM

#### TFDCX32348-97063: InternalSignal - DESTID0020 (System Interface)
- Verification Criteria: Verify by design review
- Verification Method: Code/Design Review
- Verification Owner: SW
- System Requirement State: Approved
- Primary Discipline: SW
- ASIL Rating: QM

#### TFDCX32348-108780: InternalSignal - SP1_in (System Interface)
InternalSignal - SP1_in
* Calculate "x 0.01", and change the Resolution for Seatbelt reminder SRD.
- Verification Criteria: Verify by design review
- Verification Method: Code/Design Review
- Verification Owner: SW
- System Requirement State: Approved
- Primary Discipline: SW
- ASIL Rating: QM

### TFDCX32348-2549: Hardwire (Heading)

#### TFDCX32348-3226: HW - DI_AL_DRV_SEAT_BUCKLE (Dropped) (System Interface)
HW - DI_AL_DRV_SEAT_BUCKLE (Dropped)
Range: {OFF(Buckled), ON(Unbuckled)}
Power condition: IgnMode=ON
Input deciding time (Debounce): Same value(level) received 2 times @ 20ms cycle
- Verification Criteria: Verify by design review
- Verification Method: Code/Design Review
- Verification Owner: SW
- System Requirement State: Rejected
- Primary Discipline: SW
- ASIL Rating: QM

### TFDCX32348-2551: CAN (Heading)

#### TFDCX32348-3228: CAN Signal - SP1 (Message Label : VSC1G13) (System Interface)
- Verification Criteria: Verify by design review
- Verification Method: Code/Design Review
- Verification Owner: SW
- System Requirement State: Approved
- Primary Discipline: SW
- ASIL Rating: QM

#### TFDCX32348-3229: CAN Signal - B_R (Message Label: ECT1G01) (System Interface)
- Verification Criteria: Verify by design review
- Verification Method: Code/Design Review
- Verification Owner: SW
- System Requirement State: Approved
- Primary Discipline: SW
- ASIL Rating: QM

#### TFDCX32348-95015: CAN Signal - B_N (Message Label: ECT1G01) (System Interface)
- Verification Criteria: Verify by design review
- Verification Method: Code/Design Review
- Verification Owner: SW
- System Requirement State: Approved
- Primary Discipline: SW
- ASIL Rating: QM

#### TFDCX32348-3230: CAN Signal - B_P (Message Label: ECT1G01) (System Interface)
- Verification Criteria: Verify by design review
- Verification Method: Code/Design Review
- Verification Owner: SW
- System Requirement State: Approved
- Primary Discipline: SW
- ASIL Rating: QM

#### TFDCX32348-3231: CAN Signal - DCTY (Message Label: BDB1S01) (System Interface)
- Verification Criteria: Verify by design review
- Verification Method: Code/Design Review
- Verification Owner: SW
- System Requirement State: Approved
- Primary Discipline: SW
- ASIL Rating: QM

#### TFDCX32348-3232: CAN Signal - PCTY (Message Label: BDB1S01) (System Interface)
- Verification Criteria: Verify by design review
- Verification Method: Code/Design Review
- Verification Owner: SW
- System Requirement State: Approved
- Primary Discipline: SW
- ASIL Rating: QM

#### TFDCX32348-3234: CAN Signal - RRCY (Message Label: BDB1S01) (System Interface)
- Verification Criteria: Verify by design review
- Verification Method: Code/Design Review
- Verification Owner: SW
- System Requirement State: Approved
- Primary Discipline: SW
- ASIL Rating: QM

#### TFDCX32348-3236: CAN Signal - RLCY (Message Label: BDB1S01) (System Interface)
- Verification Criteria: Verify by design review
- Verification Method: Code/Design Review
- Verification Owner: SW
- System Requirement State: Approved
- Primary Discipline: SW
- ASIL Rating: QM

#### TFDCX32348-31465: CAN Signal - BCTY (Message Label: BDB1S01) (System Interface)
- Verification Criteria: Verify by design review
- Verification Method: Code/Design Review
- Verification Owner: SW
- System Requirement State: Approved
- Primary Discipline: SW
- ASIL Rating: QM

#### TFDCX32348-3238: CAN Signal - PKB_BDB (Message Label: BDB1S01) (System Interface)
- Verification Criteria: Verify by design review
- Verification Method: Code/Design Review
- Verification Owner: SW
- System Requirement State: Approved
- Primary Discipline: SW
- ASIL Rating: QM

#### TFDCX32348-3246: CAN Signal - POSW (Message Label: BDB1S01) (System Interface)
- Verification Criteria: Verify by design review
- Verification Method: Code/Design Review
- Verification Owner: SW
- System Requirement State: Approved
- Primary Discipline: SW
- ASIL Rating: QM

#### TFDCX32348-3250: CAN Signal - RROSW (Message Label: BDB1S01) (System Interface)
- Verification Criteria: Verify by design review
- Verification Method: Code/Design Review
- Verification Owner: SW
- System Requirement State: Approved
- Primary Discipline: SW
- ASIL Rating: QM

#### TFDCX32348-3254: CAN Signal - RCOSW (Message Label: BDB1S01) (System Interface)
- Verification Criteria: Verify by design review
- Verification Method: Code/Design Review
- Verification Owner: SW
- System Requirement State: Approved
- Primary Discipline: SW
- ASIL Rating: QM

#### TFDCX32348-3257: CAN Signal - RLOSW (Message Label: BDB1S01) (System Interface)
- Verification Criteria: Verify by design review
- Verification Method: Code/Design Review
- Verification Owner: SW
- System Requirement State: Approved
- Primary Discipline: SW
- ASIL Rating: QM

#### TFDCX32348-3240: CAN Signal - DBKLAB (Message Label: ABG1S01) (System Interface)
- Verification Criteria: Verify by design review
- Verification Method: Code/Design Review
- Verification Owner: SW
- System Requirement State: Approved
- Primary Discipline: SW
- ASIL Rating: QM

#### TFDCX32348-3242: CAN Signal - PBKLAB (Message Label: ABG1S01) (System Interface)
- Verification Criteria: Verify by design review
- Verification Method: Code/Design Review
- Verification Owner: SW
- System Requirement State: Approved
- Primary Discipline: SW
- ASIL Rating: QM

#### TFDCX32348-3244: CAN Signal - PBKL_PDC (Message Label: PDC1G02) (System Interface)
- Verification Criteria: Verify by design review
- Verification Method: Code/Design Review
- Verification Owner: SW
- System Requirement State: Approved
- Primary Discipline: SW
- ASIL Rating: QM

#### TFDCX32348-3248: CAN Signal - RRBKLPDC (Message Label: PDC1G02) (System Interface)
- Verification Criteria: Verify by design review
- Verification Method: Code/Design Review
- Verification Owner: SW
- System Requirement State: Approved
- Primary Discipline: SW
- ASIL Rating: QM

#### TFDCX32348-3252: CAN Signal - RCBKLPDC (Message Label: PDC1G02) (System Interface)
- Verification Criteria: Verify by design review
- Verification Method: Code/Design Review
- Verification Owner: SW
- System Requirement State: Approved
- Primary Discipline: SW
- ASIL Rating: QM

#### TFDCX32348-3256: CAN Signal - RLBKLPDC (Message Label: PDC1G02) (System Interface)
- Verification Criteria: Verify by design review
- Verification Method: Code/Design Review
- Verification Owner: SW
- System Requirement State: Approved
- Primary Discipline: SW
- ASIL Rating: QM

#### TFDCX32348-31711: CAN Signal - CFOSW (Message Label: ZN11S19) (System Interface)
- Verification Criteria: Verify by design review
- Verification Method: Code/Design Review
- Verification Owner: SW
- System Requirement State: Approved
- Primary Discipline: SW
- ASIL Rating: QM

#### TFDCX32348-31743: CAN Signal - RL2OSW (Message Label: ZN11S19) (System Interface)
- Verification Criteria: Verify by design review
- Verification Method: Code/Design Review
- Verification Owner: SW
- System Requirement State: Approved
- Primary Discipline: SW
- ASIL Rating: QM

#### TFDCX32348-31736: CAN Signal - RR2OSW (Message Label: ZN11S19) (System Interface)
- Verification Criteria: Verify by design review
- Verification Method: Code/Design Review
- Verification Owner: SW
- System Requirement State: Approved
- Primary Discipline: SW
- ASIL Rating: QM

#### TFDCX32348-31741: CAN Signal - RC2OSW (Message Label: ZN11S19) (System Interface)
- Verification Criteria: Verify by design review
- Verification Method: Code/Design Review
- Verification Owner: SW
- System Requirement State: Approved
- Primary Discipline: SW
- ASIL Rating: QM

#### TFDCX32348-31746: CAN Signal - RR3OSW (Message Label: ZN11S19) (System Interface)
- Verification Criteria: Verify by design review
- Verification Method: Code/Design Review
- Verification Owner: SW
- System Requirement State: Approved
- Primary Discipline: SW
- ASIL Rating: QM

#### TFDCX32348-31749: CAN Signal - RC3OSW (Message Label: ZN11S19) (System Interface)
- Verification Criteria: Verify by design review
- Verification Method: Code/Design Review
- Verification Owner: SW
- System Requirement State: Approved
- Primary Discipline: SW
- ASIL Rating: QM

#### TFDCX32348-31751: CAN Signal - RL3OSW (Message Label: ZN11S19) (System Interface)
- Verification Criteria: Verify by design review
- Verification Method: Code/Design Review
- Verification Owner: SW
- System Requirement State: Approved
- Primary Discipline: SW
- ASIL Rating: QM

#### TFDCX32348-31689: CAN Signal - REVSW2 (Message Label: ZN11S26) (System Interface)
- Verification Criteria: Verify by design review
- Verification Method: Code/Design Review
- Verification Owner: SW
- System Requirement State: Approved
- Primary Discipline: SW
- ASIL Rating: QM

#### TFDCX32348-31690: CAN Signal - DBKLSW (Message Label: ZN11S26) (System Interface)
- Verification Criteria: Verify by design review
- Verification Method: Code/Design Review
- Verification Owner: SW
- System Requirement State: Approved
- Primary Discipline: SW
- ASIL Rating: QM

#### TFDCX32348-31692: CAN Signal - CFBCKL (Message Label: ZN11S26) (System Interface)
- Verification Criteria: Verify by design review
- Verification Method: Code/Design Review
- Verification Owner: SW
- System Requirement State: Approved
- Primary Discipline: SW
- ASIL Rating: QM

#### TFDCX32348-31735: CAN Signal - RR2BCKL (Message Label: ZN11S26) (System Interface)
- Verification Criteria: Verify by design review
- Verification Method: Code/Design Review
- Verification Owner: SW
- System Requirement State: Approved
- Primary Discipline: SW
- ASIL Rating: QM

#### TFDCX32348-31740: CAN Signal - CR2BCKL (Message Label: ZN11S26) (System Interface)
- Verification Criteria: Verify by design review
- Verification Method: Code/Design Review
- Verification Owner: SW
- System Requirement State: Approved
- Primary Discipline: SW
- ASIL Rating: QM

#### TFDCX32348-31742: CAN Signal - LR2BCKL (Message Label: ZN11S26) (System Interface)
- Verification Criteria: Verify by design review
- Verification Method: Code/Design Review
- Verification Owner: SW
- System Requirement State: Approved
- Primary Discipline: SW
- ASIL Rating: QM

#### TFDCX32348-31745: CAN Signal - RR3BCKL (Message Label: ZN11S26) (System Interface)
- Verification Criteria: Verify by design review
- Verification Method: Code/Design Review
- Verification Owner: SW
- System Requirement State: Approved
- Primary Discipline: SW
- ASIL Rating: QM

#### TFDCX32348-31747: CAN Signal - CR3BCKL (Message Label: ZN11S26) (System Interface)
- Verification Criteria: Verify by design review
- Verification Method: Code/Design Review
- Verification Owner: SW
- System Requirement State: Approved
- Primary Discipline: SW
- ASIL Rating: QM

#### TFDCX32348-31750: CAN Signal - LR3BCKL (Message Label: ZN11S26) (System Interface)
- Verification Criteria: Verify by design review
- Verification Method: Code/Design Review
- Verification Owner: SW
- System Requirement State: Approved
- Primary Discipline: SW
- ASIL Rating: QM

#### TFDCX32348-3259: CAN Signal - D_YEAR (Message Label: RSE1G20) (System Interface)
- Verification Criteria: Verify by design review
- Verification Method: Code/Design Review
- Verification Owner: SW
- System Requirement State: Approved
- Primary Discipline: SW
- ASIL Rating: QM

#### TFDCX32348-3261: CAN Signal - D_MONT (Message Label: RSE1G20) (System Interface)
- Verification Criteria: Verify by design review
- Verification Method: Code/Design Review
- Verification Owner: SW
- System Requirement State: Approved
- Primary Discipline: SW
- ASIL Rating: QM

#### TFDCX32348-3263: CAN Signal - D_DAY (Message Label: RSE1G20) (System Interface)
- Verification Criteria: Verify by design review
- Verification Method: Code/Design Review
- Verification Owner: SW
- System Requirement State: Approved
- Primary Discipline: SW
- ASIL Rating: QM

#### TFDCX32348-3265: CAN Signal - D_HOUR (Message Label: RSE1G20) (System Interface)
- Verification Criteria: Verify by design review
- Verification Method: Code/Design Review
- Verification Owner: SW
- System Requirement State: Approved
- Primary Discipline: SW
- ASIL Rating: QM

#### TFDCX32348-3267: CAN Signal - D_MIN (Message Label: RSE1G20) (System Interface)
- Verification Criteria: Verify by design review
- Verification Method: Code/Design Review
- Verification Owner: SW
- System Requirement State: Approved
- Primary Discipline: SW
- ASIL Rating: QM

#### TFDCX32348-3269: CAN Signal - D_SEC (Message Label: RSE1G20) (System Interface)
- Verification Criteria: Verify by design review
- Verification Method: Code/Design Review
- Verification Owner: SW
- System Requirement State: Approved
- Primary Discipline: SW
- ASIL Rating: QM

#### TFDCX32348-87003: CAN Signal - VARTRM1 (Message Label : ENG1G13) (System Interface)
- Verification Criteria: Verify by design review
- Verification Method: Code/Design Review
- Verification Owner: SW
- System Requirement State: Approved
- Primary Discipline: SW
- ASIL Rating: QM

### TFDCX32348-2553: NVM (Heading)

#### TFDCX32348-3271: NVM - NVM_SBRCustBuzzer_DRV (ON / OFF) (System Interface)
- Verification Criteria: Verify by design review
- Verification Method: Code/Design Review
- Verification Owner: SW
- System Requirement State: Approved
- Primary Discipline: SW
- ASIL Rating: QM

#### TFDCX32348-3273: NVM - NVM_SBRCustBuzzer_PSG (ON / OFF) (System Interface)
- Verification Criteria: Verify by design review
- Verification Method: Code/Design Review
- Verification Owner: SW
- System Requirement State: Approved
- Primary Discipline: SW
- ASIL Rating: QM

#### TFDCX32348-31866: NVM - NVM_SBRCustBuzzer_FCTR (ON / OFF) (System Interface)
- Verification Criteria: Verify by design review
- Verification Method: Code/Design Review
- Verification Owner: SW
- System Requirement State: Approved
- Primary Discipline: SW
- ASIL Rating: QM

#### TFDCX32348-3275: NVM - NVM_SBRCustBuzzer_RR (ON / OFF) (System Interface)
- Verification Criteria: Verify by design review
- Verification Method: Code/Design Review
- Verification Owner: SW
- System Requirement State: Approved
- Primary Discipline: SW
- ASIL Rating: QM

#### TFDCX32348-3277: NVM - NVM_SBRCustBuzzer_RC (ON / OFF) (System Interface)
- Verification Criteria: Verify by design review
- Verification Method: Code/Design Review
- Verification Owner: SW
- System Requirement State: Approved
- Primary Discipline: SW
- ASIL Rating: QM

#### TFDCX32348-3279: NVM - NVM_SBRCustBuzzer_RL (ON / OFF) (System Interface)
- Verification Criteria: Verify by design review
- Verification Method: Code/Design Review
- Verification Owner: SW
- System Requirement State: Approved
- Primary Discipline: SW
- ASIL Rating: QM

#### TFDCX32348-31879: NVM - NVM_SBRCustBuzzer_R2R (ON / OFF) (System Interface)
- Verification Criteria: Verify by design review
- Verification Method: Code/Design Review
- Verification Owner: SW
- System Requirement State: Approved
- Primary Discipline: SW
- ASIL Rating: QM

#### TFDCX32348-31880: NVM - NVM_SBRCustBuzzer_R2C (ON / OFF) (System Interface)
- Verification Criteria: Verify by design review
- Verification Method: Code/Design Review
- Verification Owner: SW
- System Requirement State: Approved
- Primary Discipline: SW
- ASIL Rating: QM

#### TFDCX32348-31881: NVM - NVM_SBRCustBuzzer_R2L (ON / OFF) (System Interface)
- Verification Criteria: Verify by design review
- Verification Method: Code/Design Review
- Verification Owner: SW
- System Requirement State: Approved
- Primary Discipline: SW
- ASIL Rating: QM

#### TFDCX32348-31882: NVM - NVM_SBRCustBuzzer_R3R (ON / OFF) (System Interface)
- Verification Criteria: Verify by design review
- Verification Method: Code/Design Review
- Verification Owner: SW
- System Requirement State: Approved
- Primary Discipline: SW
- ASIL Rating: QM

#### TFDCX32348-31883: NVM - NVM_SBRCustBuzzer_R3C (ON / OFF) (System Interface)
- Verification Criteria: Verify by design review
- Verification Method: Code/Design Review
- Verification Owner: SW
- System Requirement State: Approved
- Primary Discipline: SW
- ASIL Rating: QM

#### TFDCX32348-31884: NVM - NVM_SBRCustBuzzer_R3L (ON / OFF) (System Interface)
- Verification Criteria: Verify by design review
- Verification Method: Code/Design Review
- Verification Owner: SW
- System Requirement State: Approved
- Primary Discipline: SW
- ASIL Rating: QM

#### TFDCX32348-88149: NVM - NVM_SBRMtState (System Interface)
- Verification Criteria: Verify by design review
- Verification Method: Code/Design Review
- Verification Owner: SW
- System Requirement State: Approved
- Primary Discipline: SW
- ASIL Rating: QM

### TFDCX32348-40934: MCUCONST (Heading)

#### TFDCX32348-87261: MCUCONST - MCUID0024 (System Interface)
MCUCONST - MCUID0024
Meaning: Brand
Range : 0[Toyota(Including GR)], 1[Lexus], 2[Subaru]
- Verification Criteria: Verify by design review
- Verification Method: Code/Design Review
- Verification Owner: SW
- System Requirement State: Approved
- Primary Discipline: SW
- ASIL Rating: QM

#### TFDCX32348-33012: MCUCONST - MCUID0224 (System Interface)
MCUCONST - MCUID0224
Description: ODS availability for RR seat.
Type: UINT8
Range: 0 (without ODS), 1 (with ODS)
- Verification Criteria: Verify by design review
- Verification Method: Code/Design Review
- Verification Owner: SW
- System Requirement State: Approved
- Primary Discipline: SW
- ASIL Rating: QM

#### TFDCX32348-33014: MCUCONST - MCUID0225 (System Interface)
MCUCONST - MCUID0225
Description: ODS availability for RC seat.
Type: UINT8
Range: 0 (without ODS), 1 (with ODS)
- Verification Criteria: Verify by design review
- Verification Method: Code/Design Review
- Verification Owner: SW
- System Requirement State: Approved
- Primary Discipline: SW
- ASIL Rating: QM

#### TFDCX32348-33015: MCUCONST - MCUID0226 (System Interface)
MCUCONST - MCUID0226
Description: ODS availability for RL seat.
Type: UINT8
Range: 0 (without ODS), 1 (with ODS)
- Verification Criteria: Verify by design review
- Verification Method: Code/Design Review
- Verification Owner: SW
- System Requirement State: Approved
- Primary Discipline: SW
- ASIL Rating: QM

#### TFDCX32348-33016: MCUCONST - MCUID0227 (System Interface)
MCUCONST - MCUID0227
Description: ODS availability for R2R seat.
Type: UINT8
Range: 0 (without ODS), 1 (with ODS)
- Verification Criteria: Verify by design review
- Verification Method: Code/Design Review
- Verification Owner: SW
- System Requirement State: Approved
- Primary Discipline: SW
- ASIL Rating: QM

#### TFDCX32348-33017: MCUCONST - MCUID0228 (System Interface)
MCUCONST - MCUID0228
Description: ODS availability for R2C seat.
Type: UINT8
Range: 0 (without ODS), 1 (with ODS)
- Verification Criteria: Verify by design review
- Verification Method: Code/Design Review
- Verification Owner: SW
- System Requirement State: Approved
- Primary Discipline: SW
- ASIL Rating: QM

#### TFDCX32348-33018: MCUCONST - MCUID0229 (System Interface)
MCUCONST - MCUID0229
Description: ODS availability for R2L seat.
Type: UINT8
Range: 0 (without ODS), 1 (with ODS)
- Verification Criteria: Verify by design review
- Verification Method: Code/Design Review
- Verification Owner: SW
- System Requirement State: Approved
- Primary Discipline: SW
- ASIL Rating: QM

#### TFDCX32348-33019: MCUCONST - MCUID0230 (System Interface)
MCUCONST - MCUID0230
Description: ODS availability for R3R seat.
Type: UINT8
Range: 0 (without ODS), 1 (with ODS)
- Verification Criteria: Verify by design review
- Verification Method: Code/Design Review
- Verification Owner: SW
- System Requirement State: Approved
- Primary Discipline: SW
- ASIL Rating: QM

#### TFDCX32348-33020: MCUCONST - MCUID0231 (System Interface)
MCUCONST - MCUID0231
Description: ODS availability for R3C seat.
Type: UINT8
Range: 0 (without ODS), 1 (with ODS)
- Verification Criteria: Verify by design review
- Verification Method: Code/Design Review
- Verification Owner: SW
- System Requirement State: Approved
- Primary Discipline: SW
- ASIL Rating: QM

#### TFDCX32348-33021: MCUCONST - MCUID0232 (System Interface)
MCUCONST - MCUID0232
Description: ODS availability for R3L seat.
Type: UINT8
Range: 0 (without ODS), 1 (with ODS)
- Verification Criteria: Verify by design review
- Verification Method: Code/Design Review
- Verification Owner: SW
- System Requirement State: Approved
- Primary Discipline: SW
- ASIL Rating: QM

#### TFDCX32348-33023: MCUCONST - MCUID0233 (System Interface)
MCUCONST - MCUID0233
Description: Rear doors availability.
Type: UINT8
Range: 0 (not available), 1 (available)
- Verification Criteria: Verify by design review
- Verification Method: Code/Design Review
- Verification Owner: SW
- System Requirement State: Approved
- Primary Discipline: SW
- ASIL Rating: QM

#### TFDCX32348-33025: MCUCONST - MCUID0234 (System Interface)
MCUCONST - MCUID0234
Description: Front-Rear seats walkthrough availability.
Type: UINT8
Range: 0 (not available), 1 (available)
- Verification Criteria: Verify by design review
- Verification Method: Code/Design Review
- Verification Owner: SW
- System Requirement State: Approved
- Primary Discipline: SW
- ASIL Rating: QM

#### TFDCX32348-33029: MCUCONST - MCUID0592 (Dropped) (System Interface)
MCUCONST - MCUID0592 (Dropped)
Description: Rear seat belt indicator type.
Type: UINT8
Range: 0 (rear 1 row with 3 seats), 1 (rear 1 row with 2 seats), 2 (rear 2 row)
- Verification Criteria: Verify by design review
- Verification Method: Code/Design Review
- Verification Owner: SW
- System Requirement State: Approved
- Primary Discipline: SW
- ASIL Rating: QM

#### TFDCX32348-33034: MCUCONST - MCUID0603 <Dropped> (System Interface)
MCUCONST - MCUID0603 <Dropped>
Description: Seat belt reminder control parameter selection for North America, Canada, Middle East.
Type: UINT8
Range: 0 (Group A: North America/GCC), 1 (Group B: EUR/AUS/GeneralEUR/AUS/General), 2 (Group C: China)
- Verification Criteria: Verify by design review
- Verification Method: Code/Design Review
- Verification Owner: SW
- System Requirement State: Approved
- Primary Discipline: SW
- ASIL Rating: QM

#### TFDCX32348-33065: MCUCONST - MCUID0604 (System Interface)
MCUCONST - MCUID0604
Description: Seat belt reminder control parameter selection for Mexico.
Type: UINT8
Range: 0 (Group A: North America/GCC), 1 (Group B: EUR/AUS/GeneralEUR/AUS/General), 2 (Group C: China)
- Verification Criteria: Verify by design review
- Verification Method: Code/Design Review
- Verification Owner: SW
- System Requirement State: Approved
- Primary Discipline: SW
- ASIL Rating: QM

#### TFDCX32348-33066: MCUCONST - MCUID0605 (System Interface)
MCUCONST - MCUID0605
Description: Seat belt reminder control parameter selection for General Export, UK, Europe, South Africa, Japan, India, Taiwan, Hong Kong/Macau/Singapore, Australia.
Type: UINT8
Range: 0 (Group A: North America/GCC), 1 (Group B: EUR/AUS/GeneralEUR/AUS/General), 2 (Group C: China)
- Verification Criteria: Verify by design review
- Verification Method: Code/Design Review
- Verification Owner: SW
- System Requirement State: Approved
- Primary Discipline: SW
- ASIL Rating: QM

#### TFDCX32348-33091: MCUCONST - MCUID0606 (System Interface)
MCUCONST - MCUID0606
Description: Seat belt reminder control parameter selection for Korea.
Type: UINT8
Range: 0 (Group A: North America/GCC), 1 (Group B: EUR/AUS/GeneralEUR/AUS/General), 2 (Group C: China)
- Verification Criteria: Verify by design review
- Verification Method: Code/Design Review
- Verification Owner: SW
- System Requirement State: Approved
- Primary Discipline: SW
- ASIL Rating: QM

#### TFDCX32348-33093: MCUCONST - MCUID0607 (System Interface)
MCUCONST - MCUID0607
Description: Seat belt reminder control parameter selection for China.
Type: UINT8
Range: 0 (Group A: North America/GCC), 1 (Group B: EUR/AUS/GeneralEUR/AUS/General), 2 (Group C: China)
- Verification Criteria: Verify by design review
- Verification Method: Code/Design Review
- Verification Owner: SW
- System Requirement State: Approved
- Primary Discipline: SW
- ASIL Rating: QM

#### TFDCX32348-87250: MCUCONST - MCUID1135 (System Interface)
MCUCONST - MCUID1135
Description: Legally required buzzer/indicator (seatbelt reminder) for North America
Type: UINT8
Range: 0 = North America/GCC, 1 = Europe/Australia/Japan, 2 = China
- Verification Criteria: Verify by design review
- Verification Method: Code/Design Review
- Verification Owner: SW
- System Requirement State: Approved
- Primary Discipline: SW
- ASIL Rating: QM

#### TFDCX32348-87251: MCUCONST - MCUID1136 (System Interface)
MCUCONST - MCUID1136
Description: Legally required buzzer/indicator (seatbelt reminder) for Canada/Middle-East
Type: UINT8
Range: 0 = North America/GCC, 1 = Europe/Australia/Japan, 2 = China
- Verification Criteria: Verify by design review
- Verification Method: Code/Design Review
- Verification Owner: SW
- System Requirement State: Approved
- Primary Discipline: SW
- ASIL Rating: QM

#### TFDCX32348-87009: MCUCONST - MCUID1137 (System Interface)
MCUCONST - MCUID1137
Description: Presence of New FMVSS applied or not
Type: UINT8
Range: 0=Other than New FMVSS208, 1=New FMVSS208
- Verification Criteria: Verify by design review
- Verification Method: Code/Design Review
- Verification Owner: SW
- System Requirement State: Approved
- Primary Discipline: SW
- ASIL Rating: QM

#### TFDCX32348-87008: MCUCONST - MCUID1138 (System Interface)
MCUCONST - MCUID1138
Description: Seatbelt reminder telltale type
Type: UINT8
Range: 0 = rear 1st row + no center seat, 1 = rear 1st row + center seat, 2 = rear 2nd row, 3 = no rear seat
- Verification Criteria: Verify by design review
- Verification Method: Code/Design Review
- Verification Owner: SW
- System Requirement State: Approved
- Primary Discipline: SW
- ASIL Rating: QM

### TFDCX32348-2555: Function Entry (Heading)

#### TFDCX32348-3281: Function Entry - fn_reset_ABGDRV_existence() (System Interface)
- Verification Criteria: Verify by design review
- Verification Method: Code/Design Review
- Verification Owner: SW
- System Requirement State: Approved
- Primary Discipline: SW
- ASIL Rating: QM

#### TFDCX32348-3283: Function Entry - fn_reset_ABGPSG_existence() (System Interface)
- Verification Criteria: Verify by design review
- Verification Method: Code/Design Review
- Verification Owner: SW
- System Requirement State: Approved
- Primary Discipline: SW
- ASIL Rating: QM

#### TFDCX32348-114249: Function Entry - fn_reset_Mtjudg_existence() (System Interface)
- Verification Criteria: Verify by design review
- Verification Method: Code/Design Review
- Verification Owner: SW
- System Requirement State: Approved
- Primary Discipline: SW
- ASIL Rating: QM

## TFDCX32348-951: Output Requirements (Heading)

### TFDCX32348-2557: Buzzer (Heading)

#### TFDCX32348-3284: BZR - SBR_Legally_Required_BUZZER (System Interface)
- Verification Criteria: Verify by design review
- Verification Method: Code/Design Review
- Verification Owner: SW
- System Requirement State: Approved
- Primary Discipline: SW
- ASIL Rating: QM

#### TFDCX32348-3286: BZR - SBR_Level2_BUZZER (System Interface)
- Verification Criteria: Verify by design review
- Verification Method: Code/Design Review
- Verification Owner: SW
- System Requirement State: Approved
- Primary Discipline: SW
- ASIL Rating: QM

#### TFDCX32348-3288: BZR - SBR_Level1_BUZZER (System Interface)
- Verification Criteria: Verify by design review
- Verification Method: Code/Design Review
- Verification Owner: SW
- System Requirement State: Approved
- Primary Discipline: SW
- ASIL Rating: QM

#### TFDCX32348-3290: BZR - SBR_Unbuckled_Notify_BUZZER (System Interface)
- Verification Criteria: Verify by design review
- Verification Method: Code/Design Review
- Verification Owner: SW
- System Requirement State: Approved
- Primary Discipline: SW
- ASIL Rating: QM

### TFDCX32348-2559: Telltale (Heading)

#### TFDCX32348-3292: HMI - SBRTelltale_DRV (System Interface)
HMI - SBRTelltale_DRV
Range: {OFF, ON}
Note: On/Off timing for Lv1/Lv2-Blink is controlled in the application side.
- Verification Criteria: Verify by design review
- Verification Method: Code/Design Review
- Verification Owner: SW
- System Requirement State: Approved
- Primary Discipline: SW
- ASIL Rating: QM

#### TFDCX32348-92431: HMI - SBRTelltale_PSG (System Interface)
HMI - SBRTelltale_PSG
Range: {OFF, ON}
Note: On/Off timing for Lv1/Lv2-Blink is controlled in the application side.
- Verification Criteria: Verify by design review
- Verification Method: Code/Design Review
- Verification Owner: SW
- System Requirement State: Approved
- Primary Discipline: SW
- ASIL Rating: QM

#### TFDCX32348-35190: Internal Signal - SBRTTStatus (System Interface)
Internal Signal - SBRTTStatus
Range: {OFF, ON, Lv1-Blink, Lv2-Blink}
Note: This output is used to turn ON the TFT backlight.
- Verification Criteria: Verify by design review
- Verification Method: Code/Design Review
- Verification Owner: SW
- System Requirement State: Approved
- Primary Discipline: SW
- ASIL Rating: QM

#### TFDCX32348-3204: HMI - SBRTelltale_RL (System Interface)
HMI - SBRTelltale_RL
Range: {OFF, ON, Lv1-Blink, Lv2-Blink}
Note: On/Off timing for Lv1/Lv2-Blink is controlled in the application side.
- Verification Criteria: Verify by design review
- Verification Method: Code/Design Review
- Verification Owner: SW
- System Requirement State: Approved
- Primary Discipline: SW
- ASIL Rating: QM

#### TFDCX32348-3206: HMI - SBRTelltale_RC (System Interface)
HMI - SBRTelltale_RC
Range: {OFF, ON, Lv1-Blink, Lv2-Blink}
Note: On/Off timing for Lv1/Lv2-Blink is controlled in the application side.
- Verification Criteria: Verify by design review
- Verification Method: Code/Design Review
- Verification Owner: SW
- System Requirement State: Approved
- Primary Discipline: SW
- ASIL Rating: QM

#### TFDCX32348-3208: HMI - SBRTelltale_RR (System Interface)
HMI - SBRTelltale_RR
Range: {OFF, ON, Lv1-Blink, Lv2-Blink}
Note: On/Off timing for Lv1/Lv2-Blink is controlled in the application side.
- Verification Criteria: Verify by design review
- Verification Method: Code/Design Review
- Verification Owner: SW
- System Requirement State: Approved
- Primary Discipline: SW
- ASIL Rating: QM

#### TFDCX32348-32995: HMI - SBRTelltale_R2L (System Interface)
HMI - SBRTelltale_R2L
Range: {OFF, ON}
Note: On/Off timing for Lv1/Lv2-Blink is controlled in the application side.
- Verification Criteria: Verify by design review
- Verification Method: Code/Design Review
- Verification Owner: SW
- System Requirement State: Approved
- Primary Discipline: SW
- ASIL Rating: QM

#### TFDCX32348-32996: HMI - SBRTelltale_R2C (System Interface)
HMI - SBRTelltale_R2C
Range: {OFF, ON}
Note: On/Off timing for Lv1/Lv2-Blink is controlled in the application side.
- Verification Criteria: Verify by design review
- Verification Method: Code/Design Review
- Verification Owner: SW
- System Requirement State: Approved
- Primary Discipline: SW
- ASIL Rating: QM

#### TFDCX32348-32997: HMI - SBRTelltale_R2R (System Interface)
HMI - SBRTelltale_R2R
Range: {OFF, ON}
Note: On/Off timing for Lv1/Lv2-Blink is controlled in the application side.
- Verification Criteria: Verify by design review
- Verification Method: Code/Design Review
- Verification Owner: SW
- System Requirement State: Approved
- Primary Discipline: SW
- ASIL Rating: QM

#### TFDCX32348-32998 (System Interface)
HMI - SBRTelltale_R3L (reserved for future use)
Range: {OFF, ON}
Note: On/Off timing for Lv1/Lv2-Blink is controlled in the application side.
- Verification Criteria: Verify by design review
- Verification Method: Code/Design Review
- Verification Owner: SW
- System Requirement State: Approved
- Primary Discipline: SW
- ASIL Rating: QM

#### TFDCX32348-32999 (System Interface)
HMI - SBRTelltale_R3C (reserved for future use)
Range: {OFF, ON}
Note: On/Off timing for Lv1/Lv2-Blink is controlled in the application side.
- Verification Criteria: Verify by design review
- Verification Method: Code/Design Review
- Verification Owner: SW
- System Requirement State: Approved
- Primary Discipline: SW
- ASIL Rating: QM

#### TFDCX32348-33000 (System Interface)
HMI - SBRTelltale_R3R (reserved for future use)
Range: {OFF, ON}
Note: On/Off timing for Lv1/Lv2-Blink is controlled in the application side.
- Verification Criteria: Verify by design review
- Verification Method: Code/Design Review
- Verification Owner: SW
- System Requirement State: Approved
- Primary Discipline: SW
- ASIL Rating: QM

#### TFDCX32348-34620: HMI - SBRBlinkStatus (System Interface)
HMI - SBRBlinkStatus
Range: {OFF, ON}
Note: This output is set to ON when any of the rear seat belt indicatior is not OFF. (Used to display the rear belt indicator frame.)
- Verification Criteria: Verify by design review
- Verification Method: Code/Design Review
- Verification Owner: SW
- System Requirement State: Approved
- Primary Discipline: SW
- ASIL Rating: QM

#### TFDCX32348-33002: HMI - RearBeltIndType (System Interface)
HMI - RearBeltIndType
Range: { BELT_233_294, BELT_233_235, BELT_233_XXX, BELT_233_NONE, BELT_401, BELT_402, BELT_403}
- Verification Criteria: Verify by design review
- Verification Method: Code/Design Review
- Verification Owner: SW
- System Requirement State: Approved
- Primary Discipline: SW
- ASIL Rating: QM

### TFDCX32348-2561: CAN (Heading)

#### TFDCX32348-3210 (System Interface)
CAN Signal - DSWN (Message Label: MET1S03) (Dropped)
- Verification Criteria: Verify by design review
- Verification Method: Code/Design Review
- Verification Owner: SW
- System Requirement State: Rejected
- Primary Discipline: SW
- ASIL Rating: QM

#### TFDCX32348-3212: CAN Signal - PSWN (Message Label: MET1S01) (Dropped) (System Interface)
- Verification Criteria: Verify by design review
- Verification Method: Code/Design Review
- Verification Owner: SW
- System Requirement State: Rejected
- Primary Discipline: SW
- ASIL Rating: QM

#### TFDCX32348-3214: CAN Signal - DBKL_MET (Message Label: MET1S47) (System Interface)
- Verification Criteria: Verify by design review
- Verification Method: Code/Design Review
- Verification Owner: SW
- System Requirement State: Approved
- Primary Discipline: SW
- ASIL Rating: QM

#### TFDCX32348-3216: CAN Signal - PBKL_MET (Message Label: MET1S47) (System Interface)
- Verification Criteria: Verify by design review
- Verification Method: Code/Design Review
- Verification Owner: SW
- System Requirement State: Approved
- Primary Discipline: SW
- ASIL Rating: QM

#### TFDCX32348-3218: CAN Signal - RLBKLMET (Message Label: MET1S47) (System Interface)
- Verification Criteria: Verify by design review
- Verification Method: Code/Design Review
- Verification Owner: SW
- System Requirement State: Approved
- Primary Discipline: SW
- ASIL Rating: QM

#### TFDCX32348-3220: CAN Signal - RCBKLMET (Message Label: MET1S47) (System Interface)
- Verification Criteria: Verify by design review
- Verification Method: Code/Design Review
- Verification Owner: SW
- System Requirement State: Approved
- Primary Discipline: SW
- ASIL Rating: QM

#### TFDCX32348-3222: CAN Signal - RRBKLMET (Message Label: MET1S47) (System Interface)
- Verification Criteria: Verify by design review
- Verification Method: Code/Design Review
- Verification Owner: SW
- System Requirement State: Approved
- Primary Discipline: SW
- ASIL Rating: QM

#### TFDCX32348-31849: CAN Signal - BKL3LMET (Message Label: MET1S47) (System Interface)
- Verification Criteria: Verify by design review
- Verification Method: Code/Design Review
- Verification Owner: SW
- System Requirement State: Approved
- Primary Discipline: SW
- ASIL Rating: QM

#### TFDCX32348-31850: CAN Signal - BKL3CMET (Message Label: MET1S47) (System Interface)
- Verification Criteria: Verify by design review
- Verification Method: Code/Design Review
- Verification Owner: SW
- System Requirement State: Approved
- Primary Discipline: SW
- ASIL Rating: QM

#### TFDCX32348-31851: CAN Signal - BKL3RMET (Message Label: MET1S47) (System Interface)
- Verification Criteria: Verify by design review
- Verification Method: Code/Design Review
- Verification Owner: SW
- System Requirement State: Approved
- Primary Discipline: SW
- ASIL Rating: QM

### TFDCX32348-31852: CXPI (Heading)

#### TFDCX32348-31853: CXPI Signal - RRTT (Message Label: CXMET1S02) (System Interface)
- Verification Criteria: Verify by design review
- Verification Method: Code/Design Review
- Verification Owner: SW
- System Requirement State: Approved
- Primary Discipline: SW
- ASIL Rating: QM

#### TFDCX32348-31854: CXPI Signal - RCTT (Message Label: CXMET1S02) (System Interface)
- Verification Criteria: Verify by design review
- Verification Method: Code/Design Review
- Verification Owner: SW
- System Requirement State: Approved
- Primary Discipline: SW
- ASIL Rating: QM

#### TFDCX32348-31855: CXPI Signal - RLTT (Message Label: CXMET1S02) (System Interface)
- Verification Criteria: Verify by design review
- Verification Method: Code/Design Review
- Verification Owner: SW
- System Requirement State: Approved
- Primary Discipline: SW
- ASIL Rating: QM

#### TFDCX32348-31856: CXPI Signal - RR2TT (Message Label: CXMET1S02) (System Interface)
- Verification Criteria: Verify by design review
- Verification Method: Code/Design Review
- Verification Owner: SW
- System Requirement State: Approved
- Primary Discipline: SW
- ASIL Rating: QM

#### TFDCX32348-31857: CXPI Signal - RC2TT (Message Label: CXMET1S02) (System Interface)
- Verification Criteria: Verify by design review
- Verification Method: Code/Design Review
- Verification Owner: SW
- System Requirement State: Approved
- Primary Discipline: SW
- ASIL Rating: QM

#### TFDCX32348-31858: CXPI Signal - RL2TT (Message Label: CXMET1S02) (System Interface)
- Verification Criteria: Verify by design review
- Verification Method: Code/Design Review
- Verification Owner: SW
- System Requirement State: Approved
- Primary Discipline: SW
- ASIL Rating: QM

#### TFDCX32348-31859: CXPI Signal - RR3TT (Message Label: CXMET1S02) (System Interface)
- Verification Criteria: Verify by design review
- Verification Method: Code/Design Review
- Verification Owner: SW
- System Requirement State: Approved
- Primary Discipline: SW
- ASIL Rating: QM

#### TFDCX32348-31860: CXPI Signal - RC3TT (Message Label: CXMET1S02) (System Interface)
- Verification Criteria: Verify by design review
- Verification Method: Code/Design Review
- Verification Owner: SW
- System Requirement State: Approved
- Primary Discipline: SW
- ASIL Rating: QM

#### TFDCX32348-31861: CXPI Signal - RL3TT (Message Label: CXMET1S02) (System Interface)
- Verification Criteria: Verify by design review
- Verification Method: Code/Design Review
- Verification Owner: SW
- System Requirement State: Approved
- Primary Discipline: SW
- ASIL Rating: QM

#### TFDCX32348-31862: CXPI Signal - REARINDI (Message Label: CXMET1S02) (System Interface)
- Verification Criteria: Verify by design review
- Verification Method: Code/Design Review
- Verification Owner: SW
- System Requirement State: Approved
- Primary Discipline: SW
- ASIL Rating: QM

### TFDCX32348-2563: DIAG (Heading)

#### TFDCX32348-3225 (System Interface)
Internal Signal - SeatBeltReminderLogs[80]
Description : This array data can be used for #4 to #83 as it is to response DID$11A2 of Read Data By Identifier service.
Type : UINT8 array.
Range : Each data byte conforms $11A2 response format.
Note : This data is stored into backup RAM.
- Verification Criteria: Verify by design review
- Verification Method: Code/Design Review
- Verification Owner: SW
- System Requirement State: Approved
- Primary Discipline: SW
- ASIL Rating: QM

### TFDCX32348-96195: Internal Signal (Heading)

#### TFDCX32348-96196: Internal Signal - Destination Group (System Interface)
Internal Signal - Destination Group
Description : This is define the destination group for seat belt.
Type : UINT8.
Range :
A: North America/GCC - Toyota
B: EUR/AUS/General - Toyota
C: China - Toyota
D: North America/GCC - Lexus
E: EUR/AUS/General - Lexus
F: China - Lexus
G: North America(New FMVSS208) - Toyota
H: North America(New FMVSS208) - Lexus
- Verification Criteria: Verify by design review
- Verification Method: Code/Design Review
- Verification Owner: SW
- System Requirement State: Approved
- Primary Discipline: SW
- ASIL Rating: QM

## TFDCX32348-953: Performance Requirements (Heading)

### TFDCX32348-2565: Constant Parameter (Heading)

#### TFDCX32348-97073: Judgment the Destination for legal items (System Requirement)
Judgment the Destination for legal items
| # | Input | Output | Remarks |
| --- | --- | --- | --- |
| # | InternalSignal - DESTID0020 | CountryCodeFunc0 | Remarks |
| 1 | 0[North America/GCC] | 1[North America] |  |
| 2 | 1[Europe/Australia/Japan] | 7[Middle East Asia] |  |
| 3 | 2[China] | 12[China] |  |
| 4 | 255[Undetermined] | Internal Signal - CountryCodeFunc |  |
- Verification Criteria: Verify by executing test cases
- Verification Method: Code/Design Review, System Qualification Test
- Verification Owner: FV
- System Requirement State: Approved
- Primary Discipline: SW
- ASIL Rating: QM

#### TFDCX32348-3227: Destination Group [Toyota parameters] (System Requirement)
Destination Group [Toyota parameters]
Based on 'Destination Group' determined in this table, the constant parameters should be chosen in the following artifacts.
if MCUCONST - MCUID0024 = other than 1 (Brand : Toyota, Subaru)
(Lexus parameter are information for #2 meter. Once #5 meter will be applied, meter should switch the Toyota or Lexus brand control by MCUID0024.)
| # | Input |  |  |  |  |  |  | Output | Remarks |
| --- | --- | --- | --- | --- | --- | --- | --- | --- | --- |
| # | CountryCodeFunc0 | MCUCONST - MCUID0604 | MCUCONST - MCUID0605 | MCUCONST - MCUID0606 | MCUCONST - MCUID0607 | MCUCONST - MCUID1135 | MCUCONST - MCUID1136 | Destination Group0 | Remarks |
| 1 | 1[North America] | X | X | X | X | 0 | X | A | North America/GCC |
| 2 | 1[North America] | X | X | X | X | 1 | X | B | EUR/AUS/General |
| 3 | 1[North America] | X | X | X | X | 2 | X | C | China |
| 4 | 0[Canada] or 7[Middle East Asia] | X | X | X | X | X | 0 | A | North America/GCC |
| 5 | 0[Canada] or 7[Middle East Asia] | X | X | X | X | X | 1 | B | EUR/AUS/General |
| 6 | 0[Canada] or 7[Middle East Asia] | X | X | X | X | X | 2 | C | China |
| 7 | 2[Mexico] | 0 | X | X | X | X | X | A | North America/GCC |
| 8 | 2[Mexico] | 1 | X | X | X | X | X | B | EUR/AUS/General |
| 9 | 2[Mexico] | 2 | X | X | X | X | X | C | China |
| 10 | 3[General Export] or 4[UK] or 5[Europe] or 6[South Africa] or 8[Japan] or 9[India] or 11[Taiwan] or 13[Hong Kong/Macau/Singapore] or 14[Australia] | X | 0 | X | X | X | X | A | North America/GCC |
| 11 | 3[General Export] or 4[UK] or 5[Europe] or 6[South Africa] or 8[Japan] or 9[India] or 11[Taiwan] or 13[Hong Kong/Macau/Singapore] or 14[Australia] | X | 1 | X | X | X | X | B | EUR/AUS/General |
| 12 | 3[General Export] or 4[UK] or 5[Europe] or 6[South Africa] or 8[Japan] or 9[India] or 11[Taiwan] or 13[Hong Kong/Macau/Singapore] or 14[Australia] | X | 2 | X | X | X | X | C | China |
| 13 | 10[Korea] | X | X | 0 | X | X | X | A | North America/GCC |
| 14 | 10[Korea] | X | X | 1 | X | X | X | B | EUR/AUS/General |
| 15 | 10[Korea] | X | X | 2 | X | X | X | C | China |
| 16 | 12[China] | X | X | X | 0 | X | X | A | North America/GCC |
| 17 | 12[China] | X | X | X | 1 | X | X | B | EUR/AUS/General |
| 18 | 12[China] | X | X | X | 2 | X | X | C | China |
- Verification Criteria: Verify by executing test cases
- Verification Method: Code/Design Review, System Qualification Test
- Verification Owner: FV
- System Requirement State: Approved
- Primary Discipline: SW
- ASIL Rating: QM

##### TFDCX32348-95458: Destination Group - judgment (System Requirement)
Destination Group - judgment
if MCUCONST - MCUID0024 = other than 1 (Brand : Toyota, Subaru)
(Lexus parameter are information for #2 meter. Once #5 meter will be applied, meter should switch the Toyota or Lexus brand control by MCUID0024.)
| # | Input |  | Output |
| --- | --- | --- | --- |
| # | Destination Group0 | MCUCONST - MCUID1137 | Internal Signal - Destination Group (*1) |
| 1 | A | 1 | G |
| 2 | A | Other than 1 | A |
| 3 | B | X | B |
| 4 | C | X | C |
*1: If Destination Group changes during IgnMode is ON, all flags, etc., must be cleared equivalent to turning +B OFF to ON, and measures must be taken to prevent state fixation due to state transition switching.
- Verification Criteria: Verify by executing test cases
- Verification Method: Code/Design Review, System Qualification Test
- Verification Owner: FV
- System Requirement State: Approved
- Primary Discipline: SW
- ASIL Rating: QM

#### TFDCX32348-92456: Destination Group [Lexus parameters] (System Requirement)
Destination Group [Lexus parameters]
Lexus parameters are applied to Visteon #5 meter, #2 meter are not applied. Therefore not officially supported currently.
Based on 'Destination Group' determined in this table, the constant parameters should be chosen in the following artifacts.
if MCUCONST - MCUID0024 = 1 (Brand : Lexus)
| # | Input |  |  |  |  |  |  | Output | Remarks |
| --- | --- | --- | --- | --- | --- | --- | --- | --- | --- |
| # | CountryCodeFunc0 | MCUCONST - MCUID0604 | MCUCONST - MCUID0605 | MCUCONST - MCUID0606 | MCUCONST - MCUID0607 | MCUCONST - MCUID1135 | MCUCONST - MCUID1136 | Destination Group0 | Remarks |
| 1 | 1[North America] | X | X | X | X | 0 | X | D | North America/GCC |
| 2 | 1[North America] | X | X | X | X | 1 | X | E | EUR/AUS/General |
| 3 | 1[North America] | X | X | X | X | 2 | X | F | China |
| 4 | 0[Canada] or 7[Middle East Asia] | X | X | X | X | X | 0 | D | North America/GCC |
| 5 | 0[Canada] or 7[Middle East Asia] | X | X | X | X | X | 1 | E | EUR/AUS/General |
| 6 | 0[Canada] or 7[Middle East Asia] | X | X | X | X | X | 2 | F | China |
| 7 | 2[Mexico] | 0 | X | X | X | X | X | D | North America/GCC |
| 8 | 2[Mexico] | 1 | X | X | X | X | X | E | EUR/AUS/General |
| 9 | 2[Mexico] | 2 | X | X | X | X | X | F | China |
| 10 | 3[General Export] or 4[UK] or 5[Europe] or 6[South Africa] or 8[Japan] or 9[India] or 11[Taiwan] or 13[Hong Kong/Macau/Singapore] or 14[Australia] | X | 0 | X | X | X | X | D | North America/GCC |
| 11 | 3[General Export] or 4[UK] or 5[Europe] or 6[South Africa] or 8[Japan] or 9[India] or 11[Taiwan] or 13[Hong Kong/Macau/Singapore] or 14[Australia] | X | 1 | X | X | X | X | E | EUR/AUS/General |
| 12 | 3[General Export] or 4[UK] or 5[Europe] or 6[South Africa] or 8[Japan] or 9[India] or 11[Taiwan] or 13[Hong Kong/Macau/Singapore] or 14[Australia] | X | 2 | X | X | X | X | F | China |
| 13 | 10[Korea] | X | X | 0 | X | X | X | D | North America/GCC |
| 14 | 10[Korea] | X | X | 1 | X | X | X | E | EUR/AUS/General |
| 15 | 10[Korea] | X | X | 2 | X | X | X | F | China |
| 16 | 12[China] | X | X | X | 0 | X | X | D | North America/GCC |
| 17 | 12[China] | X | X | X | 1 | X | X | E | EUR/AUS/General |
| 18 | 12[China] | X | X | X | 2 | X | X | F | China |
- Verification Criteria: Verify by executing test cases
- Verification Method: Code/Design Review, System Qualification Test
- Verification Owner: FV
- System Requirement State: Approved
- Primary Discipline: SW
- ASIL Rating: QM

##### TFDCX32348-92455 (System Requirement)
Destination Group - judgment for New FMVSS [Lexus parameters]
Lexus parameters are applied to Visteon #5 meter, #2 meter are not applied. Therefore not officially supported currently.
if MCUCONST - MCUID0024 = 1 (Brand : Lexus)
| # | Input |  | Output |
| --- | --- | --- | --- |
| # | Destination Group0 | MCUCONST - MCUID1137 | Internal Signal - Destination Group (*1) |
| 1 | D | 1 | H |
| 2 | D | Other than 1 | D |
| 3 | E | X | E |
| 4 | F | X | F |
*1: If Destination Group changes during IgnMode is ON, all flags, etc., must be cleared equivalent to turning +B OFF to ON, and measures must be taken to prevent state fixation due to state transition switching.
- Verification Criteria: Verify by executing test cases
- Verification Method: Code/Design Review, System Qualification Test
- Verification Owner: FV
- System Requirement State: Approved
- Primary Discipline: SW
- ASIL Rating: QM

#### TFDCX32348-3233: Vehicle Equipment (System Requirement)
Dropped (Availability judgements were split into judgements for each item)
Vehicle Equipment
|  | Param. Description | Param. Name | Destination Group A |  | Destination Group B |  | Destination Group C (*3) |
| --- | --- | --- | --- | --- | --- | --- | --- |
|  | Param. Description | Param. Name | North America | GCC | Taiwan (*1) WITHOUT_ODS | Except 'Taiwan' WITH_ODS | Destination Group C (*3) |
| 1 | Rear seat ODS availability (*4) | - | Yes No | No | No | Yes | (TBD) |
| 2 | Rear doors availability | - | Yes |  | Yes |  | Yes |
| 3 | Fr-Rr seat walkthrough availability | - | No |  | No |  | No |
(*1) CountryCode is '721h'.
Group B has been separated into two sub-groups with or without ODS.
(*2) As an assumption until No.1 value for North America & China is defined, 'Yes' can be considered for '(TBD)' (Ref: Impediment 1641740).
(*3) No applicable CountryCode for now.
(*4) Customer spec reference for Rear seat ODS availability: MET-M_COUNTRYCODE-CSTD-0.
- Verification Criteria: Verify by executing test cases
- Verification Method: Code/Design Review, System Qualification Test
- Verification Owner: FV
- System Requirement State: Rejected
- Primary Discipline: SW
- ASIL Rating: QM

#### TFDCX32348-32201 (System Requirement)
Rear 1st Row Seat ODS Availability Determination
ODS availability of rear 1st row right seat
| # | Input | Output | Remarks |
| --- | --- | --- | --- |
| # | MCUCONST - MCUID0224 | Internal Parameter - RR_ODS_Availability | Remarks |
| 1 | 0 | No | ODS not available |
| 2 | 1 | Yes | ODS available |
ODS availability of rear 1st row center seat
| # | Input | Output | Remarks |
| --- | --- | --- | --- |
| # | MCUCONST - MCUID0225 | Internal Parameter - RC_ODS_Availability | Remarks |
| 1 | 0 | No | ODS not available |
| 2 | 1 | Yes | ODS available |
ODS availability of rear 1st row left seat
| # | Input | Output | Remarks |
| --- | --- | --- | --- |
| # | MCUCONST - MCUID0226 | Internal Parameter - RL_ODS_Availability | Remarks |
| 1 | 0 | No | ODS not available |
| 2 | 1 | Yes | ODS available |
- Verification Criteria: Verify by executing test cases
- Verification Method: Code/Design Review, System Qualification Test
- Verification Owner: FV
- System Requirement State: Approved
- Primary Discipline: SW
- ASIL Rating: QM

#### TFDCX32348-32204 (System Requirement)
Rear 2nd Row Seat ODS Availability Determination
ODS avaliability of rear 2nd row right seat
| # | Input | Output | Remarks |
| --- | --- | --- | --- |
| # | MCUCONST - MCUID0227 | Internal Parameter - R2R_ODS_Availability | Remarks |
| 1 | 0 | No | ODS not available |
| 2 | 1 | Yes | ODS available |
ODS avaliability of rear 2nd row center seat
| # | Input | Output | Remarks |
| --- | --- | --- | --- |
| # | MCUCONST - MCUID0228 | Internal Parameter - R2C_ODS_Availability | Remarks |
| 1 | 0 | No | ODS not available |
| 2 | 1 | Yes | ODS available |
ODS avaliability of rear 2nd row left seat
| # | Input | Output | Remarks |
| --- | --- | --- | --- |
| # | MCUCONST - MCUID0229 | Internal Parameter - R2L_ODS_Availability | Remarks |
| 1 | 0 | No | ODS not available |
| 2 | 1 | Yes | ODS available |
- Verification Criteria: Verify by executing test cases
- Verification Method: Code/Design Review, System Qualification Test
- Verification Owner: FV
- System Requirement State: Approved
- Primary Discipline: SW
- ASIL Rating: QM

#### TFDCX32348-32205 (System Requirement)
Rear 3rd Row Seat ODS Availability Determination
ODS avaliability of rear 3rd row right seat
| # | Input | Output | Remarks |
| --- | --- | --- | --- |
| # | MCUCONST - MCUID0230 | Internal Parameter - R3R_ODS_Availability | Remarks |
| 1 | 0 | No | ODS not available |
| 2 | 1 | Yes | ODS available |
ODS avaliability of rear 3rd row center seat
| # | Input | Output | Remarks |
| --- | --- | --- | --- |
| # | MCUCONST - MCUID0231 | Internal Parameter - R3C_ODS_Availability | Remarks |
| 1 | 0 | No | ODS not available |
| 2 | 1 | Yes | ODS available |
ODS avaliability of rear 3rd row left seat
| # | Input | Output | Remarks |
| --- | --- | --- | --- |
| # | MCUCONST - MCUID0232 | Internal Parameter - R3L_ODS_Availability | Remarks |
| 1 | 0 | No | ODS not available |
| 2 | 1 | Yes | ODS available |
- Verification Criteria: Verify by executing test cases
- Verification Method: Code/Design Review, System Qualification Test
- Verification Owner: FV
- System Requirement State: Approved
- Primary Discipline: SW
- ASIL Rating: QM

#### TFDCX32348-32206: Rear Doors Availability Determination (System Requirement)
Rear Doors Availability Determination
| # | Input | Output | Remarks |
| --- | --- | --- | --- |
| # | MCUCONST - MCUID0233 | Internal Parameter -REAR_DOORS_Availability | Remarks |
| 1 | 0 | No | Rear doors not available |
| 2 | 1 | Yes | Rear doors available |
- Verification Criteria: Verify by executing test cases
- Verification Method: Code/Design Review, System Qualification Test
- Verification Owner: FV
- System Requirement State: Approved
- Primary Discipline: SW
- ASIL Rating: QM

#### TFDCX32348-32208 (System Requirement)
Front-Rear Seat Walkthrough Availability Determination
| # | Input | Output | Remarks |
| --- | --- | --- | --- |
| # | MCUCONST - MCUID0234 | Internal Parameter - FR_RR_WALKTHROUGH_Availability | Remarks |
| 1 | 0 | No | Fr-Rr seat waklthrough not available |
| 2 | 1 | Yes | Fr-Rr seat waklthrough available |
- Verification Criteria: Verify by executing test cases
- Verification Method: Code/Design Review, System Qualification Test
- Verification Owner: FV
- System Requirement State: Approved
- Primary Discipline: SW
- ASIL Rating: QM

#### TFDCX32348-92477: Specific parameters for Toyota (System Requirement)
- Verification Method: Code/Design Review, System Qualification Test
- Verification Owner: FV
- System Requirement State: Approved
- Primary Discipline: SW
- ASIL Rating: QM

##### TFDCX32348-3247: All Seat Common Parameters [Toyota] (System Requirement)
All Seat Common Parameters [Toyota]
|  | Param. Description | Param. Name | Destination Group A | Destination Group B | Destination Group C | Destination Group G |
| --- | --- | --- | --- | --- | --- | --- |
| 1 | Driving judgment vehicle speed [km/h] | [S1] | 20 | 20 | 5 | 5 |
| 2 | Stopped judgment vehicle speed [km/h] | [S2] | 1.75 | 1.75 | 1.75 | 1.75 |
| 3 | Driving judgment vehicle speed for re-sounding BZR [km/h] | [S3] | 5 | 10 | 5 | N/A |
| 4 | Low-speed driving judgment vehicle speed [km/h] | [S4] | 5 | N/A | N/A | 5 |
| 5 | High-speed driving judgment vehicle speed [km/h] | [S5] | 35 | N/A | N/A | 35 |
| 6 | Shift-R - Input determination time [ms] | [T16] | 300 | 300 | 300 | N/A |
| 7 | Wait duration for other BZR sounding [s] | [T17] | 1.8 | N/A | N/A | 1.8 |
| 8 | Legally required warning duration 1 [s] | [T18] | 7.8 | N/A | N/A | N/A |
| 9 | Legally required warning duration 2 [s] | [T19] | 7.8 | N/A | N/A | N/A |
| 10 | Level2 counter time [s] | [TF4] | N/A | N/A | N/A | 36 |
| 11 | “Unbuckle alarm” state telltale output | [TTF2] | N/A | N/A | N/A | Level1 blink |
| 12 | GP duration [s] | [T20] | 18 | N/A | N/A | N/A |
| 13 | 'State F: Unbuckled notification' BZR output | [BZ8] | BZR - SBR_Unbuckled_Notify_BUZZER | BZR - SBR_Unbuckled_Notify_BUZZER | BZR - SBR_Unbuckled_Notify_BUZZER | N/A |
| 14 | Max number of soundings of Legally required BZR [times] (SYS OIL#140-23, 34) (*2) | [T22] | 5 | N/A | N/A | N/A |
| 15 | Cycle time of Legally required BZR and Blink cycle of Legally required TT output [s] | [C5] | 1.2 | 1.2 | 1.2 | N/A |
| 16 | Cycle time of Lv1 warning BZR and Blink cycle of Lv1 warning TT output [s] | [C9] | 1.2 | 1.2 | 1.2 | 1.2 |
| 17 | Cycle time of Lv2 warning BZR and Blink cycle of Lv2 warning TT output [s] | [C11] | 0.4 | 0.4 | 0.4 | 0.4 |
Group C is now available.
(*2) This parameter was once removed but enabled again based on SYS OIL#149-34, in order to avoid playing Legally required BZR more than [T22] times. Refer to TFDCX32348-32938 to find how to count the times of playing the buzzer.
- Verification Criteria: Verify by executing test cases
- Verification Method: Code/Design Review, System Qualification Test
- Verification Owner: FV
- System Requirement State: Approved
- Primary Discipline: SW
- ASIL Rating: QM

##### TFDCX32348-3245 (System Requirement)
Rear Seat (without ODS) Specific Parameters [Toyota]
Typically, ODS availability statuses of rear seats are set for all seats at once. However, they can be set individually for each rear seat by MCUID0224-MCUID0232 parameters. (Refer to TFDCX32348-32201, TFDCX32348-32204, TFDCX32348-32205) If the ODS availability settings are different for each rear seat, switch the applied parameter values according to the ODS availability setting.
|  | Param. Description | Param. Name | Destination Group A |  | Destination Group B |  | Destination Group C (*1) | Destination Group G |
| --- | --- | --- | --- | --- | --- | --- | --- | --- |
| 1 | CAN buckle status - Input determination time [ms] | [T9] | 400 |  | 400 |  | 400 | 400 |
| 2 | MID TT display duration after IG-ON [s] | [T10] | 66 |  | 66 |  | 66 | 66 |
| 3 | Unbuckle warning time [s] | [TF3] | N/A |  | N/A |  | N/A | 36 |
| 4 | Rear seat without ODS - Lv1 duration [s] | [T12] | 6 |  | 6 |  | 6 | 24 |
| 5 | Rear seat without ODS - Lv2 duration [s] | [T13] | 66 |  | 60 |  | 60 | 66 |
| 6 | 'State r: Lv2 completed' TT output | [TT22] | OFF |  | OFF |  | OFF | OFF |
| 7 | 'State r: Lv2 interrupted' TT output | [TTF3] | N/A |  | N/A |  | N/A | ON |
| 8 | Whether to wait until seatbelt-buckled determined | - | Yes |  | Yes |  | Yes | Yes |
| 9 | CAN seatbelt-buckled status - Input determination time [ms] | [T34] | 1500 |  | 1500 |  | 1500 | 1500 |
Group C is now available.
- Verification Criteria: Verify by executing test cases
- Verification Method: Code/Design Review, System Qualification Test
- Verification Owner: FV
- System Requirement State: Approved
- Primary Discipline: SW
- ASIL Rating: QM

##### TFDCX32348-3243 (System Requirement)
Rear Seat (with ODS) Specific Parameters [Toyota]
Typically, ODS availability statuses of rear seats are set for all seats at once. However, they can be set individually for each rear seat by MCUID0224-MCUID0232 parameters. (Refer to TFDCX32348-32201, TFDCX32348-32204, TFDCX32348-32205) If the ODS availability settings are different for each rear seat, switch the applied parameter values according to the ODS availability setting.
|  | Param. Description | Param. Name | Destination Group A |  | Destination Group B |  | Destination Group C | Destination Group G | Remark |
| --- | --- | --- | --- | --- | --- | --- | --- | --- | --- |
| 1 | HW buckle sensor - Input determination time [ms] | [T6] | 800 |  | 800 |  | 800 | N/A | Rear seat buckle status comes via CAN |
| 2 | CAN buckle status - Input determination time [ms] | [T32] | 400 |  | 400 |  | 400 | N/A |  |
| 3 | CAN ODS status - Input determination time [ms] | [T33] | 800 |  | 800 |  | 800 | N/A |  |
| 4 | Rear seat with ODS - Lv1 duration [s] | [T7] | 6 |  | 24 |  | 6 | N/A |  |
| 5 | Rear seat with ODS - Lv2 duration [s] | [T8] | 66 |  | 100 |  | 100 | N/A |  |
| 6 | 'State r: Lv2 completed' TT output | [TT25] | ON |  | ON |  | ON | N/A |  |
Group C is now available.
- Verification Criteria: Verify by executing test cases
- Verification Method: Code/Design Review, System Qualification Test
- Verification Owner: FV
- System Requirement State: Approved
- Primary Discipline: SW
- ASIL Rating: QM

##### TFDCX32348-3241: Rear Seat Common Parameters [Toyota] (System Requirement)
Rear Seat Common Parameters [Toyota]
|  | Param. Description | Param. Name | Destination Group A |  | Destination Group B |  | Destination Group C | Destination Group G | Remark |
| --- | --- | --- | --- | --- | --- | --- | --- | --- | --- |
| 1 | Legally required BZR applicability | - | No |  | No |  | No | N/A |  |
| 2 | GP applicability (*1) | - | Yes |  | No |  | No | N/A |  |
| 3 | Whether to continue BZR while vehicle is parked | - | No |  | No |  | No | N/A |  |
| 4 | MID TT display duration while door closed [s] | [T11] | 66 |  | 66 |  | 66 | 66 |  |
| 5 | MID TT display duration while unbuckled [s] | [T14] | 66 |  | 66 |  | 66 | 66 |  |
| 6 | Whether to display when other rear seatbelt buckled | - | No |  | No |  | No | No |  |
| 7 | Rear seatbelt buckled edge timer[s] | [T27] | 30 |  | 30 |  | 30 | 30 | N/A as No.6 is 'No' (38xD SYS OIL#140-6) |
| 8 | 'State k: Indication for fixed time after IG-ON' TT output | [TT36] | ON |  | ON |  | ON | ON |  |
| 9 | 'State l: Indication after door open/door close' TT output | [TT37] | ON |  | ON |  | ON | ON |  |
| 10 | 'State o: Indication of state interlocked with other rear seat' TT output | [TT38] | ON |  | ON |  | ON | N/A |  |
| 11 | 'State p: Lv1 while driving' TT output | [TT20] | Lv1-Blink |  | Lv1-Blink |  | Lv1-Blink | Lv1-Blink |  |
| 12 | 'State q: Lv2 while driving' TT output | [TT21] | Lv2-Blink |  | Lv2-Blink |  | Lv2-Blink | Lv2-Blink |  |
| 13 | 'State n: Lv1 while vehicle stopped' TT output | [TT23] | ON |  | ON |  | ON | N/A |  |
| 14 | 'State s: Lv2 while vehicle stopped' TT output | [TT24] | Lv1-Blink |  | Lv1-Blink |  | Lv1-Blink | N/A |  |
(*1) GP ... Grace Period
Group C is now available.
- Verification Criteria: Verify by executing test cases
- Verification Method: Code/Design Review, System Qualification Test
- Verification Owner: FV
- System Requirement State: Approved
- Primary Discipline: SW
- ASIL Rating: QM

##### TFDCX32348-3239 (System Requirement)
P/FrCtr-Seat Specific Parameters [Toyota]
|  | Param. Description | Param. Name | Destination Group A |  | Destination Group B |  | Destination Group C | Destination Group G | Remark |
| --- | --- | --- | --- | --- | --- | --- | --- | --- | --- |
| 1 | Legally required BZR applicability | - | No |  | No |  | No | N/A |  |
| 2 | Legally required TT applicability | - | No |  | No |  | No | N/A |  |
| 3 | GP applicability (*1) | - | Yes |  | No |  | No | N/A |  |
| 4 | Whether to continue BZR while vehicle is parked | - | No |  | Yes |  | No | N/A |  |
| 5 | HW buckle sensor - Input determination time [ms] | [T4] | 400 |  | 400 |  | 400 | 400 | P seat buckle status comes via CAN |
| 6 | CAN buckle status - Input determination time [ms] | [T30] | 400 |  | 400 |  | 400 | 400 |  |
| 7 | CAN ODS status - Input determination time [ms] | [T31] | 800 |  | 800 |  | 800 | 800 |  |
| 8 | 'State d: Legally required warning' TT output | [TT7] | Lv1-Blink (38xD SYS OIL#140-26) |  | OFF |  | OFF | N/A |  |
| 9 | 'State f: Lv1 while driving' TT output | [TT8] | Lv1-Blink |  | Lv1-Blink |  | Lv1-Blink | Lv1-Blink |  |
| 10 | 'State g: Lv2 while driving' TT output | [TT9] | Lv2-Blink |  | Lv2-Blink |  | Lv2-Blink | Lv2-Blink |  |
| 11 | 'State h: Lv2 completed' TT output | [TT10] | ON |  | ON |  | ON | ON |  |
| 12 | 'State i: Lv1 while vehicle stopped' TT output | [TT11] | ON |  | ON |  | ON | N/A |  |
| 13 | 'State j: Lv2 while vehicle stopped ' TT output | [TT12] | Lv1-Blink |  | Lv1-Blink |  | Lv1-Blink | N/A |  |
| 14 | 'State D: Legally required warning' BZR output | [BZ2] | N/A |  | N/A |  | N/A | N/A |  |
(*1) GP ... Grace Period
Group C is now available.
FrCtr (Front center) seat is now available.
- Verification Criteria: Verify by executing test cases
- Verification Method: Code/Design Review, System Qualification Test
- Verification Owner: FV
- System Requirement State: Approved
- Primary Discipline: SW
- ASIL Rating: QM

##### TFDCX32348-3237: D-Seat Specific Parameters [Toyota] (System Requirement)
D-Seat Specific Parameters [Toyota]
|  | Param. Description | Param. Name | Destination Group A |  | Destination Group B |  | Destination Group C | Destination Group G |  |
| --- | --- | --- | --- | --- | --- | --- | --- | --- | --- |
| 1 | Legally required BZR applicability | - | Yes |  | No |  | No | N/A |  |
| 2 | Legally required TT applicability | - | Yes |  | No |  | No | N/A |  |
| 3 | GP applicability (*1) | - | Yes |  | No |  | No | N/A |  |
| 4 | Whether to continue BZR while vehicle is parked | - | No |  | Yes |  | No | N/A |  |
| 5 | HW buckle sensor - Input determination time [ms] | [T3] (Not used) | 400 |  | 400 |  | 400 | 400 |  |
| 6 | 'State d: Legally required warning' TT output | [TT1] | Lv1-Blink |  | OFF |  | OFF | N/A |  |
| 7 | 'State f: Lv1 while driving' TT output | [TT2] | Lv1-Blink |  | Lv1-Blink |  | Lv1-Blink | Lv1-Blink |  |
| 8 | 'State g: Lv2 while driving' TT output | [TT3] | Lv2-Blink |  | Lv2-Blink |  | Lv2-Blink | Lv2-Blink |  |
| 9 | 'State h: Lv2 completed' TT output | [TT4] | ON |  | ON |  | ON | ON |  |
| 10 | 'State i: Lv1 while vehicle stopped' TT output | [TT5] | ON |  | ON |  | ON | N/A |  |
| 11 | 'State j: Lv2 while vehicle stopped ' TT output | [TT6] | Lv1-Blink |  | Lv1-Blink |  | Lv1-Blink | N/A |  |
| 12 | 'State D: Legally required warning' BZR output | [BZ1] | BZR - SBR_Legally_Required_BUZZER |  | N/A |  | N/A | N/A |  |
(*1) GP ... Grace Period
Group C is now available.
- Verification Criteria: Verify by executing test cases
- Verification Method: Code/Design Review, System Qualification Test
- Verification Owner: FV
- System Requirement State: Approved
- Primary Discipline: SW
- ASIL Rating: QM

##### TFDCX32348-3235 (System Requirement)
D/P/FrCtr-Seat Common Parameters [Toyota]
|  | Param. Description | Param. Name | Destination Group A |  | Destination Group B |  | Destination Group C | Destination Group G |
| --- | --- | --- | --- | --- | --- | --- | --- | --- |
| 1 | D/P seat - Lv1 duration [s] | [T1] | 6 |  | 24 |  | 6 | 24 |
| 2 | D/P seat - Lv2 duration [s] | [T2] | 100 |  | 100 |  | 100 | - |
| 3 | Blink cycle of InitialAlarm Timer [s] | [TF1] | - |  | - |  | - | - |
| 4 | InitialAlarm Timer durations [s] | [TF2] | - |  | - |  | - | 36 |
| 5 | Initial warning state telltale output | [TTF1] | - |  | - |  | - | Lv1-Blink |
Group C is now available.
FrCtr (front center) seat is now available.
- Verification Criteria: Verify by executing test cases
- Verification Method: Code/Design Review, System Qualification Test
- Verification Owner: FV
- System Requirement State: Approved
- Primary Discipline: SW
- ASIL Rating: QM

#### TFDCX32348-92479: Specific parameters for Lexus (System Requirement)
- Verification Method: Code/Design Review, System Qualification Test
- Verification Owner: FV
- System Requirement State: Approved
- Primary Discipline: SW
- ASIL Rating: QM

##### TFDCX32348-92480: All Seat Common Parameters [Lexus] (System Requirement)
All Seat Common Parameters [Lexus]
|  | Param. Description | Param. Name | Destination Group D | Destination Group E | Destination Group F | Destination Group H |
| --- | --- | --- | --- | --- | --- | --- |
| 1 | Driving judgment vehicle speed [km/h] | [S1] | 20 | 20 | 5 | 5 |
| 2 | Stopped judgment vehicle speed [km/h] | [S2] | 1.75 | 1.75 | 1.75 | 1.75 |
| 3 | Driving judgment vehicle speed for re-sounding BZR [km/h] | [S3] | 5 | 10 | 5 | N/A |
| 4 | Low-speed driving judgment vehicle speed [km/h] | [S4] | 5 | N/A | N/A | 5 |
| 5 | High-speed driving judgment vehicle speed [km/h] | [S5] | 35 | N/A | N/A | 35 |
| 6 | Shift-R - Input determination time [ms] | [T16] | 300 | 300 | 300 | N/A |
| 7 | Wait duration for other BZR sounding [s] | [T17] | 1.8 | N/A | N/A | 1.8 |
| 8 | Legally required warning duration 1 [s] | [T18] | 7.8 | N/A | N/A | N/A |
| 9 | Legally required warning duration 2 [s] | [T19] | 7.8 | N/A | N/A | N/A |
| 10 | Level2 counter time [s] | [TF4] | N/A | N/A | N/A | 36 |
| 11 | “Unbuckle alarm” state telltale output | [TTF2] | N/A | N/A | N/A | Level1 blink |
| 12 | GP duration [s] | [T20] | 18 | N/A | N/A | N/A |
| 13 | 'State F: Unbuckled notification' BZR output | [BZ8] | BZR - SBR_Unbuckled_Notify_BUZZER | BZR - SBR_Unbuckled_Notify_BUZZER | BZR - SBR_Unbuckled_Notify_BUZZER | N/A |
| 14 | Max number of soundings of Legally required BZR [times] (SYS OIL#140-23, 34) (*2) | [T22] | 3 | N/A | N/A | N/A |
| 15 | Cycle time of Legally required BZR and Blink cycle of Legally required TT output [s] | [C5] | 1.2 | 1.2 | 1.2 | N/A |
| 16 | Blink cycle of Legally required TT output [s] | [T35] | 1 | 1 | 1 | N/A |
| 17 | Cycle time of Lv1 warning BZR and Blink cycle of Lv1 warning TT output [s] | [T36] (DRV, PSG) | 1 | 1 | 1 | 1 |
| 17 | Cycle time of Lv1 warning BZR and Blink cycle of Lv1 warning TT output [s] | [T38] (REAR) | 1 | 1 | 1 | 1 |
| 18 | Cycle time of Lv2 warning BZR and Blink cycle of Lv2 warning TT output [s] | [T37] (DRV, PSG) | 0.36 | 0.36 | 0.36 | 0.36 |
| 18 | Cycle time of Lv2 warning BZR and Blink cycle of Lv2 warning TT output [s] | [T39] (REAR) | 0.36 | 0.36 | 0.36 | 0.36 |
(*2) This parameterwas once removed but enabled again based on SYS OIL#149-34, in order to avoid playing Legally required BZR more than [T22] times. Refer to TFDCX32348-32938 to find how to count the times of playing the buzzer.
- Verification Criteria: Verify by executing test cases
- Verification Method: Code/Design Review, System Qualification Test
- Verification Owner: FV
- System Requirement State: Approved
- Primary Discipline: SW
- ASIL Rating: QM

##### TFDCX32348-92481 (System Requirement)
Rear Seat (without ODS) Specific Parameters [Lexus]
Typically, ODS availability statuses of rear seats are set for all seats at once. However, they can be set individually for each rear seat by MCUID0224-MCUID0232 parameters. (Refer to TFDCX32348-32201, TFDCX32348-32204, TFDCX32348-32205) If the ODS availability settings are different for each rear seat, switch the applied parameter values according to the ODS availability setting.
|  | Param. Description | Param. Name | Destination Group D |  | Destination Group E |  | Destination Group F | Destination Group H |
| --- | --- | --- | --- | --- | --- | --- | --- | --- |
| 1 | CAN buckle status - Input determination time [ms] | [T9] | 400 |  | 400 |  | 400 | 400 |
| 2 | MID TT display duration after IG-ON [s] | [T10] | 66 |  | 66 |  | 66 | 66 |
| 3 | Unbuckle warning time [s] | [TF3] | N/A |  | N/A |  | N/A | 36 |
| 4 | Rear seat without ODS - Lv1 duration [s] | [T12] | 6 |  | 6 |  | 6 | 24 |
| 5 | Rear seat without ODS - Lv2 duration [s] | [T13] | 64.8 |  | 64.8 |  | 64.8 | 64.8 |
| 6 | 'State r: Lv2 completed' TT output | [TT22] | OFF |  | OFF |  | OFF | OFF |
| 7 | 'State r: Lv2 interrupted' TT output | [TTF3] | N/A |  | N/A |  | N/A | ON |
| 8 | Whether to wait until seatbelt-buckled determined | - | Yes |  | Yes |  | Yes | Yes |
| 9 | CAN seatbelt-buckled status - Input determination time [ms] | [T34] | 1500 |  | 1500 |  | 1500 | 1500 |
- Verification Criteria: Verify by executing test cases
- Verification Method: Code/Design Review, System Qualification Test
- Verification Owner: FV
- System Requirement State: Approved
- Primary Discipline: SW
- ASIL Rating: QM

##### TFDCX32348-92482 (System Requirement)
Rear Seat (with ODS) Specific Parameters [Lexus]
Typically, ODS availability statuses of rear seats are set for all seats at once. However, they can be set individually for each rear seat by MCUID0224-MCUID0232 parameters. (Refer to TFDCX32348-32201, TFDCX32348-32204, TFDCX32348-32205) If the ODS availability settings are different for each rear seat, switch the applied parameter values according to the ODS availability setting.
|  | Param. Description | Param. Name | Destination Group D |  | Destination Group E |  | Destination Group F | Destination Group H | Remark |
| --- | --- | --- | --- | --- | --- | --- | --- | --- | --- |
| 1 | HW buckle sensor - Input determination time [ms] | [T6] | 800 |  | 800 |  | 800 | N/A | Rear seat buckle status comes via CAN |
| 2 | CAN buckle status - Input determination time [ms] | [T32] | 400 |  | 400 |  | 400 | N/A |  |
| 3 | CAN ODS status - Input determination time [ms] | [T33] | 800 |  | 800 |  | 800 | N/A |  |
| 4 | Rear seat with ODS - Lv1 duration [s] | [T7] | 6 |  | 24 |  | 24 6 | N/A |  |
| 5 | Rear seat with ODS - Lv2 duration [s] | [T8] | 64.8 |  | 100.8 |  | 100.8 | N/A |  |
| 6 | 'State r: Lv2 completed' TT output | [TT25] | ON |  | ON |  | ON | N/A |  |
- Verification Criteria: Verify by executing test cases
- Verification Method: Code/Design Review, System Qualification Test
- Verification Owner: FV
- System Requirement State: Approved
- Primary Discipline: SW
- ASIL Rating: QM

##### TFDCX32348-92483: Rear Seat Common Parameters [Lexus] (System Requirement)
Rear Seat Common Parameters [Lexus]
|  | Param. Description | Param. Name | Destination Group D |  | Destination Group E |  | Destination Group F | Destination Group H | Remark |
| --- | --- | --- | --- | --- | --- | --- | --- | --- | --- |
| 1 | Legally required BZR applicability | - | No |  | No |  | No | N/A |  |
| 2 | GP applicability (*1) | - | Yes |  | No |  | No | N/A |  |
| 3 | Whether to continue BZR while vehicle is parked | - | No |  | No |  | No | N/A |  |
| 4 | MID TT display duration while door closed [s] | [T11] | 66 |  | 66 |  | 66 | 66 |  |
| 5 | MID TT display duration while unbuckled [s] | [T14] | 66 |  | 66 |  | 66 | 66 |  |
| 6 | Whether to display when other rear seatbelt buckled | - | No |  | No |  | No | No |  |
| 7 | Rear seatbelt buckled edge timer[s] | [T27] | 30 |  | 30 |  | 30 | 30 | N/A as No.6 is 'No' (38xD SYS OIL#140-6) |
| 8 | 'State k: Indication for fixed time after IG-ON' TT output | [TT36] | ON |  | ON |  | ON | ON |  |
| 9 | 'State l: Indication after door open/door close' TT output | [TT37] | ON |  | ON |  | ON | ON |  |
| 10 | 'State o: Indication of state interlocked with other rear seat' TT output | [TT38] | ON |  | ON |  | ON | N/A |  |
| 11 | 'State p: Lv1 while driving' TT output | [TT20] | Lv1-Blink |  | Lv1-Blink |  | Lv1-Blink | Lv1-Blink |  |
| 12 | 'State q: Lv2 while driving' TT output | [TT21] | Lv2-Blink |  | Lv2-Blink |  | Lv2-Blink | Lv2-Blink |  |
| 13 | 'State n: Lv1 while vehicle stopped' TT output | [TT23] | ON |  | ON |  | ON | N/A |  |
| 14 | 'State s: Lv2 while vehicle stopped' TT output | [TT24] | Lv1-Blink |  | Lv1-Blink |  | Lv1-Blink | N/A |  |
(*1) GP ... Grace Period
- Verification Criteria: Verify by executing test cases
- Verification Method: Code/Design Review, System Qualification Test
- Verification Owner: FV
- System Requirement State: Approved
- Primary Discipline: SW
- ASIL Rating: QM

##### TFDCX32348-92484: P/FrCtr-Seat Specific Parameters [Lexus] (System Requirement)
P/FrCtr-Seat Specific Parameters [Lexus]
|  | Param. Description | Param. Name | Destination Group D |  | Destination Group E |  | Destination Group F | Destination Group H | Remark |
| --- | --- | --- | --- | --- | --- | --- | --- | --- | --- |
| 1 | Legally required BZR applicability | - | No |  | No |  | No | N/A |  |
| 2 | Legally required TT applicability | - | No |  | No |  | No | N/A |  |
| 3 | GP applicability (*1) | - | Yes |  | No |  | No | N/A |  |
| 4 | Whether to continue BZR while vehicle is parked | - | No |  | Yes |  | No | N/A |  |
| 5 | HW buckle sensor - Input determination time [ms] | [T4] | 400 |  | 400 |  | 400 | 400 | P seat buckle status comes via CAN |
| 6 | CAN buckle status - Input determination time [ms] | [T30] | 400 |  | 400 |  | 400 | 400 |  |
| 7 | CAN ODS status - Input determination time [ms] | [T31] | 800 |  | 800 |  | 800 | 800 |  |
| 8 | 'State d: Legally required warning' TT output | [TT7] | Lv1-Blink (38xD SYS OIL#140-26) |  | OFF |  | OFF | N/A |  |
| 9 | 'State f: Lv1 while driving' TT output | [TT8] | Lv1-Blink |  | Lv1-Blink |  | Lv1-Blink | Lv1-Blink |  |
| 10 | 'State g: Lv2 while driving' TT output | [TT9] | Lv2-Blink |  | Lv2-Blink |  | Lv2-Blink | Lv2-Blink |  |
| 11 | 'State h: Lv2 completed' TT output | [TT10] | ON |  | ON |  | ON | ON |  |
| 12 | 'State i: Lv1 while vehicle stopped' TT output | [TT11] | ON |  | ON |  | ON | N/A |  |
| 13 | 'State j: Lv2 while vehicle stopped ' TT output | [TT12] | Lv1-Blink |  | Lv1-Blink |  | Lv1-Blink | N/A |  |
| 14 | 'State D: Legally required warning' BZR output | [BZ2] | N/A |  | N/A |  | N/A | N/A |  |
(*1) GP ... Grace Period
FrCtr (Front center) seat is now available.
- Verification Criteria: Verify by executing test cases
- Verification Method: Code/Design Review, System Qualification Test
- Verification Owner: FV
- System Requirement State: Approved
- Primary Discipline: SW
- ASIL Rating: QM

##### TFDCX32348-92485: D-Seat Specific Parameters [Lexus] (System Requirement)
D-Seat Specific Parameters [Lexus]
|  | Param. Description | Param. Name | Destination Group D |  | Destination Group E |  | Destination Group F | Destination Group H |  |
| --- | --- | --- | --- | --- | --- | --- | --- | --- | --- |
| 1 | Legally required BZR applicability | - | Yes |  | No |  | No | N/A |  |
| 2 | Legally required TT applicability | - | Yes |  | No |  | No | N/A |  |
| 3 | GP applicability (*1) | - | Yes |  | No |  | No | N/A |  |
| 4 | Whether to continue BZR while vehicle is parked | - | No |  | Yes |  | No | N/A |  |
| 5 | HW buckle sensor - Input determination time [ms] | [T3] (Not used) | 400 |  | 400 |  | 400 | 400 |  |
| 6 | 'State d: Legally required warning' TT output | [TT1] | Lv1-Blink |  | OFF |  | OFF | N/A |  |
| 7 | 'State f: Lv1 while driving' TT output | [TT2] | Lv1-Blink |  | Lv1-Blink |  | Lv1-Blink | Lv1-Blink |  |
| 8 | 'State g: Lv2 while driving' TT output | [TT3] | Lv2-Blink |  | Lv2-Blink |  | Lv2-Blink | Lv2-Blink |  |
| 9 | 'State h: Lv2 completed' TT output | [TT4] | ON |  | ON |  | ON | ON |  |
| 10 | 'State i: Lv1 while vehicle stopped' TT output | [TT5] | ON |  | ON |  | ON | N/A |  |
| 11 | 'State j: Lv2 while vehicle stopped ' TT output | [TT6] | Lv1-Blink |  | Lv1-Blink |  | Lv1-Blink | N/A |  |
| 12 | 'State D: Legally required warning' BZR output | [BZ1] | BZR - SBR_Legally_Required_BUZZER |  | N/A |  | N/A | N/A |  |
(*1) GP ... Grace Period
- Verification Criteria: Verify by executing test cases
- Verification Method: Code/Design Review, System Qualification Test
- Verification Owner: FV
- System Requirement State: Approved
- Primary Discipline: SW
- ASIL Rating: QM

##### TFDCX32348-92486: D/P/FrCtr-Seat Common Parameters [Lexus] (System Requirement)
D/P/FrCtr-Seat Common Parameters [Lexus]
|  | Param. Description | Param. Name | Destination Group D |  | Destination Group E |  | Destination Group F | Destination Group H |
| --- | --- | --- | --- | --- | --- | --- | --- | --- |
| 1 | D/P seat - Lv1 duration [s] | [T1] | 6 |  | 24 |  | 6 | 24 |
| 2 | D/P seat - Lv2 duration [s] | [T2] | 100.8 |  | 100.8 |  | 100.8 | - |
| 3 | Blink cycle of InitialAlarm Timer [s] | [TF1] | 1 |  | - |  | - | - |
| 4 | InitialAlarm Timer durations [s] | [TF2] | - |  | - |  | - | 36 |
| 5 | Initial warning state telltale output | [TTF1] | - |  | - |  | - | Lv1-Blink |
- Verification Criteria: Verify by executing test cases
- Verification Method: Code/Design Review, System Qualification Test
- Verification Owner: FV
- System Requirement State: Approved
- Primary Discipline: SW
- ASIL Rating: QM

### TFDCX32348-2567: BZR Customization (Heading)

#### TFDCX32348-3249: BZR ON/OFF Switching (by Diag Command) (System Requirement)
BZR ON/OFF Switching (by Diag Command)
Based on the input parameters NVM_SBRCustBuzzer_[XXX], Meter shall determine the buzzer output control flags SBRCustomBuzzer_[XXX] for each seat.
| # | Input |  | Output | Remark |
| --- | --- | --- | --- | --- |
| # | Internal Parameter - Destination Group | Internal Signal - NVM_SBRCustBuzzer_[XXX] (*1) | SBRCustomBuzzer_[XXX] (*1) | Remark |
| 1 | X | X | ON (Initial Value) | This output is used in TFDCX32348-5659 to determine the BZR output. |
| 2 | C or F or G or H(*2) | X | ON | This output is used in TFDCX32348-5659 to determine the BZR output. |
| 3 | In case of failures in reading data (*3) |  | ON | This output is used in TFDCX32348-5659 to determine the BZR output. |
| 4 | A or B or D or E | ON | ON | This output is used in TFDCX32348-5659 to determine the BZR output. |
| 5 | A or B or D or E | OFF | OFF | This output is used in TFDCX32348-5659 to determine the BZR output. |
(*1) [XXX] = DRV, PSG, FCTR, RR, RC, RL, R2R, R2C, R2L, R3R, R3C, R3L -> Meter shall maintain the flags for each seat.
(*2) In case of C, F, G, H, SBR buzzer OFF customization shall not be accepted.
(*3) This condition is removed because there is no way to detect failures in reading data.
- Verification Criteria: Verify by executing test cases
- Verification Method: Code/Design Review, System Qualification Test
- Verification Owner: FV
- System Requirement State: Approved
- Primary Discipline: SW
- ASIL Rating: QM

### TFDCX32348-1462: Initialization (Heading)

#### TFDCX32348-3251 (System Requirement)
Function ('Proxy Transmission of Seatbelt Buckle Status by ABG') Presence Judgement
Meter shall determine which signal (D-Seat: DBKLSW or DBKLAB, P-Seat: PBKL_PDC or PBKLAB) is used as the seatbelt buckle status input based on the following state transition diagrams.
The current state information ('ABG NOT Available' or 'ABG Available') shall be stored in Backup RAM for each seat (38xD SYS OIL#140-36).
[D-Seat - Seatbelt Buckle Status Input]
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[P-Seat - Seatbelt Buckle Status Input]
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Note: In both the diagrams, the part of condition 'received twice in a row' shall be satisfied only when the same values are received twice from CAN bus during normal communication without having Communication Failure between 2 data receptions (Impediment 1670630).
- Verification Criteria: Verify by executing test cases
- Verification Method: Code/Design Review, System Qualification Test
- Verification Owner: FV
- System Requirement State: Approved
- Primary Discipline: SW
- ASIL Rating: QM

#### TFDCX32348-88062 (System Requirement)
Function ('MT status') Presence Judgement
Meter shall determine which status (MT or not MT) is used as the status input based on the following state transition diagrams.
The current state information ('MT NOT Available' or 'MT Available') shall be stored in NVM_SBRMtState.
When state parameter changed, it should write the NVM_SBRMtState.
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- Verification Criteria: Verify by executing test cases
- Verification Method: Code/Design Review, System Qualification Test
- Verification Owner: FV
- System Requirement State: Approved
- Primary Discipline: SW
- ASIL Rating: QM

#### TFDCX32348-3253 (System Requirement)
D-Seat buckle status input selection (Dropped)
| # | Input |  | Output |
| --- | --- | --- | --- |
| # | Cfg - region_Group | D-Seat Buckle Status Input (Refer to ) | D-Seat Buckle Status Input Final |
| 1 | 0:380D | X | Use CAN input |
| 2 | Other than 0:380D | Use CANSignal - DBKLAB | Use CAN input |
| 3 | Other than 0:380D | Use HW - DI_AL_DRV_SEAT_BUCKLE | Use H/W input |
Note: DI_AL_DRV_SEAT_BUCKLE H/W input circuit is depopped for 380D.
- Verification Criteria: Verify by executing test cases
- Verification Method: Code/Design Review, System Qualification Test
- Verification Owner: FV
- System Requirement State: Rejected
- Primary Discipline: SW
- ASIL Rating: QM

#### TFDCX32348-3255: Data Reset (Output Parameters) (System Requirement)
Data Reset (Output Parameters)
Meter shall perform resetting the initial values at timing of '+B connection' or 'CPU wakeup' based on the following table.
| # | Input / Output | Item | Initial Value | Special Requirement | CAN/CXPI Signal Power Domain (for reference) | Remarks |
| --- | --- | --- | --- | --- | --- | --- |
| 1 | Output | BZR - SBR_Legally_Required_BUZZER | OFF | - | - |  |
| 2 | Output | BZR - SBR_Level2_BUZZER | OFF | - | - |  |
| 3 | Output | BZR - SBR_Level1_BUZZER | OFF | - | - |  |
| 4 | Output | BZR - SBR_Unbuckled_Notify_BUZZER | OFF | - | - |  |
| 5 | Output | HMI - SBRTelltale | OFF | - | - |  |
| 6 | Output | HMI - SBRBlinkStatus | OFF | - | - |  |
| 7 | Output | HMI - SBRTelltale_RL | OFF | - | - |  |
| 8 | Output | HMI - SBRTelltale_RC | OFF | - | - |  |
| 9 | Output | HMI - SBRTelltale_RR | OFF | - | - |  |
| 10 | Output | HMI - SBRTelltale_R2L | OFF | - | - |  |
| 11 | Output | HMI - SBRTelltale_R2C | OFF | - | - |  |
| 12 | Output | HMI - SBRTelltale_R2R | OFF | - | - |  |
| 13 | Output | HMI - SBRTelltale_R3L | OFF | - | - |  |
| 14 | Output | HMI - SBRTelltale_R3C | OFF | - | - |  |
| 15 | Output | HMI - SBRTelltale_R3R | OFF | - | - |  |
| 16 | Output | CAN Signal - DSWN | 00b | - |  | Dropped |
| 17 | Output | CAN Signal - PSWN | 00b | - |  | Dropped |
| 18 | Output | CAN Signal - DBKL_MET | 10b | - | B |  |
| 19 | Output | CAN Signal - PBKL_MET | 10b | - | B |  |
| 20 | Output | CAN Signal - RLBKLMET | 10b | - | B |  |
| 21 | Output | CAN Signal - RCBKLMET | 10b | - | B |  |
| 22 | Output | CAN Signal - RRBKLMET | 10b | - | B |  |
| 23 | Output | CAN Signal - BKL3LMET | 10b | - | B |  |
| 24 | Output | CAN Signal - BKL3CMET | 10b | - | B |  |
| 25 | Output | CAN Signal - BKL3RMET | 10b | - | B |  |
| 26 | Output | CXPI Signal - RRTT | 0 | - | CXPI_IGR |  |
| 27 | Output | CXPI Signal - RCTT | 0 | - | CXPI_IGR |  |
| 28 | Output | CXPI Signal - RLTT | 0 | - | CXPI_IGR |  |
| 29 | Output | CXPI Signal - RR2TT | 0 | - | CXPI_IGR |  |
| 30 | Output | CXPI Signal - RC2TT | 0 | - | CXPI_IGR |  |
| 31 | Output | CXPI Signal - RL2TT | 0 | - | CXPI_IGR |  |
| 32 | Output | CXPI Signal - RR3TT | 0 | - | CXPI_IGR |  |
| 33 | Output | CXPI Signal - RC3TT | 0 | - | CXPI_IGR |  |
| 34 | Output | CXPI Signal - RL3TT | 0 | - | CXPI_IGR |  |
| 35 | Output | CXPI Signal - REARINDI | 0 | - | CXPI_IGR |  |
- Verification Criteria: Verify by executing test cases
- Verification Method: Code/Design Review, System Qualification Test
- Verification Owner: FV
- System Requirement State: Approved
- Primary Discipline: SW
- ASIL Rating: QM

#### TFDCX32348-32341: Data Reset (Input Parameters) (System Requirement)
Data Reset (Input Parameters)
Meter shall perform resetting the initial values at timing of '+B connection' or 'CPU wakeup' based on the following table.
Note: Some of the initial values are different from the values defined in CAN Summary SRD (See (*1)), but the following values should be set as the application side process.
| # | Input / Output | Item | Initial Value | Special Requirement | CAN/CXPI Signal Power Domain (for reference) | Remarks |
| --- | --- | --- | --- | --- | --- | --- |
| 1 | Input | HW - DI_AL_DRV_SEAT_BUCKLE | OFF | - |  | Dropped |
| 2 | Input | CAN Signal - SP1 | 0000h | Meter shall also set this value when IgnMode OFF -> ON | IGR |  |
| 3 | Input | CAN Signal - B_R | 0b | - | IGR |  |
| 4 | Input | CAN Signal - B_N | 0b | Meter shall also set this value when IgnMode OFF -> ON | IGR |  |
| 5 | Input | CAN Signal - REVSW2 | 0 | - | IGR |  |
| 6 | Input | CAN Signal - B_P | 1b (*1) | Meter shall also set this value when IgnMode OFF -> ON | IGR |  |
| 7 | Input | CAN Signal - DCTY | 0b | - | B |  |
| 8 | Input | CAN Signal - PCTY | 0b | - | B |  |
| 9 | Input | CAN Signal - RRCY | 0b | - | B |  |
| 10 | Input | CAN Signal - RLCY | 0b | - | B |  |
| 11 | Input | CAN Signal - BCTY | 0b | - | B |  |
| 12 | Input | CAN Signal - PKB_BDB | 1b (*1) | Meter shall keep this value until 500ms has passed after IgnMode OFF -> ON | B |  |
| 13 | Input | CAN Signal - DBKLSW | 10b | - | IGR |  |
| 14 | Input | CAN Signal - DBKLAB | 10b | - | IGR |  |
| 15 | Input | CAN Signal - PBKLAB | 10b | - | IGR |  |
| 16 | Input | CAN Signal - PBKL_PDC | 10b | Meter shall also set this value when IgnMode OFF -> ON (38xD SYS OIL#140-35) | B (Signal valid: IGR) |  |
| 17 | Input | CAN Signal - POSW | 10b | - | B |  |
| 18 | Input | CAN Signal - CFBCKL | 10b | - | IGR |  |
| 19 | Input | CAN Signal - CFOSW | 10b | - | B |  |
| 20 | Input | CAN Signal - RRBKLPDC | 10b | Meter shall also set this value when IgnMode OFF -> ON (38xD SYS OIL#140-35) | B (Signal valid: IGR) |  |
| 21 | Input | CAN Signal - RROSW | 10b | - | B |  |
| 22 | Input | CAN Signal - RCBKLPDC | 10b | Meter shall also set this value when IgnMode OFF -> ON (38xD SYS OIL#140-35) | B (Signal valid: IGR) |  |
| 23 | Input | CAN Signal - RCOSW | 10b | - | B |  |
| 24 | Input | CAN Signal - RLBKLPDC | 10b | Meter shall also set this value when IgnMode OFF -> ON (38xD SYS OIL#140-35) | B (Signal valid: IGR) |  |
| 25 | Input | CAN Signal - RLOSW | 10b | - | B |  |
| 26 | Input | CAN Signal - RR2BCKL | 10b | - | IGR |  |
| 27 | Input | CAN Signal - RR2OSW | 10b | - | B |  |
| 28 | Input | CAN Signal - CR2BCKL | 10b | - | IGR |  |
| 29 | Input | CAN Signal - RC2OSW | 10b | - | B |  |
| 30 | Input | CAN Signal - LR2BCKL | 10b | - | IGR |  |
| 31 | Input | CAN Signal - RL2OSW | 10b | - | B |  |
| 32 | Input | CAN Signal - RR3BCKL | 10b | - | IGR |  |
| 33 | Input | CAN Signal - RR3OSW | 10b | - | B |  |
| 34 | Input | CAN Signal - CR3BCKL | 10b | - | IGR |  |
| 35 | Input | CAN Signal - RC3OSW | 10b | - | B |  |
| 36 | Input | CAN Signal - LR3BCKL | 10b | - | IGR |  |
| 37 | Input | CAN Signal - RL3OSW | 10b | - | B |  |
| 38 | Input | CAN Signal - VARTRM1 | 0010b | - | B |  |
- Verification Criteria: Verify by executing test cases
- Verification Method: Code/Design Review, System Qualification Test
- Verification Owner: FV
- System Requirement State: Approved
- Primary Discipline: SW
- ASIL Rating: QM

### TFDCX32348-1464: Normal Operation (Heading)

#### TFDCX32348-3258: Internal Status Determination (Heading)

##### TFDCX32348-5624 (System Requirement)
BklStat_DRV_BZR & BklStat_DRV_TT (Use CAN Signal - DBKLAB)
Apply this table logic when CAN input selection of D-Seat is ‘Use CAN Signal - DBKLAB’. Refer to TFDCX32348-3251 .
|  | Input |  | Output |  |
| --- | --- | --- | --- | --- |
|  | Internal Signal - IgnMode | CAN Signal - DBKLAB (*2) | BklStat_DRV_BZR (*1) | BklStat_DRV_TT (*1) |
| 1 | OFF | X | Buckled | Buckled |
| 2 | ON | Never Received Status=1(Never Received) | Buckled | Buckled |
| 3 | ON | Communication Failure Status=1(Failed) | Buckled | (No Change) |
| 4 | ON | 00b or 10b | Buckled | Buckled |
| 5 | ON | 01b or 11b | Unbuckled | Unbuckled |
(*1) Range: Buckled(Initial State), Unbuckled
- Verification Criteria: Verify by executing test cases
- Verification Method: Code/Design Review, System Qualification Test
- Verification Owner: FV
- System Requirement State: Approved
- Primary Discipline: SW
- ASIL Rating: QM

##### TFDCX32348-5626 (System Requirement)
BklStat_DRV_BZR & BklStat_DRV_TT (Use H/W input) (Dropped)
|  | Input |  | Output |  |
| --- | --- | --- | --- | --- |
|  | InternalSignal - IgnMode | HW - DI_AL_DRV_SEAT_BUCKLE | BklStat_DRV_BZR (*1) | BklStat_DRV_TT (*1) |
| 1 | ON | ON continues for [T3] or more | Unbuckled | Unbuckled |
| 2 | other than above |  | Buckled | Buckled |
(*1) Range: Buckled(Initial State), Unbuckled
- Verification Criteria: Verify by executing test cases
- Verification Method: Code/Design Review, System Qualification Test
- Verification Owner: FV
- System Requirement State: Approved
- Primary Discipline: SW
- ASIL Rating: QM

##### TFDCX32348-32492 (System Requirement)
BklStat_DRV_BZR & BklStat_DRV_TT (Use CAN Signal - DBKLSW)
Apply this table logic when CAN input selection of D-Seat is ‘Use CAN Signal - DBKLSW’. Refer to TFDCX32348-3251 .
|  | Input |  | Output |  |
| --- | --- | --- | --- | --- |
|  | Internal Signal - IgnMode | CAN Signal - DBKLSW (*2) | BklStat_DRV_BZR (*1) | BklStat_DRV_TT (*1) |
| 1 | OFF | X | Buckled | Buckled |
| 2 | ON | Never Received Status=1(Never Received) | Buckled | Buckled |
| 3 | ON | Communication Failure Status=1(Failed) | Buckled | (No Change) |
| 4 | ON | 00b or 10b | Buckled | Buckled |
| 5 | ON | 01b or 11b | Unbuckled | Unbuckled |
(*1) Range: Buckled(Initial State), Unbuckled
- Verification Criteria: Verify by executing test cases
- Verification Method: Code/Design Review, System Qualification Test
- Verification Owner: FV
- System Requirement State: Approved
- Primary Discipline: SW
- ASIL Rating: QM

##### TFDCX32348-5627 (System Requirement)
BklStat_PSG_BZR & BklStat_PSG_TT (PBKLAB & POSW used as input)
Apply this table logic when CAN input selection of P-Seat is ‘Use CAN Signal - PBKLAB’. Refer to TFDCX32348-3251 .
|  | Input |  |  | Output |  | Remark |
| --- | --- | --- | --- | --- | --- | --- |
|  | Internal Signal - IgnMode | CAN Signal - PBKLAB (*2) | CAN Signal - POSW (*2) | BklStat_PSG_BZR (*1) | BklStat_PSG_TT (*1) | Remark |
| 1 | OFF | X | X | Buckled | Buckled |  |
| 2 | ON | 00b | 00b or 01b or 10b | Buckled | Buckled |  |
| 3 | ON | 01b | 00b or 10b | Buckled | Buckled |  |
| 4 | ON | 10b | 00b or 01b or 10b | Buckled | Buckled |  |
| 5 | ON | 01b | 01b continues for [T31] or more | Unbuckled | Unbuckled |  |
| 6 | ON | 11b | X | Unbuckled | Unbuckled |  |
| 7 | ON | X | 11b | Unbuckled | Unbuckled |  |
| 8 | ON | other than above |  | Previous Value | Previous Value | Until No.5 is fixed |
(*1) Range: Buckled(Initial State), Unbuckled
(*2) For BklStat_PSG_BZR, in case of 'Communication Failure Status'=1 (Failed), use '10b' for PBKLAB and '10b' for POSW, and as for 'Never Received Status', refer to TFDCX32348-32341 Data Reset .
For BklStat_PSG_TT, in case of 'Communication Failure Status'=1 (Failed), use the previous value of PBKLAB and POSW, and as for 'Never Received Status', refer to TFDCX32348-32341 Data Reset .
- Verification Criteria: Verify by executing test cases
- Verification Method: Code/Design Review, System Qualification Test
- Verification Owner: FV
- System Requirement State: Approved
- Primary Discipline: SW
- ASIL Rating: QM

##### TFDCX32348-5628 (System Requirement)
BklStat_PSG_BZR & BklStat_PSG_TT (PBKL_PDC & POSW used as input)
Apply this table logic when CAN input selection of P-Seat is ‘Use CAN Signal - PBKL_PDC’. Refer to TFDCX32348-3251 .
|  | Input |  |  | Output |  | Remark |
| --- | --- | --- | --- | --- | --- | --- |
|  | Internal Signal - IgnMode | CAN Signal - PBKL_PDC (*2) | CAN Signal - POSW (*2) | BklStat_PSG_BZR (*1) | BklStat_PSG_TT (*1) | Remark |
| 1 | OFF | X | X | Buckled | Buckled |  |
| 2 | ON | 00b | 00b or 01b or 10b | Buckled | Buckled |  |
| 3 | ON | 01b | 00b or 10b | Buckled | Buckled |  |
| 4 | ON | 10b | 00b or 01b or 10b | Buckled | Buckled |  |
| 5 | ON | 01b continues for [T30] or more | 01b continues for [T31] or more | Unbuckled | Unbuckled |  |
| 6 | ON | X | 11b | Unbuckled | Unbuckled |  |
| 7 | ON | other than above |  | Previous Value | Previous Value | Until No.5 is fixed, or PBKL_PDC=11b |
(*1) Range: Buckled(Initial State), Unbuckled
(*2) For BklStat_PSG_BZR, in case of 'Communication Failure Status'=1 (Failed), use '10b' for PBKL_PDC and '10b' for POSW, and as for 'Never Received Status', refer to TFDCX32348-32341 Data Reset .
For BklStat_PSG_TT, in case of 'Communication Failure Status'=1 (Failed), use the previous value of PBKL_PDC and POSW, and as for 'Never Received Status', refer to TFDCX32348-32341 Data Reset .
- Verification Criteria: Verify by executing test cases
- Verification Method: Code/Design Review, System Qualification Test
- Verification Owner: FV
- System Requirement State: Approved
- Primary Discipline: SW
- ASIL Rating: QM

##### TFDCX32348-32498 (System Requirement)
BklStat_FCTR_BZR & BklStat_FCTR_TT (Front Center Seat)
|  | Input |  |  | Output |  | Remark |
| --- | --- | --- | --- | --- | --- | --- |
|  | Internal Signal - IgnMode | CAN Signal - CFBCKL (*2) | CAN Signal - CFOSW (*2) | BklStat_FCTR_BZR (*1) | BklStat_FCTR_TT (*1) | Remark |
| 1 | OFF | X | X | Buckled | Buckled |  |
| 2 | ON | 00b | 00b or 01b or 10b | Buckled | Buckled |  |
| 3 | ON | 01b | 00b or 10b | Buckled | Buckled |  |
| 4 | ON | 10b | 00b or 01b or 10b | Buckled | Buckled |  |
| 5 | ON | 01b continues for [T30] or more | 01b continues for [T31] or more | Unbuckled | Unbuckled |  |
| 6 | ON | 11b | X | Previous Value | Previous Value |  |
| 7 | ON | X | 11b | Previous Value | Previous Value |  |
| 8 | ON | other than above |  | Previous Value | Previous Value | Until No.5 is fixed |
(*1) Range: Buckled(Initial State), Unbuckled
(*2) For BklStat_FCTR_BZR, in case of 'Communication Failure Status'=1 (Failed), use '10b' for CFBCKL and '10b' for CFOSW, and as for 'Never Received Status', refer to TFDCX32348-32341 Data Reset .
For BklStat_FCTR_TT, in case of 'Communication Failure Status'=1 (Failed), use the previous value of CFBCKL and CFOSW, and as for 'Never Received Status', refer to TFDCX32348-32341 Data Reset .
- Verification Criteria: Verify by executing test cases
- Verification Method: Code/Design Review, System Qualification Test
- Verification Owner: FV
- System Requirement State: Approved
- Primary Discipline: SW
- ASIL Rating: QM

##### TFDCX32348-34376 (System Requirement)
Rear Seat Belt Status Determination Logic Selection
Determine the applicable rear seat belt statsus determination logic according to below table.
| # | Rear Seat | Rear Seat Belt Status Parameter (*1) | ODS Availability Condition (*2) | Applied Determination Logic | Value Range | Remarks |
| --- | --- | --- | --- | --- | --- | --- |
| 1 | Rear 1st Row Right | BklStat_RR_BZR (for BUZZER control) BklStat_RR_TT (for TT control) | RR_ODS_Availability = Yes | TFDCX32348-5629 | Buckled Unbuckled |  |
| 2 | Rear 1st Row Right | BklStat_RR_BZR (for BUZZER control) BklStat_RR_TT (for TT control) | RR_ODS_Availability = No | TFDCX32348-5630 | Undecided Buckled Unbuckled |  |
| 3 | Rear 1st Row Center | BklStat_RC_BZR (for BUZZER control) BklStat_RC_TT (for TT control) | RC_ODS_Availability = Yes | TFDCX32348-5629 | Buckled Unbuckled |  |
| 4 | Rear 1st Row Center | BklStat_RC_BZR (for BUZZER control) BklStat_RC_TT (for TT control) | RC_ODS_Availability = No | TFDCX32348-5630 | Undecided Buckled Unbuckled |  |
| 5 | Rear 1st Row Left | BklStat_RL_BZR (for BUZZER control) BklStat_RL_TT (for TT control) | RL_ODS_Availability = Yes | TFDCX32348-5629 | Buckled Unbuckled |  |
| 6 | Rear 1st Row Left | BklStat_RL_BZR (for BUZZER control) BklStat_RL_TT (for TT control) | RL_ODS_Availability = No | TFDCX32348-5630 | Undecided Buckled Unbuckled |  |
| 7 | Rear 2nd Row Right | BklStat_R2R_BZR (for BUZZER control) BklStat_R2R_TT (for TT control) | R2R_ODS_Availability = Yes | TFDCX32348-32525 | Buckled Unbuckled |  |
| 8 | Rear 2nd Row Right | BklStat_R2R_BZR (for BUZZER control) BklStat_R2R_TT (for TT control) | R2R_ODS_Availability = No | TFDCX32348-32573 | Undecided Buckled Unbuckled |  |
| 9 | Rear 2nd Row Center | BklStat_R2C_BZR (for BUZZER control) BklStat_R2C_TT (for TT control) | R2C_ODS_Availability = Yes | TFDCX32348-32525 | Buckled Unbuckled |  |
| 10 | Rear 2nd Row Center | BklStat_R2C_BZR (for BUZZER control) BklStat_R2C_TT (for TT control) | R2C_ODS_Availability = No | TFDCX32348-32573 | Undecided Buckled Unbuckled |  |
| 11 | Rear 2nd Row Left | BklStat_R2L_BZR (for BUZZER control) BklStat_R2L_TT (for TT control) | R2L_ODS_Availability = Yes | TFDCX32348-32525 | Buckled Unbuckled |  |
| 12 | Rear 2nd Row Left | BklStat_R2L_BZR (for BUZZER control) BklStat_R2L_TT (for TT control) | R2L_ODS_Availability = No | TFDCX32348-32573 | Undecided Buckled Unbuckled |  |
| 13 | Rear 3rd Row Right | BklStat_R3R_BZR (for BUZZER control) BklStat_R3R_TT (for TT control) | R3R_ODS_Availability = Yes | TFDCX32348-32525 | Buckled Unbuckled |  |
| 14 | Rear 3rd Row Right | BklStat_R3R_BZR (for BUZZER control) BklStat_R3R_TT (for TT control) | R3R_ODS_Availability = No | TFDCX32348-32573 | Undecided Buckled Unbuckled |  |
| 15 | Rear 3rd Row Center | BklStat_R3C_BZR (for BUZZER control) BklStat_R3C_TT (for TT control) | R3C_ODS_Availability = Yes | TFDCX32348-32525 | Buckled Unbuckled |  |
| 16 | Rear 3rd Row Center | BklStat_R3C_BZR (for BUZZER control) BklStat_R3C_TT (for TT control) | R3C_ODS_Availability = No | TFDCX32348-32573 | Undecided Buckled Unbuckled |  |
| 17 | Rear 3rd Row Left | BklStat_R3L_BZR (for BUZZER control) BklStat_R3L_TT (for TT control) | R3L_ODS_Availability = Yes | TFDCX32348-32525 | Buckled Unbuckled |  |
| 18 | Rear 3rd Row Left | BklStat_R3L_BZR (for BUZZER control) BklStat_R3L_TT (for TT control) | R3L_ODS_Availability = No | TFDCX32348-32573 | Undecided Buckled Unbuckled |  |
(*1) Same parameters are used for ‘with ODS’ and ‘without ODS’.
(*2) Refer to TFDCX32348-32201 for rear 1st row, TFDCX32348-32204 for rear 2nd row, TFDCX32348-32205 for rear 3rd row.
- Verification Criteria: Verify by executing test cases
- Verification Method: Code/Design Review, System Qualification Test
- Verification Owner: FV
- System Requirement State: Approved
- Primary Discipline: SW
- ASIL Rating: QM

##### TFDCX32348-5629 (System Requirement)
BklStat_R*_BZR & BklStat_R*_TT' (with ODS) for Rear 1st Row Seat
Apply below table logic for the rear 1st row seat with ODS. (*1)
Buckled status parameters are commonly used for ‘with ODS’ and ‘without ODS’.
|  | Input |  |  | Output |  | Remark |
| --- | --- | --- | --- | --- | --- | --- |
|  | InternalSignal - IgnMode | CANSignal - R*BKLPDC (*2)(*4) | CANSignal - R*OSW (*2)(*4) | BklStat_R*_BZR (*2)(*3) | BklStat_R*_TT (*2)(*3) | Remark |
| 1 | OFF | X | X | Buckled | Buckled |  |
| 2 | ON | 00b | 00b or 01b or 10b | Buckled | Buckled |  |
| 3 | ON | 01b | 00b or 10b | Buckled | Buckled |  |
| 4 | ON | 10b | 00b or 01b or 10b | Buckled | Buckled |  |
| 5 | ON | 01b continues for [T32] or more | 01b continues for [T33] or more | Unbuckled | Unbuckled |  |
| 6 | ON | X | 11b | Unbuckled | Unbuckled |  |
| 7 | ON | other than above |  | Previous Value | Previous Value | Until No.5 is fixed, or R*BKLPDC=11b |
(*1) Refer to TFDCX32348-34376 .
(*2) R*BKLPDC = RRBKLPDC, RCBKLPDC, RLBKLPDC,
R*OSW = RROSW, RCOSW, RLOSW,
BklStat_R*_BZR = BklStat_RR_BZR, BklStat_RC_BZR, BklStat_RL_BZR, respectively.
BklStat_R*_TT = BklStat_RR_TT, BklStat_RC_TT, BklStat_RL_TT, respectively.
-> Combination of signals for the same seat should be used to determine the status of the same seat.
(*3) Range: Buckled(Initial State), Unbuckled
(*4) For BklStat_R*_BZR, in case of 'Communication Failure Status'=1 (Failed), use '10b' for R*BKLPDC and '10b' for R*OSW, and as for 'Never Received Status', refer to TFDCX32348-32341 Data Reset .
For BklStat_R*_TT, in case of 'Communication Failure Status'=1 (Failed), use the previous value of R*BKLPDC and R*OSW, and as for 'Never Received Status', refer to TFDCX32348-32341 Data Reset .
- Verification Criteria: Verify by executing test cases
- Verification Method: Code/Design Review, System Qualification Test
- Verification Owner: FV
- System Requirement State: Approved
- Primary Discipline: SW
- ASIL Rating: QM

##### TFDCX32348-32525 (System Requirement)
BklStat_R*_BZR & BklStat_R*_TT (with ODS) for Rear 2nd&3rd Row Seat*
Apply below table logic for the rear 1st row seat with ODS. (*1)
Buckled status parameters are commonly used for ‘with ODS’ and ‘without ODS’.
|  | Input |  |  | Output |  | Remark |
| --- | --- | --- | --- | --- | --- | --- |
|  | InternalSignal - IgnMode | CANSignal - *R*BCKL (*2)(*4) | CANSignal - R**OSW (*2)(*4) | BklStat_R*_BZR (*2)(*3) | BklStat_R*_TT (*2)(*3) | Remark |
| 1 | OFF | X | X | Buckled | Buckled |  |
| 2 | ON | 00b | 00b or 01b or 10b | Buckled | Buckled |  |
| 3 | ON | 01b | 00b or 10b | Buckled | Buckled |  |
| 4 | ON | 10b | 00b or 01b or 10b | Buckled | Buckled |  |
| 5 | ON | 01b continues for [T32] or more | 01b continues for [T33] or more | Unbuckled | Unbuckled |  |
| 6 | ON | 11b | X | Previous Value | Previous Value |  |
| 7 | ON | X | 11b | Previous Value | Previous Value |  |
| 8 | ON | other than above |  | Previous Value | Previous Value | Until No.5 is fixed |
(*1) Refer to TFDCX32348-34376 .
(*2) *R*BCKL = RR2BCKL, CR2BCKL, LR2BCKL, RR3BCKL, CR3BCKL, LR3BCKL
R*OSW = RR2OSW, RC2OSW, RL2OSW, RR3OSW, RC3OSW, RL3OSW
BklStat_R*_BZR = BklStat_R2R_BZR, BklStat_R2C_BZR, BklStat_R2L_BZR, BklStat_R3R_BZR, BklStat_R3C_BZR, BklStat_R3L_BZR, respectively.
BklStat_R*_TT = BklStat_R2R_TT, BklStat_R2C_TT, BklStat_R2L_TT, BklStat_R3R_TT, BklStat_R3C_TT, BklStat_R3L_TT, respectively.
-> Combination of signals for the same seat should be used to determine the status of the same seat.
(*3) Range: Buckled(Initial State), Unbuckled
(*4) For BklStat_R*_BZR, in case of 'Communication Failure Status'=1 (Failed), use '10b' for *R*BCKL and '10b' for R**OSW, and as for 'Never Received Status', refer to TFDCX32348-32341 Data Reset .
For BklStat_R*_TT, in case of 'Communication Failure Status'=1 (Failed), use the previous value of R*BCKL and R**OSW, and as for 'Never Received Status', refer to TFDCX32348-32341 Data Reset .
- Verification Criteria: Verify by executing test cases
- Verification Method: Code/Design Review, System Qualification Test
- Verification Owner: FV
- System Requirement State: Approved
- Primary Discipline: SW
- ASIL Rating: QM

##### TFDCX32348-5630 (System Requirement)
BklStat_R*_BZR & BklStat_R*_TT (without ODS) for Rear 1st Row Seat
Apply below table logic for the rear 1st row seat without ODS. (*1)
Buckled status parameters are commonly used for ‘with ODS’ and ‘without ODS’.
|  | Input |  | Output |  | Remark |
| --- | --- | --- | --- | --- | --- |
|  | InternalSignal - IgnMode | CANSignal - R*BKLPDC (*2)(*4) | BklStat_R*_BZR (*2)(*3) | BklStat_R*_TT (*2)(*3) | Remark |
| 1 | OFF | X | Undecided | Undecided |  |
| 2 | ON | Never Received Status=1(Never Received) | Undecided | Undecided |  |
| 3 | ON | Communication Failure Status=1(Failed) | Undecided | (No Change) |  |
| 4 | ON | 00b | Buckled | Buckled | No.4 and 5 are exclusive. If 'Whether to wait until seatbelt-buckled determined' (Refer toTFDCX32348-3245 ) is 'Yes', follow No.5, otherwise follow No.4 |
| 5 | ON | 00b continues for [T34] or more | Buckled | Buckled | No.4 and 5 are exclusive. If 'Whether to wait until seatbelt-buckled determined' (Refer toTFDCX32348-3245 ) is 'Yes', follow No.5, otherwise follow No.4 |
| 6 | ON | 01b continues for [T9] or more | Unbuckled | Unbuckled |  |
| 7 | ON | 10b | Undecided | Undecided |  |
| 8 | ON | other than above | Previous Value | Previous Value | Until No.5 or 6 is fixed, or R*BKLPDC=11b |
(*1) Refer to TFDCX32348-34376 .
(*2) R*OSW = RROSW, RCOSW, RLOSW,
BklStat_R*_BZR = BklStat_RR_BZR, BklStat_RC_BZR, BklStat_RL_BZR, respectively.
BklStat_R*_TT = BklStat_RR_TT, BklStat_RC_TT, BklStat_RL_TT, respectively.
-> Combination of signals for the same seat should be used to determine the status of the same seat.
(*3) Range: Buckled, Unbuckled, Undecided(Initial State)
- Verification Criteria: Verify by executing test cases
- Verification Method: Code/Design Review, System Qualification Test
- Verification Owner: FV
- System Requirement State: Approved
- Primary Discipline: SW
- ASIL Rating: QM

##### TFDCX32348-32573 (System Requirement)
BklStat_R*_BZR & BklStat_R*_TT (without ODS) for Rear 2nd&3rd Row Seat
Apply below table logic for the rear seat without ODS (R**_ODS_Availability = No) individually. (*1)
| # | Input |  | Output |  | Remark |
| --- | --- | --- | --- | --- | --- |
| # | InternalSignal - IgnMode | CANSignal - *R*BCKL (*2)(*4) | BklStat_R*_BZR (*2)(*3) | BklStat_R*_TT (*2)(*3) | Remark |
| 1 | OFF | X | Undecided | Undecided |  |
| 2 | ON | Never Received Status=1(Never Received) | Undecided | Undecided |  |
| 3 | ON | Communication Failure Status=1(Failed) | Undecided | (No Change) |  |
| 4 | ON | 00b | Buckled | Buckled | No.4 and 5 are exclusive. If 'Whether to wait until seatbelt-buckled determined' (Refer toTFDCX32348-3245 ) is 'Yes', follow No.5, otherwise follow No.4. |
| 5 | ON | 00b continues for [T34] or more | Buckled | Buckled | No.4 and 5 are exclusive. If 'Whether to wait until seatbelt-buckled determined' (Refer toTFDCX32348-3245 ) is 'Yes', follow No.5, otherwise follow No.4. |
| 6 | ON | 01b continues for [T9] or more | Unbuckled | Unbuckled |  |
| 7 | ON | 10b | Undecided | Undecided |  |
| 8 | ON | other than above | Previous Value | Previous Value | Until No.5 is fixed, or *R*BCKL=11b |
(*1) Refer to TFDCX32348-34376 .
(*2) *R*BCKL= RR2BCKL, CR2BCKL, LR2BCKL, RR3BCKL, CR3BCKL, LR3BCKL, respectively.
BklStat_R*_BZR = BklStat_R2R_BZR, BklStat_R2C_BZR, BklStat_R2L_BZR, BklStat_R3R_BZR, BklStat_R3C_BZR, BklStat_R3L_BZR, respectively.
BklStat_R*_TT= BklStat_R2R_TT, BklStat_R2C_TT, BklStat_R2L_TT, BklStat_R3R_TT, BklStat_R3C_TT, BklStat_R3L_TT, respectively.
-> Combination of signals for the same seat should be used to determine the status of the same seat.
(*3) Range: Buckled, Unbuckled, Undecided(Initial State)
- Verification Criteria: Verify by executing test cases
- Verification Method: Code/Design Review, System Qualification Test
- Verification Owner: FV
- System Requirement State: Approved
- Primary Discipline: SW
- ASIL Rating: QM

##### TFDCX32348-5632 (System Requirement)
Door_DRV / Door_PSG / Door_RR / Door RL / Back Door
Door DRV
|  | Input | Output |
| --- | --- | --- |
|  | CAN Signal - DCTY (*2) | Door_DRV (*1) |
| 1 | 0b | Close |
| 2 | 1b | Open |
Door PSG
|  | Input | Output |
| --- | --- | --- |
|  | CAN Signal - PCTY (*2) | Door_PSG (*1) |
| 1 | 0b | Close |
| 2 | 1b | Open |
DOOR RR
|  | Input | Output |
| --- | --- | --- |
|  | CAN Signal - RRCY (*2) | Door_RR (*1) |
| 1 | 0b | Close |
| 2 | 1b | Open |
DOOR RL
|  | Input | Output |
| --- | --- | --- |
|  | CAN Signal - RLCY (*2) | Door_RL (*1) |
| 1 | 0b | Close |
| 2 | 1b | Open |
Door Back
|  | Input | Output |
| --- | --- | --- |
|  | CAN Signal - BCTY (*2) | Door_BACK (*1) |
| 1 | 0b | Close |
| 2 | 1b | Open |
(*1) Range: Open, Close(Initial State)
(*2) In case of 'Communication Failure Status'=1 (Failed), use '0b' for DCTY, '0b' for PCTY, '0b' for RRCY, '0b' for RLCY, 0b for BCTY and as for 'Never Received Status', refer to TFDCX32348-32341 Data Reset .
- Verification Criteria: Verify by executing test cases
- Verification Method: Code/Design Review, System Qualification Test
- Verification Owner: FV
- System Requirement State: Approved
- Primary Discipline: SW
- ASIL Rating: QM

##### TFDCX32348-5634 (System Requirement)
AllDoor_R (Rear Seat - All Door Open/Close Status) (Dropped)
Logic moved to to TFDCX32348-32619
Meter shall determine 'AllDoor_R' based on the below state transition diagram.
(Refer to to find the applicability of 'Rear doors availability' and 'Fr-Rr seat walkthrough availability')
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Note: For [When Rear doors availability='No' & Fr-Rr seat walkthrough availability='No] and [When Fr-Rr seat walkthrough availability='Yes'] conditions, 'AllDoor_R' should stay the initial state (i.e. 'AllClose').
- Verification Criteria: Verify by executing test cases
- Verification Method: Code/Design Review, System Qualification Test
- Verification Owner: FV
- System Requirement State: Approved
- Primary Discipline: SW
- ASIL Rating: QM

##### TFDCX32348-32619 (System Requirement)
AllDoor_R (Rear Seat - All Door Open/Close Status)
if Internal Parameter - Destination Group = A or B or C or D or E or F
| # | Input |  |  |  |  |  |  | Output |
| --- | --- | --- | --- | --- | --- | --- | --- | --- |
| # | Fr-Rr seat walkthrough availability (*1) | Rear doors availability (*2) | Door_DRV (*3) | Door_PSG (*3) | Door_RR (*3) | Door_RL (*3) | Door_BACK (*3) | AllDoor_R |
| 1 | No | No | Open | X | X | X | X | AnyOpen |
| 2 | No | No | X | Open | X | X | X | AnyOpen |
| 3 | No | No | X | X | X | X | Open | AnyOpen |
| 4 | No | No | Close | Close | X | X | Close | AllClose |
| 5 | No | Yes | X | X | Open | X | X | AnyOpen |
| 6 | No | Yes | X | X | X | Open | X | AnyOpen |
| 7 | No | Yes | X | X | X | X | Open | AnyOpen |
| 8 | No | Yes | X | X | Close | Close | Close | AllClose |
| 9 | Yes | X | X | Open | X | X | X | AnyOpen |
| 10 | Yes | X | X | X | Open | X | X | AnyOpen |
| 11 | Yes | X | X | X | X | Open | X | AnyOpen |
| 12 | Yes | X | X | X | X | X | Open | AnyOpen |
| 13 | Yes | X | X | Close | Close | Close | Close | AllClose |
(*1) Refer to TFDCX32348-32208 .
(*2) Refer to TFDCX32348-32206 .
(*3) Refer to TFDCX32348-5632 .
- Verification Criteria: Verify by executing test cases
- Verification Method: Code/Design Review, System Qualification Test
- Verification Owner: FV
- System Requirement State: Approved
- Primary Discipline: SW
- ASIL Rating: QM

##### TFDCX32348-88155 (System Requirement)
AllDoor_R (Rear Seat - All Door Open/Close Status) for FMVSS208
if Internal Parameter - Destination Group = G or H (New FMVSS208)
| # | Input |  |  |  |  |  | Output |
| --- | --- | --- | --- | --- | --- | --- | --- |
| # | Fr-Rr seat walkthrough availability (*1) | Rear doors availability (*2) | Door_DRV (*3) | Door_PSG (*3) | Door_RR (*3) | Door_RL (*3) | AllDoor_R |
| 1 | No | No | Open | X | X | X | AnyOpen |
| 2 | No | No | X | Open | X | X | AnyOpen |
| 3 | No | No | Close | Close | X | X | AllClose |
| 4 | No | Yes | X | X | Open | X | AnyOpen |
| 5 | No | Yes | X | X | X | Open | AnyOpen |
| 6 | No | Yes | X | X | Close | Close | AllClose |
| 7 | Yes | X | X | Open | X | X | AnyOpen |
| 8 | Yes | X | X | X | Open | X | AnyOpen |
| 9 | Yes | X | X | X | X | Open | AnyOpen |
| 10 | Yes | X | X | Close | Close | Close | AllClose |
(*1) Refer to TFDCX32348-32208 .
(*2) Refer to TFDCX32348-32206 .
(*3) Refer to TFDCX32348-5632 .
- Verification Criteria: Verify by executing test cases
- Verification Method: Code/Design Review, System Qualification Test
- Verification Owner: FV
- System Requirement State: Approved
- Primary Discipline: SW
- ASIL Rating: QM

##### TFDCX32348-5636: ParkStat (Vehicle Parking Status) (System Requirement)
ParkStat (Vehicle Parking Status)
if Internal Parameter - Destination Group = A or B or C or D or E or F
|  | Input |  |  |  | Output |
| --- | --- | --- | --- | --- | --- |
|  | Internal Signal - IgnMode | CAN Signal - SP1 (*2) InternalSignal - SP1_in | CAN Signal - B_P (*2) | CAN Signal - PKB_BDB (*3) | ParkStat (*1) |
| 1 | ON | <= [S2] | 1b | X | Parked |
| 2 | ON | <= [S2] | X | 1b | Parked |
| 3 | other than above |  |  |  | NotParked |
(*1) Range: Parked(Initial State), NotParked
(*2) In case of 'Communication Failure Status'=1 (Failed), use '0000h' for SP1 and '0b' for B_P, and as for 'Never Received Status', refer to TFDCX32348-32341 Data Reset .
(*3) In case of 'Communication Failure Status'=1 (Failed), use '0b' for PKB_BDB, and as for 'Never Received Status', refer to TFDCX32348-32341 Data Reset . (Data Reset value shall be kept until 500ms has passed after IgnMode OFF -> ON, irrespective of 'Communication Failure Status' and 'Never Received Status') (Impediment 1672634).
- Verification Criteria: Verify by executing test cases
- Verification Method: Code/Design Review, System Qualification Test
- Verification Owner: FV
- System Requirement State: Approved
- Primary Discipline: SW
- ASIL Rating: QM

##### TFDCX32348-88247 (System Requirement)
ParkStat (Vehicle Parking Status) for FMVSS208
if Internal Parameter - Destination Group = G or H (New FMVSS208)
| # | Input |  |  |  |  | Output |
| --- | --- | --- | --- | --- | --- | --- |
| # | Internal Signal - IgnMode | NVM - NVM_SBRMtState | CAN Signal - B_P (*2) | CAN Signal - B_N (*2) | CAN Signal - PKB_BDB (*3) | ParkStat (*1) |
| 1 | ON | 0 (MT NOT Available) | 1b | X | X | Parked |
| 2 | ON | 0 (MT NOT Available) | X | 1b | X | Parked |
| 3 | ON | 1 (MT Available) | X | X | 1b | Parked |
| 4 | other than above |  |  |  |  | NotParked |
(*1) Range: Parked(Initial State), NotParked
(*2) In case of 'Communication Failure Status'=1 (Failed), use for B_P, B_N, and as for 'Never Received Status', refer to TFDCX32348-32341 Data Reset .
(*3) In case of 'Communication Failure Status'=1 (Failed), use '0b' for PKB_BDB, and as for 'Never Received Status', refer to TFDCX32348-32341 Data Reset . (Data Reset value shall be kept until 500ms has passed after IgnMode OFF -> ON, irrespective of 'Communication Failure Status' and 'Never Received Status') (Impediment 1672634).
- Verification Criteria: Verify by executing test cases
- Verification Method: Code/Design Review, System Qualification Test
- Verification Owner: FV
- System Requirement State: Approved
- Primary Discipline: SW
- ASIL Rating: QM

##### TFDCX32348-5639: ShiftStat ('Reverse' Gear Shift Status) (System Requirement)
ShiftStat ('Reverse' Gear Shift Status)
| # | Input |  |  | Output |
| --- | --- | --- | --- | --- |
| # | Internal Signal - IgnMode | CAN Signal - B_R (*2) | CAN Signal - REVSW2 (*3) | ShiftStat (*1) |
| 1 | ON | 1b continues for [T16] or more | X | R |
| 2 | ON | X | 1b continues for [T16] or more | R |
| 3 | Other than above |  |  | NotR |
(*1) Range: R, NotR(Initial State)
(*2) In case of 'Communication Failure Status'=1 (Failed), use '0b' for B_R, and as for 'Never Received Status', refer to TFDCX32348-32341 Data Reset .
(*3) In case of 'Communication Failure Status'=1 (Failed), use '0b' for REVSW2, and as for 'Never Received Status', refer to TFDCX32348-32341 Data Reset .
- Verification Criteria: Verify by executing test cases
- Verification Method: Code/Design Review, System Qualification Test
- Verification Owner: FV
- System Requirement State: Approved
- Primary Discipline: SW
- ASIL Rating: QM

#### TFDCX32348-3260: Internal Flag & Timer (Heading)

##### TFDCX32348-34407 (System Requirement)
Rear Seat Belt Unbuckled Flag Processing Table
Follow below table condition to process unbuckled flag.
if Internal Parameter - Destination Group = A or B or C or D or E or F
| # | Rear Seat | Unbuckled Flag Parameter | ODS Availability Condition (*1) | Applied Determination Logic | Remarks |
| --- | --- | --- | --- | --- | --- |
| 1 | 1st Row Right | UnbklFlag_RR_NODS_BZR (for BUZZER control) UnbklFlag_RR_NODS_TT (for TT control) | RR_ODS_Availability = Yes | UnbklFlag_RR_NODS_BZR = 0 UnbklFlag_RR_NODS_TT = 0 | Unbuckled flag is not used for ‘with ODS’. |
| 2 | 1st Row Right | UnbklFlag_RR_NODS_BZR (for BUZZER control) UnbklFlag_RR_NODS_TT (for TT control) | RR_ODS_Availability = No | TFDCX32348-5641 |  |
| 3 | 1st Row Center | UnbklFlag_RC_NODS_BZR (for BUZZER control) UnbklFlag_RC_NODS_TT (for TT control) | RC_ODS_Availability = Yes | UnbklFlag_RC_NODS_BZR = 0 UnbklFlag_RC_NODS_TT = 0 | Unbuckled flag is not used for ‘with ODS’. |
| 4 | 1st Row Center | UnbklFlag_RC_NODS_BZR (for BUZZER control) UnbklFlag_RC_NODS_TT (for TT control) | RC_ODS_Availability = No | TFDCX32348-5641 |  |
| 5 | 1st Row Left | UnbklFlag_RL_NODS_BZR (for BUZZER control) UnbklFlag_RL_NODS_TT (for TT control) | RL_ODS_Availability = Yes | UnbklFlag_RL_NODS_BZR = 0 UnbklFlag_RL_NODS_TT = 0 | Unbuckled flag is not used for ‘with ODS’. |
| 6 | 1st Row Left | UnbklFlag_RL_NODS_BZR (for BUZZER control) UnbklFlag_RL_NODS_TT (for TT control) | RL_ODS_Availability = No | TFDCX32348-5641 |  |
| 7 | 2nd Row Right | UnbklFlag_R2R_NODS_BZR (for BUZZER control) UnbklFlag_R2R_NODS_TT (for TT control) | R2R_ODS_Availability = Yes | UnbklFlag_R2R_NODS_BZR = 0 UnbklFlag_R2R_NODS_TT = 0 | Unbuckled flag is not used for ‘with ODS’. |
| 8 | 2nd Row Right | UnbklFlag_R2R_NODS_BZR (for BUZZER control) UnbklFlag_R2R_NODS_TT (for TT control) | R2R_ODS_Availability = No | TFDCX32348-5641 |  |
| 9 | 2nd Row Center | UnbklFlag_R2C_NODS_BZR (for BUZZER control) UnbklFlag_R2C_NODS_TT (for TT control) | R2C_ODS_Availability = Yes | UnbklFlag_R2C_NODS_BZR = 0 UnbklFlag_R2C_NODS_TT = 0 | Unbuckled flag is not used for ‘with ODS’. |
| 10 | 2nd Row Center | UnbklFlag_R2C_NODS_BZR (for BUZZER control) UnbklFlag_R2C_NODS_TT (for TT control) | R2C_ODS_Availability = No | TFDCX32348-5641 |  |
| 11 | 2nd Row Left | UnbklFlag_R2L_NODS_BZR (for BUZZER control) UnbklFlag_R2L_NODS_TT (for TT control) | R2L_ODS_Availability = Yes | UnbklFlag_R2L_NODS_BZR = 0 UnbklFlag_R2L_NODS_TT = 0 | Unbuckled flag is not used for ‘with ODS’. |
| 12 | 2nd Row Left | UnbklFlag_R2L_NODS_BZR (for BUZZER control) UnbklFlag_R2L_NODS_TT (for TT control) | R2L_ODS_Availability = No | TFDCX32348-5641 |  |
| 13 | 3rd Row Right | UnbklFlag_R3R_NODS_BZR (for BUZZER control) UnbklFlag_R3R_NODS_TT (for TT control) | R3R_ODS_Availability = Yes | UnbklFlag_R3R_NODS_BZR = 0 UnbklFlag_R3R_NODS_TT = 0 | Unbuckled flag is not used for ‘with ODS’. |
| 14 | 3rd Row Right | UnbklFlag_R3R_NODS_BZR (for BUZZER control) UnbklFlag_R3R_NODS_TT (for TT control) | R3R_ODS_Availability = No | TFDCX32348-5641 |  |
| 15 | 3rd Row Center | UnbklFlag_R3C_NODS_BZR (for BUZZER control) UnbklFlag_R3C_NODS_TT (for TT control) | R3C_ODS_Availability = Yes | UnbklFlag_R3C_NODS__BZR = 0 UnbklFlag_R3C_NODS_TT = 0 | Unbuckled flag is not used for ‘with ODS’. |
| 16 | 3rd Row Center | UnbklFlag_R3C_NODS_BZR (for BUZZER control) UnbklFlag_R3C_NODS_TT (for TT control) | R3C_ODS_Availability = No | TFDCX32348-5641 |  |
| 17 | 3rd Row Left | UnbklFlag_R3L_NODS_BZR (for BUZZER control) UnbklFlag_R3L_NODS_TT (for TT control) | R3L_ODS_Availability = Yes | UnbklFlag_R3L_NODS_BZR = 0 UnbklFlag_R3L_NODS_TT = 0 | Unbuckled flag is not used for ‘with ODS’. |
| 18 | 3rd Row Left | UnbklFlag_R3L_NODS_BZR (for BUZZER control) UnbklFlag_R3L_NODS_TT (for TT control) | R3L_ODS_Availability = No | TFDCX32348-5641 |  |
(*1) Refer to TFDCX32348-32201 for rear 1st row, TFDCX32348-32204 for rear 2nd row, TFDCX32348-32205 for rear 3rd row.
- Verification Criteria: Verify by executing test cases
- Verification Method: Code/Design Review, System Qualification Test
- Verification Owner: FV
- System Requirement State: Approved
- Primary Discipline: SW
- ASIL Rating: QM

##### TFDCX32348-5641 (System Requirement)
UnbklFlag_R*_NODS_BZR & UnbklFlag_R* NODS_TT (Rear-Seat without ODS)
Apply below table logic for the rear seat without ODS (*1)
Meter shall set the flags for each rear seat, based on the following table.
These flags are used for rear seat without ODS, and indicate if the seatbelt of each seat is buckled or not. The results are used in BZR Status Determination and TT Status Determination.
if Internal Parameter - Destination Group = A or B or C or D or E or F
|  | Condition | Action |
| --- | --- | --- |
| 1 | IgnMode=ON AND BklStat_R*_NODS_[BZR/TT] turns Buckled -> Unbuckled (*2) | Set UnbklFlag_R*_NODS_[BZR/TT]=1 (*2)(*3) |
| 2 | IgnMode=OFF OR BklStat_R*_NODS_[BZR/TT]=Buckled or Undecided OR {'Rear doors availability'=Yes & IgnMode=ON & SP1_in<=[S2] & (Door_RR=open or Door_RL=open)} (*4)(*5) OR {'Rear doors availability'=No & IgnMode=ON & SP1_in<=[S2] & (Door_DRV=open or Door_PSG=open)} (*5) OR {BZR status of corresponding seat='State J: Lv2 completed' & TT status of corresponding seat='State r: Lv2 completed'} | Set UnbklFlag_R*_NODS_[BZR/TT]=0 (*2)(*3) |
(*1) Refer to TFDCX32348-34407
(*2)
For rear 1st row
BklStat_R*_NODS_[BZR/TT] = BklStat_RR_NODS_BZR, BklStat_RC_NODS_BZR, BklStat_RL_NODS_BZR, BklStat_RR_NODS_TT, BklStat_RC_NODS_TT, BklStat_RL_NODS_TT
UnbklFlag_R*_NODS_[BZR/TT] = UnbklFlag_RR_NODS_BZR, UnbklFlag_RC_NODS_BZR, UnbklFlag_RL_NODS_BZR, UnbklFlag_RR_NODS_TT, UnbklFlag_RC_NODS_TT, UnbklFlag_RL_NODS_TT, respectively (Separate parameters are used for BZR & TT)
For rear 2nd row
BklStat_R*_NODS_[BZR/TT] = BklStat_R2R_NODS_BZR, BklStat_R2C_NODS_BZR, BklStat_R2L_NODS_BZR, BklStat_R2R_NODS_TT, BklStat_R2C_NODS_TT, BklStat_R2L_NODS_TT
UnbklFlag_R*_NODS_[BZR/TT] = UnbklFlag_R2R_NODS_BZR, UnbklFlag_R2C_NODS_BZR, UnbklFlag_R2L_NODS_BZR, UnbklFlag_R2R_NODS_TT, UnbklFlag_R2C_NODS_TT, UnbklFlag_R2L_NODS_TT, respectively (Separate parameters are used for BZR & TT)
For rear 3rd row
BklStat_R*_NODS_[BZR/TT] = BklStat_R3R_NODS_BZR, BklStat_R3C_NODS_BZR, BklStat_R3L_NODS_BZR, BklStat_R3R_NODS_TT, BklStat_R3C_NODS_TT, BklStat_R3L_NODS_TT
UnbklFlag_R*_NODS_[BZR/TT] = UnbklFlag_R3R_NODS_BZR, UnbklFlag_R3C_NODS_BZR, UnbklFlag_R3L_NODS_BZR, UnbklFlag_R3R_NODS_TT, UnbklFlag_R3C_NODS_TT, UnbklFlag_R3L_NODS_TT, respectively (Separate parameters are used for BZR & TT)
-> Status or Flag for the same seat should be used.
(*3) Range: 0(Initialized at CPU Reset OR Wakeup), 1
(*4) In case of 'Communication Failure Status'=1 (Failed), use '0000h' for SP1_in, and as for 'Never Received Status', refer to TFDCX32348-32341 Data Reset .
(*5) If this condition and No.1 are met at the same time, prioritize this condition over No.1 (SYS OIL#140-5).
- Verification Criteria: Verify by executing test cases
- Verification Method: Code/Design Review, System Qualification Test
- Verification Owner: FV
- System Requirement State: Approved
- Primary Discipline: SW
- ASIL Rating: QM

##### TFDCX32348-88268 (System Requirement)
Rear Seat Belt Unbuckled Flag Processing Table for FMVSS208
Follow below table condition to process unbuckled flag.
if Internal Parameter - Destination Group = G or H (New FMVSS208)
| # | Rear Seat | Unbuckled Flag Parameter | ODS Availability Condition (*1) | Applied Determination Logic | Remarks |
| --- | --- | --- | --- | --- | --- |
| 1 | 1st Row Right | UnbklFlag_RR_NODS_BZR (for BUZZER control) UnbklFlag_RR_NODS_TT (for TT control) | RR_ODS_Availability = Yes | UnbklFlag_RR_NODS_BZR = 0 UnbklFlag_RR_NODS_TT = 0 | Unbuckled flag is not used for ‘with ODS’. |
| 2 | 1st Row Right | UnbklFlag_RR_NODS_BZR (for BUZZER control) UnbklFlag_RR_NODS_TT (for TT control) | RR_ODS_Availability = No | TFDCX32348-95774 |  |
| 3 | 1st Row Center | UnbklFlag_RC_NODS_BZR (for BUZZER control) UnbklFlag_RC_NODS_TT (for TT control) | RC_ODS_Availability = Yes | UnbklFlag_RC_NODS_BZR = 0 UnbklFlag_RC_NODS_TT = 0 | Unbuckled flag is not used for ‘with ODS’. |
| 4 | 1st Row Center | UnbklFlag_RC_NODS_BZR (for BUZZER control) UnbklFlag_RC_NODS_TT (for TT control) | RC_ODS_Availability = No | TFDCX32348-95774 |  |
| 5 | 1st Row Left | UnbklFlag_RL_NODS_BZR (for BUZZER control) UnbklFlag_RL_NODS_TT (for TT control) | RL_ODS_Availability = Yes | UnbklFlag_RL_NODS_BZR = 0 UnbklFlag_RL_NODS_TT = 0 | Unbuckled flag is not used for ‘with ODS’. |
| 6 | 1st Row Left | UnbklFlag_RL_NODS_BZR (for BUZZER control) UnbklFlag_RL_NODS_TT (for TT control) | RL_ODS_Availability = No | TFDCX32348-95774 |  |
| 7 | 2nd Row Right | UnbklFlag_R2R_NODS_BZR (for BUZZER control) UnbklFlag_R2R_NODS_TT (for TT control) | R2R_ODS_Availability = Yes | UnbklFlag_R2R_NODS_BZR = 0 UnbklFlag_R2R_NODS_TT = 0 | Unbuckled flag is not used for ‘with ODS’. |
| 8 | 2nd Row Right | UnbklFlag_R2R_NODS_BZR (for BUZZER control) UnbklFlag_R2R_NODS_TT (for TT control) | R2R_ODS_Availability = No | TFDCX32348-95774 |  |
| 9 | 2nd Row Center | UnbklFlag_R2C_NODS_BZR (for BUZZER control) UnbklFlag_R2C_NODS_TT (for TT control) | R2C_ODS_Availability = Yes | UnbklFlag_R2C_NODS_BZR = 0 UnbklFlag_R2C_NODS_TT = 0 | Unbuckled flag is not used for ‘with ODS’. |
| 10 | 2nd Row Center | UnbklFlag_R2C_NODS_BZR (for BUZZER control) UnbklFlag_R2C_NODS_TT (for TT control) | R2C_ODS_Availability = No | TFDCX32348-95774 |  |
| 11 | 2nd Row Left | UnbklFlag_R2L_NODS_BZR (for BUZZER control) UnbklFlag_R2L_NODS_TT (for TT control) | R2L_ODS_Availability = Yes | UnbklFlag_R2L_NODS_BZR = 0 UnbklFlag_R2L_NODS_TT = 0 | Unbuckled flag is not used for ‘with ODS’. |
| 12 | 2nd Row Left | UnbklFlag_R2L_NODS_BZR (for BUZZER control) UnbklFlag_R2L_NODS_TT (for TT control) | R2L_ODS_Availability = No | TFDCX32348-95774 |  |
| 13 | 3rd Row Right | UnbklFlag_R3R_NODS_BZR (for BUZZER control) UnbklFlag_R3R_NODS_TT (for TT control) | R3R_ODS_Availability = Yes | UnbklFlag_R3R_NODS_BZR = 0 UnbklFlag_R3R_NODS_TT = 0 | Unbuckled flag is not used for ‘with ODS’. |
| 14 | 3rd Row Right | UnbklFlag_R3R_NODS_BZR (for BUZZER control) UnbklFlag_R3R_NODS_TT (for TT control) | R3R_ODS_Availability = No | TFDCX32348-95774 |  |
| 15 | 3rd Row Center | UnbklFlag_R3C_NODS_BZR (for BUZZER control) UnbklFlag_R3C_NODS_TT (for TT control) | R3C_ODS_Availability = Yes | UnbklFlag_R3C_NODS__BZR = 0 UnbklFlag_R3C_NODS_TT = 0 | Unbuckled flag is not used for ‘with ODS’. |
| 16 | 3rd Row Center | UnbklFlag_R3C_NODS_BZR (for BUZZER control) UnbklFlag_R3C_NODS_TT (for TT control) | R3C_ODS_Availability = No | TFDCX32348-95774 |  |
| 17 | 3rd Row Left | UnbklFlag_R3L_NODS_BZR (for BUZZER control) UnbklFlag_R3L_NODS_TT (for TT control) | R3L_ODS_Availability = Yes | UnbklFlag_R3L_NODS_BZR = 0 UnbklFlag_R3L_NODS_TT = 0 | Unbuckled flag is not used for ‘with ODS’. |
| 18 | 3rd Row Left | UnbklFlag_R3L_NODS_BZR (for BUZZER control) UnbklFlag_R3L_NODS_TT (for TT control) | R3L_ODS_Availability = No | TFDCX32348-95774 |  |
(*1) Refer to TFDCX32348-32201 for rear 1st row, TFDCX32348-32204 for rear 2nd row, TFDCX32348-32205 for rear 3rd row.
- Verification Criteria: Verify by executing test cases
- Verification Method: Code/Design Review, System Qualification Test
- Verification Owner: FV
- System Requirement State: Approved
- Primary Discipline: SW
- ASIL Rating: QM

##### TFDCX32348-95774 (System Requirement)
UnbklFlag_R*_NODS_BZR & UnbklFlag_R* NODS_TT (Rear-Seat without ODS) for FMVSS208
Apply below table logic for the rear seat without ODS (*1)
Meter shall set the flags for each rear seat, based on the following table.
These flags are used for rear seat without ODS, and indicate if the seatbelt of each seat is buckled or not. The results are used in BZR Status Determination and TT Status Determination.
if Internal Parameter - Destination Group = G or H (New FMVSS208)
|  | Condition | Action |
| --- | --- | --- |
| 1 | IgnMode=ON AND BklStat_R*NODS[BZR/TT] turns Buckled -> Unbuckled (*2) | Set UnbklFlag_R*NODS[BZR/TT]=1 (*2)(*3) |
| 2 | IgnMode=OFF OR BklStat_R*NODS[BZR/TT]=Buckled or Undecided OR {'Rear doors availability'=Yes & IgnMode=ON & SP1_in<=[S2] & (Door_RR=open or Door_RL=open)} (*4)(*5) OR {'Rear doors availability'=No & IgnMode=ON & SP1_in<=[S2] & (Door_DRV=open or Door_PSG=open)} (*5) OR {BZR status of corresponding seat='State J: Lv2 completed' & TT status of corresponding seat='State k: Lv2 completed'} | Set UnbklFlag_R*NODS[BZR/TT]=0 (*2)(*3) |
(*1) Refer to TFDCX32348-88268
(*2)
For rear 1st row
BklStat_R*_NODS_[BZR/TT] = BklStat_RR_NODS_BZR, BklStat_RC_NODS_BZR, BklStat_RL_NODS_BZR, BklStat_RR_NODS_TT, BklStat_RC_NODS_TT, BklStat_RL_NODS_TT
UnbklFlag_R*_NODS[BZR/TT] = UnbklFlag_RR_NODS_BZR, UnbklFlag_RC_NODS_BZR, UnbklFlag_RL_NODS_BZR, UnbklFlag_RR_NODS_TT, UnbklFlag_RC_NODS_TT, UnbklFlag_RL_NODS_TT, respectively (Separate parameters are used for BZR & TT)
For rear 2nd row
BklStat_R*_NODS[BZR/TT] = BklStat_R2R_NODS_BZR, BklStat_R2C_NODS_BZR, BklStat_R2L_NODS_BZR, BklStat_R2R_NODS_TT, BklStat_R2C_NODS_TT, BklStat_R2L_NODS_TT
UnbklFlag_R*_NODS[BZR/TT] = UnbklFlag_R2R_NODS_BZR, UnbklFlag_R2C_NODS_BZR, UnbklFlag_R2L_NODS_BZR, UnbklFlag_R2R_NODS_TT, UnbklFlag_R2C_NODS_TT, UnbklFlag_R2L_NODS_TT, respectively (Separate parameters are used for BZR & TT)
For rear 3rd row
BklStat_R*_NODS[BZR/TT] = BklStat_R3R_NODS_BZR, BklStat_R3C_NODS_BZR, BklStat_R3L_NODS_BZR, BklStat_R3R_NODS_TT, BklStat_R3C_NODS_TT, BklStat_R3L_NODS_TT
UnbklFlag_R*_NODS[BZR/TT] = UnbklFlag_R3R_NODS_BZR, UnbklFlag_R3C_NODS_BZR, UnbklFlag_R3L_NODS_BZR, UnbklFlag_R3R_NODS_TT, UnbklFlag_R3C_NODS_TT, UnbklFlag_R3L_NODS_TT, respectively (Separate parameters are used for BZR & TT)
-> Status or Flag for the same seat should be used.
(*3) Range: 0(Initialized at CPU Reset OR Wakeup), 1
(*4) In case of 'Communication Failure Status'=1 (Failed), use '0000h' for SP1_in, and as for 'Never Received Status', refer to TFDCX32348-32341 Data Reset .
(*5) If this condition and No.1 are met at the same time, prioritize this condition over No.1 (SYS OIL#140-5).
- Verification Criteria: Verify by executing test cases
- Verification Method: Code/Design Review, System Qualification Test
- Verification Owner: FV
- System Requirement State: Approved
- Primary Discipline: SW
- ASIL Rating: QM

##### TFDCX32348-5643 (System Requirement)
R_BklEdgeTimer (Rear-Seat Common SB Buckled Timer)
Meter shall reset/count-up the timer (common to all rear seats), based on the following table.
This timer is used to decide the duration in 'State o: Indication of state interlocked with other rear seat' in TT Status Determination.
This timer should be initialized as '0' (not start counting-up) at CPU Reset OR Wakeup.
|  | Condition | Action |
| --- | --- | --- |
| 1 | IgnMode=OFF | Set R_BklEdgeTimer=0 |
| 2 | IgnMode=ON AND Any of 'BklStat_R*_TT' turns Unbuckled -> Buckled (*1) | Set R_BklEdgeTimer=0, Start count-up R_BklEdgeTimer (*2) |
| 3 | R_BklEdgeTimer>=[T27] | Stop R_BklEdgeTimer |
(*1) BklStat_R*_TT = BklStat_RR_TT, BklStat_RC_TT, BklStat_RL_TT, BklStat_R2R_TT, BklStat_R2C_TT, BklStat_R2L_TT, BklStat_R3R_TT, BklStat_R3C_TT, BklStat_R3L_TT,
(*2) If Condition No.2 is met again during timer counting up, Meter shall reset/count-up the timer (just follow the Action).
- Verification Criteria: Verify by executing test cases
- Verification Method: Code/Design Review, System Qualification Test
- Verification Owner: FV
- System Requirement State: Approved
- Primary Discipline: SW
- ASIL Rating: QM

##### TFDCX32348-5645 (System Requirement)
Lv1_WarnInterruptFlag_DRV / PSG / FCTR / RR / RC / RL / R2R / R2C / R2L / R3R / R3C / R3L
(Level 1 warning buzzer interruption flag)
Front seats:
Lv1_WarnInterruptFlag_DRV / Lv1_WarnInterruptFlag_PSG / Lv1_WarnInterruptFlag_FCTR
Rear 1st row seats:
Lv1_WarnInterruptFlag_RR / Lv1_WarnInterruptFlag_RC / Lv1_WarnInterruptFlag_RL
Rear 2nd row seats:
Lv1_WarnInterruptFlag_R2R / Lv1_WarnInterruptFlag_R2C / Lv1_WarnInterruptFlag_R2L
Rear 3rd row seats:
Lv1_WarnInterruptFlag_R3R / Lv1_WarnInterruptFlag_R3C / Lv1_WarnInterruptFlag_R3L
Meter shall set the flags for each seat, based on the following table.
These flags are used in BZR Status Determination, especially to decide the vehicle speed threshold which is used when gear shift changes from 'R' to another and restart the warning buzzer.
These flags should be initialized as '0' at CPU Reset OR Wakeup.
Note: There are different conditions to set the value to these flags in BZR Status Determination. If the conditions defined here and in BZR Status Determination are met simultaneously, the ones defined here should be prioritized.
Table 1 [DRV]
|  | Condition | Action |
| --- | --- | --- |
| 1 | IgnMode=OFF OR BklStat_D RV_BZR=Buckled OR {'Whether to continue BZR while vehicle is parked'=No & ParkStat=Parked} OR {IgnMode=ON & SP1_in<=[S2] & Door_DRV=Open} (*3) | Set Lv1_WarnInterruptFlag_DRV=0 (*5) |
Table 2 [PSG] [FCTR] (Flag should be maintained for PSG, FCTR individually)
|  | Condition | Action |
| --- | --- | --- |
| 1 | IgnMode=OFF OR BklStat_**_BZR=Buckled (*1) OR {'Whether to continue BZR while vehicle is parked'=No & ParkStat=Parked} OR {IgnMode=ON & SP1_in<=[S2] & Door_PSG=Open} (*3) | Set Lv1_WarnInterruptFlag_**=0 (*5) |
(*5) BklStat_**_BZR = BklStat_PSG_BZR, BklStat_FCTR_BZR
Lv1_WarnInterruptFlag_** = Lv1_WarnInterruptFlag_PSG, Lv1_WarnInterruptFlag_FCTR, respectively.
Table 3 Rear Seat Processing Application Table
| # | Rear Seat | Lv1 Warning Interrupt Flag Name | ODS Availability Condition (*4) | Applied Processing Table | Remarks |
| --- | --- | --- | --- | --- | --- |
| 1 | 1st Row Right | Lv1_WarnInterruptFlag_RR | RR_ODS_Availability = Yes | Table 4 [Rear Seat (with ODS)] |  |
| 2 | 1st Row Right | Lv1_WarnInterruptFlag_RR | RR_ODS_Availability = No | Table 5 [Rear Seat (without ODS)] |  |
| 3 | 1st Row Center | Lv1_WarnInterruptFlag_RC | RC_ODS_Availability = Yes | Table 4 [Rear Seat (with ODS)] |  |
| 4 | 1st Row Center | Lv1_WarnInterruptFlag_RC | RC_ODS_Availability = No | Table 5 [Rear Seat (without ODS)] |  |
| 5 | 1st Row Left | Lv1_WarnInterruptFlag_RL | RL_ODS_Availability = Yes | Table 4 [Rear Seat (with ODS)] |  |
| 6 | 1st Row Left | Lv1_WarnInterruptFlag_RL | RL_ODS_Availability = No | Table 5 [Rear Seat (without ODS)] |  |
| 7 | 2nd Row Right | Lv1_WarnInterruptFlag_R2R | R2R_ODS_Availability = Yes | Table 4 [Rear Seat (with ODS)] |  |
| 8 | 2nd Row Right | Lv1_WarnInterruptFlag_R2R | R2R_ODS_Availability = No | Table 5 [Rear Seat (without ODS)] |  |
| 9 | 2nd Row Center | Lv1_WarnInterruptFlag_R2C | R2C_ODS_Availability = Yes | Table 4 [Rear Seat (with ODS)] |  |
| 10 | 2nd Row Center | Lv1_WarnInterruptFlag_R2C | R2C_ODS_Availability = No | Table 5 [Rear Seat (without ODS)] |  |
| 11 | 2nd Row Left | Lv1_WarnInterruptFlag_R2L | R2L_ODS_Availability = Yes | Table 4 [Rear Seat (with ODS)] |  |
| 12 | 2nd Row Left | Lv1_WarnInterruptFlag_R2L | R2L_ODS_Availability = No | Table 5 [Rear Seat (without ODS)] |  |
| 13 | 3rd Row Right | Lv1_WarnInterruptFlag_R3R | R3R_ODS_Availability = Yes | Table 4 [Rear Seat (with ODS)] |  |
| 14 | 3rd Row Right | Lv1_WarnInterruptFlag_R3R | R3R_ODS_Availability = No | Table 5 [Rear Seat (without ODS)] |  |
| 15 | 3rd Row Center | Lv1_WarnInterruptFlag_R3C | R3C_ODS_Availability = Yes | Table 4 [Rear Seat (with ODS)] |  |
| 16 | 3rd Row Center | Lv1_WarnInterruptFlag_R3C | R3C_ODS_Availability = No | Table 5 [Rear Seat (without ODS)] |  |
| 17 | 3rd Row Left | Lv1_WarnInterruptFlag_R3L | R3L_ODS_Availability = Yes | Table 4 [Rear Seat (with ODS)] |  |
| 18 | 3rd Row Left | Lv1_WarnInterruptFlag_R3L | R3L_ODS_Availability = No | Table 5 [Rear Seat (without ODS)] |  |
(*4) Refer to TFDCX32348-32201 for rear 1st row, TFDCX32348-32204 for rear 2nd row, TFDCX32348-32205 for rear 3rd row, to find 'Rear seat ODS availability'.
Table 4 [Rear Seat (with ODS)] (Flag should be maintained for each seat)
|  | Condition | Action |
| --- | --- | --- |
| 1 | IgnMode=OFF OR BklStat _R*_BZR=Buckled (*1) OR {'Whether to continue BZR while vehicle is parked'=No & ParkStat=Parked} OR {IgnMode=ON & SP1_in<=[S2] & AllDoor_R=AnyOpen} (*3) | Set Lv1_WarnInterruptFlag_R*=0 (*1) |
(*1)
For rear 1st row seat
BklStat_R*_BZR = BklStat_RR_BZR, BklStat_RC_BZR, BklStat_RL_BZR,
Lv1_WarnInterruptFlag_R* = Lv1_WarnInterruptFlag_RR, Lv1_WarnInterruptFlag_RC, Lv1_WarnInterruptFlag_RL, respectively.
For rear 2nd row seat
BklStat_R*_BZR = BklStat_R2R_BZR, BklStat_R2C_BZR, BklStat_R2L_BZR,
Lv1_WarnInterruptFlag_R* = Lv1_WarnInterruptFlag_R2R, Lv1_WarnInterruptFlag_R2C, Lv1_WarnInterruptFlag_R2L, respectively.
For rear 3rd row seat
BklStat_R*_BZR = BklStat_R3R_BZR, BklStat_R3C_BZR, BklStat_R3L_BZR,
Lv1_WarnInterruptFlag_R* = Lv1_WarnInterruptFlag_R3R, Lv1_WarnInterruptFlag_R3C, Lv1_WarnInterruptFlag_R3L, respectively.
Table 5 [Rear Seat (without ODS)] (Flag should be maintained for each seat)
|  | Condition | Action |
| --- | --- | --- |
| 1 | IgnMode=OFF OR UnbklFlag_R*_NODS_BZR=0 (*2) OR {'Whether to continue BZR while vehicle is parked'=No & ParkStat=Parked} OR {IgnMode=ON & SP1_in<=[S2] & AllDoor_R=AnyOpen} (*3) | Set Lv1_WarnInterruptFlag_R*=0 (*2) |
(*2)
For rear 1st row seat
UnbklFlag_R*_NODS_BZR = UnbklFlag_RR_NODS_BZR, UnbklFlag_RC_NODS_BZR, UnbklFlag_RL_NODS_BZR,
Lv1_WarnInterruptFlag_R* = Lv1_WarnInterruptFlag_RR, Lv1_WarnInterruptFlag_RC, Lv1_WarnInterruptFlag_RL, respectively.
For rear 2nd row seat
UnbklFlag_R*_NODS_BZR = UnbklFlag_R2R_NODS_BZR, UnbklFlag_R2C_NODS_BZR, UnbklFlag_R2L_NODS_BZR,
Lv1_WarnInterruptFlag_R* = Lv1_WarnInterruptFlag_R2R, Lv1_WarnInterruptFlag_R2C, Lv1_WarnInterruptFlag_R2L, respectively.
For rear 3rd row seat
UnbklFlag_R*_NODS_BZR = UnbklFlag_R3R_NODS_BZR, UnbklFlag_R3C_NODS_BZR, UnbklFlag_R3L_NODS_BZR,
Lv1_WarnInterruptFlag_R* = Lv1_WarnInterruptFlag_R3R, Lv1_WarnInterruptFlag_R3C, Lv1_WarnInterruptFlag_R3L, respectively.
(*3) In case of 'Communication Failure Status'=1 (Failed), use '0000h' for SP1_in, and as for 'Never Received Status', refer to TFDCX32348-32341 Data Reset .
- Verification Criteria: Verify by executing test cases
- Verification Method: Code/Design Review, System Qualification Test
- Verification Owner: FV
- System Requirement State: Approved
- Primary Discipline: SW
- ASIL Rating: QM

##### TFDCX32348-5647 (System Requirement)
Lv2_WarnInterruptFlag_DRV / PSG / FCTR / RR / RC / RL / R2R / R2C / R2L / R3R / R3C / R3L
(Level 2 warning buzzer interruption flag)
Front seats:
Lv2_WarnInterruptFlag_DRV / Lv2_WarnInterruptFlag_PSG / Lv2_WarnInterruptFlag_FCTR
Rear 1st row seats:
Lv2_WarnInterruptFlag_RR / Lv2_WarnInterruptFlag_RC / Lv2_WarnInterruptFlag_RL
Rear 2nd row seats:
Lv2_WarnInterruptFlag_R2R / Lv2_WarnInterruptFlag_R2C / Lv2_WarnInterruptFlag_R2L
Rear 3rd row seats:
Lv2_WarnInterruptFlag_R3R / Lv2_WarnInterruptFlag_R3C / Lv2_WarnInterruptFlag_R3L
Meter shall set the flags for each seat, based on the following table.
These flags are used in BZR Status Determination, especially to decide the vehicle speed threshold which is used when gear shift changes from 'R' to another and restart the warning buzzer.
These flags should be initialized as '0' at CPU Reset OR Wakeup.
Note: There are different conditions to set the value to these flags in BZR Status Determination. If the conditions defined here and in BZR Status Determination are met simultaneously, the ones defined here should be prioritized.
Table 1 [DRV]
|  | Condition | Action |
| --- | --- | --- |
| 1 | IgnMode=OFF OR BklStat_DRV_BZR=Buckled OR {'Whether to continue BZR while vehicle is parked'=No & ParkStat=Parked} OR {IgnMode=ON & SP1_in<=[S2] & Door_DRV=Open} (*3) | Set Lv2_WarnInterruptFlag_DRV=0 |
Table 2 [PSG] [FCTR] (Flag should be maintained for PSG, FCTR individually)
|  | Condition | Action |
| --- | --- | --- |
| 1 | IgnMode=OFF OR BklStat_**_BZR=Buckled (*5) OR {'Whether to continue BZR while vehicle is parked'=No & ParkStat=Parked} OR {IgnMode=ON & SP1_in<=[S2] & Door_PSG=Open} (*3) | Set Lv2_WarnInterruptFlag_**=0 (*5) |
(*5) BklStat_**_BZR = BklStatPSG_BZR, BklStat_FCTR_BZR
Lv2_WarnInterruptFlag_** = Lv2_WarnInterruptFlag_PSG, Lv2_WarnInterruptFlag_FCTR respectively.
Table 3 Rear Seat Processing Application Table
| # | Rear Seat | Lv2 Warning Interrupt Flag Name | ODS Availability Condition (*4) | Applied Processing Table | Remarks |
| --- | --- | --- | --- | --- | --- |
| 1 | 1st Row Right | Lv2_WarnInterruptFlag_RR | RR_ODS_Availability = Yes | Table 4 [Rear Seat (with ODS)] |  |
| 2 | 1st Row Right | Lv2_WarnInterruptFlag_RR | RR_ODS_Availability = No | Table 5 [Rear Seat (without ODS)] |  |
| 3 | 1st Row Center | Lv2_WarnInterruptFlag_RC | RC_ODS_Availability = Yes | Table 4 [Rear Seat (with ODS)] |  |
| 4 | 1st Row Center | Lv2_WarnInterruptFlag_RC | RC_ODS_Availability = No | Table 5 [Rear Seat (without ODS)] |  |
| 5 | 1st Row Left | Lv2_WarnInterruptFlag_RL | RL_ODS_Availability = Yes | Table 4 [Rear Seat (with ODS)] |  |
| 6 | 1st Row Left | Lv2_WarnInterruptFlag_RL | RL_ODS_Availability = No | Table 5 [Rear Seat (without ODS)] |  |
| 7 | 2nd Row Right | Lv2_WarnInterruptFlag_R2R | R2R_ODS_Availability = Yes | Table 4 [Rear Seat (with ODS)] |  |
| 8 | 2nd Row Right | Lv2_WarnInterruptFlag_R2R | R2R_ODS_Availability = No | Table 5 [Rear Seat (without ODS)] |  |
| 9 | 2nd Row Center | Lv2_WarnInterruptFlag_R2C | R2C_ODS_Availability = Yes | Table 4 [Rear Seat (with ODS)] |  |
| 10 | 2nd Row Center | Lv2_WarnInterruptFlag_R2C | R2C_ODS_Availability = No | Table 5 [Rear Seat (without ODS)] |  |
| 11 | 2nd Row Left | Lv2_WarnInterruptFlag_R2L | R2L_ODS_Availability = Yes | Table 4 [Rear Seat (with ODS)] |  |
| 12 | 2nd Row Left | Lv2_WarnInterruptFlag_R2L | R2L_ODS_Availability = No | Table 5 [Rear Seat (without ODS)] |  |
| 13 | 3rd Row Right | Lv2_WarnInterruptFlag_R3R | R3R_ODS_Availability = Yes | Table 4 [Rear Seat (with ODS)] |  |
| 14 | 3rd Row Right | Lv2_WarnInterruptFlag_R3R | R3R_ODS_Availability = No | Table 5 [Rear Seat (without ODS)] |  |
| 15 | 3rd Row Center | Lv2_WarnInterruptFlag_R3C | R3C_ODS_Availability = Yes | Table 4 [Rear Seat (with ODS)] |  |
| 16 | 3rd Row Center | Lv2_WarnInterruptFlag_R3C | R3C_ODS_Availability = No | Table 5 [Rear Seat (without ODS)] |  |
| 17 | 3rd Row Left | Lv2_WarnInterruptFlag_R3L | R3L_ODS_Availability = Yes | Table 4 [Rear Seat (with ODS)] |  |
| 18 | 3rd Row Left | Lv2_WarnInterruptFlag_R3L | R3L_ODS_Availability = No | Table 5 [Rear Seat (without ODS)] |  |
(*4) Refer to TFDCX32348-32201 for rear 1st row, TFDCX32348-32204 for rear 2nd row, TFDCX32348-32205 for rear 3rd row, to find 'Rear seat ODS availability'.
Table 4 [Rear Seat (with ODS)] (Flag should be maintained for each seat)
|  | Condition | Action |
| --- | --- | --- |
| 1 | IgnMode=OFF OR BklStat_R*_BZR=Buckled (*1) OR {'Whether to continue BZR while vehicle is parked'=No & ParkStat=Parked} OR {IgnMode=ON & SP1_in<=[S2] & AllDoor_R=AnyOpen} (*3) | Set Lv2_WarnInterruptFlag_R*=0 (*1) |
(*1)
For rear 1st row seat
BklStat_R*_BZR = BklStat_RR_BZR, BklStat_RC_BZR, BklStat_RL_BZR,
Lv2_WarnInterruptFlag_R* = Lv2_WarnInterruptFlag_RR, Lv2_WarnInterruptFlag_RC, Lv2_WarnInterruptFlag_RL, respectively.
For rear 2nd row seat
BklStat_R*_BZR = BklStat_R2R_BZR, BklStat_R2C_BZR, BklStat_R2L_BZR,
Lv2_WarnInterruptFlag_R* = Lv2_WarnInterruptFlag_R2R, Lv2_WarnInterruptFlag_R2C, Lv2_WarnInterruptFlag_R2L, respectively.
For rear 3rd row seat
BklStat_R*_BZR = BklStat_R3R_BZR, BklStat_R3C_BZR, BklStat_R3L_BZR,
Lv2_WarnInterruptFlag_R* = Lv2_WarnInterruptFlag_R3R, Lv2_WarnInterruptFlag_R3C, Lv2_WarnInterruptFlag_R3L, respectively.
Table 5 [Rear Seat (without ODS)] (Flag should be maintained for each seat)
|  | Condition | Action |
| --- | --- | --- |
| 1 | IgnMode=OFF OR UnbklFlag_R*_NODS_BZR=0 (*2) OR {'Whether to continue BZR while vehicle is parked'=No & ParkStat=Parked} OR {IgnMode=ON & SP1_in<=[S2] & AllDoor_R=AnyOpen} (*3) | Set Lv2_WarnInterruptFlag_R*=0 (*2) |
(*2)
For rear 1st row seat
UnbklFlag_R*_NODS_BZR = UnbklFlag_RR_NODS_BZR, UnbklFlag_RC_NODS_BZR, UnbklFlag_RL_NODS_BZR,
Lv2_WarnInterruptFlag_R* = Lv2_WarnInterruptFlag_RR, Lv2_WarnInterruptFlag_RC, Lv2_WarnInterruptFlag_RL, respectively.
For rear 2nd row seat
UnbklFlag_R*_NODS_BZR = UnbklFlag_R2R_NODS_BZR, UnbklFlag_R2C_NODS_BZR, UnbklFlag_R2L_NODS_BZR,
Lv2_WarnInterruptFlag_R* = Lv2_WarnInterruptFlag_R2R, Lv2_WarnInterruptFlag_R2C, Lv2_WarnInterruptFlag_R2L, respectively.
For rear 3rd row seat
UnbklFlag_R*_NODS_BZR = UnbklFlag_R3R_NODS_BZR, UnbklFlag_R3C_NODS_BZR, UnbklFlag_R3L_NODS_BZR,
Lv2_WarnInterruptFlag_R* = Lv2_WarnInterruptFlag_R3R, Lv2_WarnInterruptFlag_R3C, Lv2_WarnInterruptFlag_R3L, respectively.
(*3) In case of 'Communication Failure Status'=1 (Failed), use '0000h' for SP1_in, and as for 'Never Received Status', refer to TFDCX32348-32341 Data Reset .
- Verification Criteria: Verify by executing test cases
- Verification Method: Code/Design Review, System Qualification Test
- Verification Owner: FV
- System Requirement State: Approved
- Primary Discipline: SW
- ASIL Rating: QM

##### TFDCX32348-5649 (System Requirement)
GP_TimerCntFlag_DRV / PSG / FCTR / RR / RC / RL / R2R / R2C / R2L / R3R / R3C / R3L
(GP Timer Counting-up Flag)
Front seats:
GP_TimerCntFlag_DRV / GP_TimerCntFlag_PSG / GP_TimerCntFlag_FCTR
Rear 1st row seats:
GP_TimerCntFlag_RR / GP_TimerCntFlag_RC / GP_TimerCntFlag_RL
Rear 2nd row seats:
GP_TimerCntFlag_R2R / GP_TimerCntFlag_R2C / GP_TimerCntFlag_R2L
Rear 3rd row seats:
GP_TimerCntFlag_R3R / GP_TimerCntFlag_R3C / GP_TimerCntFlag_R3L
Meter shall set the flags for each seat, based on the following table.
These flags are used in BZR Status Determination to decide if 'GP_Timer_[XXX]' (Refer to FDCX32348-5651 ) should be counted up / stopped.
These flags should be initialized as '0' at CPU Reset OR Wakeup.
Note: There are different conditions to set the value to these flags in BZR Status Determination. If the conditions defined here and in BZR Status Determination are met simultaneously, the ones defined here should be prioritized.
Table 1 [DRV]
|  | Condition (*5) | Action |
| --- | --- | --- |
| 1 | IgnMode=ON AND 'GP applicability'=Yes AND ShiftStat=NotR AND SP1_in>=[S4] (*3) AND BklStat_DRV_BZR=Unbuckled AND {Lv1_WarnInterruptFlag_DRV=0 & Lv2_WarnInterruptFlag_DRV=0} | Set GP_TimerCntFlag_DRV=1 |
| 2 | IgnMode=OFF OR BklStat_DRV_BZR=Buckled OR {'Whether to continue BZR while vehicle is parked'=No & ParkStat=Parked} OR {IgnMode=ON & SP1_in<=[S2] & Door_DRV=Open} (*3) OR ShiftStat=R | Set GP_TimerCntFlag_DRV=0 |
Table 2 [PSG] [FCTR] (Flag should be maintained for PSG, FCTR individually)
|  | Condition (*5) | Action |
| --- | --- | --- |
| 1 | IgnMode=ON AND 'GP applicability'=Yes AND ShiftStat=NotR AND SP1_in>=[S4] (*3) AND BklStat_**_BZR=Unbuckled (*6) AND {Lv1_WarnInterruptFlag_**=0 & Lv2_WarnInterruptFlag_**=0} (*6) | Set GP_TimerCntFlag_**=1 (*6) |
| 2 | IgnMode=OFF OR BklStat_**_BZR=Buckled (*6) OR {'Whether to continue BZR while vehicle is parked'=No & ParkStat=Parked} OR {IgnMode=ON & SP1_in<=[S2] & Door_PSG=Open} (*3) OR ShiftStat=R | Set GP_TimerCntFlag_**=0 (*6) |
(*6) BklStat_**_BZR = BklStat_PSG_BZR, BklStat_FCTR_BZR
GP_TimerCntFlag_** = GP_TimerCntFlag_PSG, GP_TimerCntFlag_FCTR
Lv1_WarnInterruptFlag_** = Lv1_WarnInterruptFlag_PSG, Lv1_WarnInterruptFlag_FCTR
Lv2_WarnInterruptFlag_** = Lv2_WarnInterruptFlag_PSG, Lv2_WarnInterruptFlag_FCTR, respectively.
Table 3 Rear Seat Processing Application Table
| # | Rear Seat | GP Timer Count Flag Name | ODS Availability Condition (*4) | Applied Processing Table | Remarks |
| --- | --- | --- | --- | --- | --- |
| 1 | 1st Row Right | GP_TimerCntFlag_RR | RR_ODS_Availability = Yes | Table 4 [Rear Seat (with ODS)] |  |
| 2 | 1st Row Right | GP_TimerCntFlag_RR | RR_ODS_Availability = No | Table 5 [Rear Seat (without ODS)] |  |
| 3 | 1st Row Center | GP_TimerCntFlag_RC | RC_ODS_Availability = Yes | Table 4 [Rear Seat (with ODS)] |  |
| 4 | 1st Row Center | GP_TimerCntFlag_RC | RC_ODS_Availability = No | Table 5 [Rear Seat (without ODS)] |  |
| 5 | 1st Row Left | GP_TimerCntFlag_RL | RL_ODS_Availability = Yes | Table 4 [Rear Seat (with ODS)] |  |
| 6 | 1st Row Left | GP_TimerCntFlag_RL | RL_ODS_Availability = No | Table 5 [Rear Seat (without ODS)] |  |
| 7 | 2nd Row Right | GP_TimerCntFlag_R2R | R2R_ODS_Availability = Yes | Table 4 [Rear Seat (with ODS)] |  |
| 8 | 2nd Row Right | GP_TimerCntFlag_R2R | R2R_ODS_Availability = No | Table 5 [Rear Seat (without ODS)] |  |
| 9 | 2nd Row Center | GP_TimerCntFlag_R2C | R2C_ODS_Availability = Yes | Table 4 [Rear Seat (with ODS)] |  |
| 10 | 2nd Row Center | GP_TimerCntFlag_R2C | R2C_ODS_Availability = No | Table 5 [Rear Seat (without ODS)] |  |
| 11 | 2nd Row Left | GP_TimerCntFlag_R2L | R2L_ODS_Availability = Yes | Table 4 [Rear Seat (with ODS)] |  |
| 12 | 2nd Row Left | GP_TimerCntFlag_R2L | R2L_ODS_Availability = No | Table 5 [Rear Seat (without ODS)] |  |
| 13 | 3rd Row Right | GP_TimerCntFlag_R3R | R3R_ODS_Availability = Yes | Table 4 [Rear Seat (with ODS)] |  |
| 14 | 3rd Row Right | GP_TimerCntFlag_R3R | R3R_ODS_Availability = No | Table 5 [Rear Seat (without ODS)] |  |
| 15 | 3rd Row Center | GP_TimerCntFlag_R3C | R3C_ODS_Availability = Yes | Table 4 [Rear Seat (with ODS)] |  |
| 16 | 3rd Row Center | GP_TimerCntFlag_R3C | R3C_ODS_Availability = No | Table 5 [Rear Seat (without ODS)] |  |
| 17 | 3rd Row Left | GP_TimerCntFlag_R3L | R3L_ODS_Availability = Yes | Table 4 [Rear Seat (with ODS)] |  |
| 18 | 3rd Row Left | GP_TimerCntFlag_R3L | R3L_ODS_Availability = No | Table 5 [Rear Seat (without ODS)] |  |
(*4) Refer to TFDCX32348-32201 for rear 1st row, TFDCX32348-32204 for rear 2nd row, TFDCX32348-32205 for rear 3rd row, to find 'Rear seat ODS availability'.
Table 4 [Rear Seat (with ODS)] (Flag should be maintained for each seat)
|  | Condition (*5) | Action |
| --- | --- | --- |
| 1 | IgnMode=ON AND 'GP applicability'=Yes AND ShiftStat=NotR AND SP1_in>=[S4] (*3) AND BklStat_R*_ODS_BZR=Unbuckled (*1) AND {Lv1_WarnInterruptFlag_R*=0 & Lv2_WarnInterruptFlag_R*=0} (*1) | Set GP_TimerCntFlag_R*=1 (*1) |
| 2 | IgnMode=OFF OR BklStat_R*_ODS_BZR=Buckled OR {'Whether to continue BZR while vehicle is parked'=No & ParkStat=Parked} OR {IgnMode=ON & SP1_in<=[S2] & AllDoor_R=AnyOpen} (*3) OR ShiftStat=R | Set GP_TimerCntFlag_R*=0 (*1) |
(*1)
For rear 1st row seat
BklStat_R*_ODS_BZR = BklStat_RR_ODS_BZR, BklStat_RC_ODS_BZR, BklStat_RL_ODS_BZR,
Lv1_WarnInterruptFlag_R* = Lv1_WarnInterruptFlag_RR, Lv1_WarnInterruptFlag_RC, Lv1_WarnInterruptFlag_RL,
GP_TimerCntFlag_R* = GP_TimerCntFlag_RR, GP_TimerCntFlag_RC, GP_TimerCntFlag_RL, respectively.
For rear 2nd row seat
BklStat_R*_ODS_BZR = BklStat_R2R_ODS_BZR, BklStat_R2C_ODS_BZR, BklStat_R2L_ODS_BZR,
Lv1_WarnInterruptFlag_R* = Lv1_WarnInterruptFlag_R2R, Lv1_WarnInterruptFlag_R2C, Lv1_WarnInterruptFlag_R2L,
GP_TimerCntFlag_R* = GP_TimerCntFlag_R2R, GP_TimerCntFlag_R2C, GP_TimerCntFlag_R2L, respectively.
For rear 3rd row seat
BklStat_R*_ODS_BZR = BklStat_R3R_ODS_BZR, BklStat_R3C_ODS_BZR, BklStat_R3L_ODS_BZR,
Lv1_WarnInterruptFlag_R* = Lv1_WarnInterruptFlag_R3R, Lv1_WarnInterruptFlag_R3C, Lv1_WarnInterruptFlag_R3L,
GP_TimerCntFlag_R* = GP_TimerCntFlag_R3R, GP_TimerCntFlag_R3C, GP_TimerCntFlag_R3L, respectively.
Table 5 [Rear Seat (without ODS)] (Flag should be maintained for each seat)
|  | Condition (*5) | Action |
| --- | --- | --- |
| 1 | IgnMode=ON AND 'GP applicability'=Yes AND ShiftStat=NotR AND SP1_in>=[S4] (*3) AND UnbklFlag_R*_NODS_BZR=1 (*2) AND {Lv1_WarnInterruptFlag_R*=0 & Lv2_WarnInterruptFlag_R*=0} (*2) | Set GP_TimerCntFlag_R*=1 (*2) |
| 2 | IgnMode=OFF OR UnbklFlag_R*_NODS_BZR=0 (*2) OR {'Whether to continue BZR while vehicle is parked'=No & ParkStat=Parked} OR {IgnMode=ON & SP1_in<=[S2] & AllDoor_R=AnyOpen} (*3) OR ShiftStat=R | Set GP_TimerCntFlag_R*=0 (*2) |
(*2)
For rear 1st row seat
UnbklFlag_R*_NODS_BZR = UnbklFlag_RR_NODS_BZR, UnbklFlag_RC_NODS_BZR, UnbklFlag_RL_NODS_BZR,
Lv1_WarnInterruptFlag_R* = Lv1_WarnInterruptFlag_RR, Lv1_WarnInterruptFlag_RC, Lv1_WarnInterruptFlag_RL,
GP_TimerCntFlag_R* = GP_TimerCntFlag_RR, GP_TimerCntFlag_RC, GP_TimerCntFlag_RL, respectively.
For rear 2nd row seat
UnbklFlag_R*_NODS_BZR = UnbklFlag_R2R_NODS_BZR, UnbklFlag_R2C_NODS_BZR, UnbklFlag_R2L_NODS_BZR,
Lv1_WarnInterruptFlag_R* = Lv1_WarnInterruptFlag_R2R, Lv1_WarnInterruptFlag_R2C, Lv1_WarnInterruptFlag_R2L,
GP_TimerCntFlag_R* = GP_TimerCntFlag_R2R, GP_TimerCntFlag_R2C, GP_TimerCntFlag_R2L, respectively.
For rear 3rd row seat
UnbklFlag_R*_NODS_BZR = UnbklFlag_R3R_NODS_BZR, UnbklFlag_R3C_NODS_BZR, UnbklFlag_R3L_NODS_BZR,
Lv1_WarnInterruptFlag_R* = Lv1_WarnInterruptFlag_R3R, Lv1_WarnInterruptFlag_R3C, Lv1_WarnInterruptFlag_R3L,
GP_TimerCntFlag_R* = GP_TimerCntFlag_R3R, GP_TimerCntFlag_R3C, GP_TimerCntFlag_R3L, respectively.
(*3) In case of 'Communication Failure Status'=1 (Failed), use '0000h' for SP1_in, and as for 'Never Received Status', refer to TFDCX32348-32341 Data Reset .
(*5) Priority should be considered as No.1 > No.2 > Transition Condition in BZR Status Determination, if multiple conditions are satisfied simultaneously.
- Verification Criteria: Verify by executing test cases
- Verification Method: Code/Design Review, System Qualification Test
- Verification Owner: FV
- System Requirement State: Approved
- Primary Discipline: SW
- ASIL Rating: QM

##### TFDCX32348-5651 (System Requirement)
GP_Timer_DRV / PSG / FCTR / RR / RC / RL / R2R / R2C / R2L / R3R / R3C / R3L
(GP Timer)
Front seats:
GP_Timer_DRV / GP_Timer_PSG / GP_Timer_FCTR
Rear 1st row seats:
GP_Timer_RR / GP_Timer_RC / GP_Timer_RL
Rear 2nd row seats:
GP_Timer_R2R / GP_Timer_R2C / GP_Timer_R2L
Rear 3rd row seats:
GP_Timer_R3R / GP_Timer_R3C / GP_Timer_R3L
Meter shall reset/count-up the timers for each seat, based on the following table (This timer corresponds to [T20]).
These timers are used in BZR Status Determination to decide if Lv1 warning BZR should start sounding or not.
This timer should be initialized as '0' (not start counting-up) at CPU Reset OR Wakeup.
[DRV]
|  | Condition | Action |
| --- | --- | --- |
| 1 | GP_TimerCntFlag_DRV turns 0 -> 1 | Set GP_Timer_DRV=0 Start count-up GP_Timer_DRV |
| 2 | GP_TimerCntFlag_DRV=0 | Stop GP_Timer_DRV Set GP_Timer_DRV=0 |
[PSG] [FCTR] (Timer should be maintained for PSG, FCTR individulally)
|  | Condition | Action |
| --- | --- | --- |
| 1 | GP_TimerCntFlag_** turns 0 -> 1 (*2) | Set GP_Timer_**=0 (*2) Start count-up GP_Timer_** (*2) |
| 2 | GP_TimerCntFlag_**=0 (*2) | Stop GP_Timer_** (*2) Set GP_Timer_**=0 (*2) |
(*2) GP_TimerCntFlag_** = GP_TimerCntFlag_PSG, GP_TimerCntFlag_FCTR,
GP_Timer_** = GP_Timer_PSG, GP_Timer_FCTR, respectively.
[Rear Seat (Common to 'with ODS' & 'without ODS')] (Timer should be maintained for each seat)
|  | Condition | Action |
| --- | --- | --- |
| 1 | GP_TimerCntFlag_R* turns 0 -> 1 (*1) | Set GP_Timer_R*=0 (*1) Start count-up GP_Timer_R* |
| 2 | GP_TimerCntFlag_R*=0 | Stop GP_Timer_R* Set GP_Timer_R*=0 |
(*1)
For rear 1st row seat
GP_TimerCntFlag_R* = GP_TimerCntFlag_RR, GP_TimerCntFlag_RC, GP_TimerCntFlag_RL,
GP_Timer_R* = GP_Timer_RR, GP_Timer_RC, GP_Timer_RL, respectively.
For rear 2nd row seat
GP_TimerCntFlag_R* = GP_TimerCntFlag_R2R, GP_TimerCntFlag_R2C, GP_TimerCntFlag_R2L,
GP_Timer_R* = GP_Timer_R2R, GP_Timer_R2C, GP_Timer_R2L, respectively.
For rear 3rd row seat
GP_TimerCntFlag_R* = GP_TimerCntFlag_R3R, GP_TimerCntFlag_R3C, GP_TimerCntFlag_R3L,
GP_Timer_R* = GP_Timer_R3R, GP_Timer_R3C, GP_Timer_R3L, respectively.
- Verification Criteria: Verify by executing test cases
- Verification Method: Code/Design Review, System Qualification Test
- Verification Owner: FV
- System Requirement State: Approved
- Primary Discipline: SW
- ASIL Rating: QM

##### TFDCX32348-88271 (System Requirement)
Legal warning and other buzzer waiting time timer
| # | Input |  |  | Output |
| --- | --- | --- | --- | --- |
| # | Internal Parameter - Destination Group | Internal Signal - IgnMode | LegalWrn_WaitBzr_Timer count (TC) | LegalWrn_WaitBzr_Timer |
| 1 | G or H | OFF to ON | X | Set LegalWrn_WaitBzr_Timer=0 Start count-up LegalWrn_WaitBzr_Timer |
| 2 | G or H | ON | TC >= Wait duration for other BZR sounding [T17] | Stop LegalWrn_WaitBzr_Timer |
| 3 | G or H | ON | TC < Wait duration for other BZR sounding [T17] | No change |
| 4 | G or H | ON to OFF | X | Set LegalWrn_WaitBzr_Timer=0 |
| 5 | G or H | OFF | X | No change |
| 6 | Other than “G or H” | X | X | Stop LegalWrn_WaitBzr_Timer |
- Verification Criteria: Verify by executing test cases
- Verification Method: Code/Design Review, System Qualification Test
- Verification Owner: FV
- System Requirement State: Approved
- Primary Discipline: SW
- ASIL Rating: QM

#### TFDCX32348-3262: BZR Status Determination (Heading)

##### TFDCX32348-5653: State Transition for BZR (System Requirement)
State Transition for BZR
if Internal Parameter - Destination Group = A or B or C or D or E or F
Meter shall control the following state transition to determine BZR output.
State transition shall be maintained for each seat individually. (All the seats DRV, PSG, FCTR, RR, RC, RL, R2R, R2C, R2L, R3R, R3C, R3L)
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State Definition
|  | State Name | Description |
| --- | --- | --- |
| 1 | State A: OFF | BZR sounding stopped. |
| 2 | State B: Wait for other buzzer sounding | Wait while higher-priority BZR is sounding. |
| 3 | State C: Legally required wait | BZR is in non-sounding wait state while driver/passenger is buckling seatbelt. |
| 4 | State D: Legally required warning | Legally required BZR sounding when a seatbelt is unbuckled. |
| 5 | State E: End of legally required warning | Warning BZR sounding and legally required wait completed. |
| 6 | State F: Unbuckled notification | Single shot BZR generated when a seatbelt is unbuckled. |
| 7 | State G: GP | Grace Period until start of warning. |
| 8 | State H: Level 1 | BZR sounding start when a seatbelt is unbuckled while driving. |
| 9 | State I: Level 2 | Short-cycle BZR sounding when a seatbelt continues to be unbuckled while driving. |
| 10 | State J: Level 2 completed | Completion of short-cycle BZR sounding when a seatbelt continues to be unbuckled while driving. |
Note: Refer to TFDCX32348-3264 BZR Output Control to find the details of BZR output.
- Verification Criteria: Verify by executing test cases
- Verification Method: Code/Design Review, System Qualification Test
- Verification Owner: FV
- System Requirement State: Approved
- Primary Discipline: SW
- ASIL Rating: QM

##### TFDCX32348-89836: State Transition for BZR for FMVSS208 (System Requirement)
State Transition for BZR for FMVSS208
if Internal Parameter - Destination Group = G or H (New FMVSS208)
Meter shall control the following state transition to determine BZR output.
State transition shall be maintained for each seat individually. (All the seats DRV, PSG, RR, RC, RL, R2R, R2C, R2L, R3R, R3C, R3L)
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State Definition
|  | State Name | Description |
| --- | --- | --- |
| 1 | State A: OFF | BZR sounding stopped. |
| 2 | State B: Wait for other buzzer sounding | Wait while higher-priority BZR is sounding. |
| 3 | State C: Initial warning | Initial warning BZR sounding when a seatbelt is unbuckled. |
| 4 | State D: Initial warning finished | Initial warning BZR sounding is completed. |
| 5 | State E: Unbuckled notification | Before driving BZR sounding when a seatbelt is unbuckled. |
| 6 | State F: Unbuckled notification finished | Unbuckled notification BZR is finished. |
| 7 | State G: Level 1 | BZR sounding start when a seatbelt is unbuckled while driving. |
| 8 | State H: Level 2 | Short-cycle BZR sounding when a seatbelt continues to be unbuckled while driving. |
| 9 | State I: Level 2 interrupted | Interrupted due to judgment of vehicle stop state during Level2 sounding. |
| 10 | State J: Level 2 completed | Completion of short-cycle BZR sounding when a seatbelt continues to be unbuckled while driving. |
Note: Refer to TFDCX32348-3264 BZR Output Control to find the details of BZR output.
- Verification Criteria: Verify by executing test cases
- Verification Method: Code/Design Review, System Qualification Test
- Verification Owner: FV
- System Requirement State: Approved
- Primary Discipline: SW
- ASIL Rating: QM

##### TFDCX32348-32938: Transition Condition (System Requirement)
Transition Condition
Ver. 2.7 : Refer to the attachment - Toyota 12.3FDC SBR StateTransition Condition v2.7.xlsx.
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Change points from Toyota 38xD SBR StateTransition Condition v1.1.xlsx (specification for 38xD),
State transition conditions of BZR, TT(D_P), and TT_Rear) have not changed from 38xD logic. But followings change have been made.
(1) Front center seats, rear 2nd row seats, and rear 3rd row seats have been newly supported. (Supports totally 4 rows seats (front + 3 rear rows)).
(2) All the supported seats shall be always processed regardless of the actual seats arrangement. Buckled status CAN signals for not equipped seats are always sent as BUCKLED.
(3) For rear seats, ‘with ODS’ or ‘without ODS’ can be configured for each rear seat individually. State transition logic ‘Rear(with ODS)’ or ‘Rear(without ODS)' shall be applied for each rear seat individually according to the configuration. (*1)(*2)
(4) Related to (3), rear seat buckled status parameters for ‘with ODS’ and ‘without ODS’ are consolidated to common parameter.
BklStat_R*_ODS_BZR and BklStat_R*_NODS_BZR are consolidated to BklStat_R*_BZR.
BklStat_R*_ODS_TT and BklStat_R*_NODS_TT are consolidated to BklStat_R*_TT.
Consolidated parameters are commonly used for ‘with ODS’ and ‘without ODS’ processing.
(5) Added the BZR/TT sheet for corresponding New FMVSS208.
(*1) Refer to TFDCX32348-32201 for rear 1st row, TFDCX32348-32204 for rear 2nd row, TFDCX32348-32205 for rear 3rd row, to find 'Rear seat ODS availability'.
(*2) In the current customer specification, some logic is based on the assumption that setting of ‘with ODS’ or ‘without ODS’ is the same for all rear seats. However, ‘with ODS’ or ‘without ODS’ is determined by the customer specified parameters for each seat individually. If the setting is different for each rear seat, it is okay as long as it operates according to the customer specification.
- Verification Criteria: Verify by executing test cases
- Verification Method: Code/Design Review, System Qualification Test
- Verification Owner: FV
- System Requirement State: Approved
- Primary Discipline: SW
- ASIL Rating: QM

#### TFDCX32348-3264: BZR Output Control (Heading)

##### TFDCX32348-5657: BZR State & Output Correspondence (System Requirement)
BZR State & Output Correspondence
if Internal Parameter - Destination Group = A or B or C or D or E or F
Meter shall trigger the respective BZR output based on the 'State' and the below table. (For all seats, DRV, PSG, FCTR, RR, RC, RL, R2R, R2C, R2L, R3R, R3C, R3L)
| # | State Name | Output |  |  |  |  |
| --- | --- | --- | --- | --- | --- | --- |
| # | State Name | DRV | PSG | FCTR | Rear (with ODS) | Rear (without ODS) |
| 1 | InternalSignal - BuzzerTest_SBR = ON (*1) | BZR - SBR_Level1_BUZZER |  |  |  |  |
| 2 | State A: OFF | OFF | OFF | OFF | OFF | OFF |
| 3 | State B: Wait for other buzzer sounding | OFF | OFF | OFF | OFF | OFF |
| 4 | State C: Legally required wait | OFF | OFF | OFF | OFF | OFF |
| 5 | State D: Legally required warning | [BZ1] | [BZ2] | [BZ2] | OFF | OFF |
| 6 | State E: End of legally required warning | OFF | OFF | OFF | OFF | OFF |
| 7 | State F: Unbuckled notification | [BZ8] | [BZ8] | [BZ8] | [BZ8] | [BZ8] |
| 8 | State G: GP | OFF | OFF | OFF | OFF | OFF |
| 9 | State H: Level 1 | BZR - SBR_Level1_BUZZER | BZR - SBR_Level1_BUZZER | BZR - SBR_Level1_BUZZER | BZR - SBR_Level1_BUZZER | BZR - SBR_Level1_BUZZER |
| 10 | State I: Level 2 | BZR - SBR_Level2_BUZZER | BZR - SBR_Level2_BUZZER | BZR - SBR_Level2_BUZZER | BZR - SBR_Level2_BUZZER | BZR - SBR_Level2_BUZZER |
| 11 | State J: Level 2 completed | OFF | OFF | OFF | OFF | OFF |
(*1) Special state triggered from ETM mode SRD() to play SBR buzzer forcibly. When BuzzerTest_SBR = OFF, Meter shall work normally with the states of No.2 ~ 11.
- Verification Criteria: Verify by executing test cases
- Verification Method: Code/Design Review, System Qualification Test
- Verification Owner: FV
- System Requirement State: Approved
- Primary Discipline: SW
- ASIL Rating: QM

##### TFDCX32348-90624 (System Requirement)
BZR State & Output Correspondence for FMVSS208
if Internal Parameter - Destination Group = G or H (New FMVSS208)
Meter shall trigger the respective BZR output based on the 'State' and the below table. (For all seats, DRV, PSG, RR, RC, RL, R2R, R2C, R2L, R3R, R3C, R3L)
| # | State Name | Output |  |  |
| --- | --- | --- | --- | --- |
| # | State Name | DRV | PSG | Rear (without ODS) |
| 1 | InternalSignal - BuzzerTest_SBR = ON (*1) | BZR - SBR_Level1_BUZZER |  |  |
| 2 | State A: OFF | OFF | OFF | OFF |
| 3 | State B: Wait for other buzzer sounding | OFF | OFF | OFF |
| 4 | State C: Initial warning | BZR - SBR_Level1_BUZZER | BZR - SBR_Level1_BUZZER | OFF |
| 5 | State D: Initial warning finished | OFF | OFF | OFF |
| 6 | State E: Unbuckled notification | OFF | OFF | BZR - SBR_Level1_BUZZER |
| 7 | State F: Unbuckled notification finished | OFF | OFF | OFF |
| 8 | State G: Level 1 | BZR - SBR_Level1_BUZZER | BZR - SBR_Level1_BUZZER | BZR - SBR_Level1_BUZZER |
| 9 | State H: Level 2 | BZR - SBR_Level2_BUZZER | BZR - SBR_Level2_BUZZER | BZR - SBR_Level2_BUZZER |
| 10 | State I: Level 2 interrupted | OFF | OFF | OFF |
| 11 | State J: Level 2 completed | OFF | OFF | OFF |
(*1) Special state triggered from ETM mode SRD() to play SBR buzzer forcibly. When BuzzerTest_SBR = OFF, Meter shall work normally with the states of No.2 ~ 11.
- Verification Criteria: Verify by executing test cases
- Verification Method: Code/Design Review, System Qualification Test
- Verification Owner: FV
- System Requirement State: Approved
- Primary Discipline: SW
- ASIL Rating: QM

##### TFDCX32348-5659 (System Requirement)
BZR Output Determination (considering BZR customization)
Meter shall determine BZR output for each seat, considering BZR ON/OFF customization (Refer to TFDCX32348-2567: BZR Customization).
|  | Input | Output |  |  |  |
| --- | --- | --- | --- | --- | --- |
|  | SBRCustomBuzzer_[XXX] (*1) | BZR - SBR_Legally_Required_BUZZER | BZR - SBR_Level2_BUZZER | BZR - SBR_Level1_BUZZER | BZR - SBR_Unbuckled_Notify_BUZZER |
| 1 | ON | (Follow output for each 'State') | (Follow output for each 'State') | (Follow output for each 'State') | (Follow output for each 'State') |
| 2 | OFF | (Follow output for each 'State') | OFF | OFF | OFF |
(*1) [XXX] = DRV, PSG, FCTR, RR, RC, RL, R2R, R2C, R2L, R3R, R3C, R3L
- Verification Criteria: Verify by executing test cases
- Verification Method: Code/Design Review, System Qualification Test
- Verification Owner: FV
- System Requirement State: Approved
- Primary Discipline: SW
- ASIL Rating: QM

##### TFDCX32348-5661: Detailed Operation (System Requirement)
Detailed Operation
if Internal Parameter - Destination Group = A or B or C or D or E or F
|  | Item | Requirement |
| --- | --- | --- |
| 1 | Delay to judge sound condition | None |
| 2 | In case of sound condition not met | [BZR - SBR_Legally_Required_BUZZER] Complete sounding current cycle, then Stop [BZR - SBR_Level2_BUZZER] - Complete sounding current cycle, then Stop (In case of transition to 'State J: Level2 completed') - Stop immediately (Other than above case) [BZR - SBR_Level1_BUZZER] Stop immediately [BZR - SBR_Unbuckled_Notify_BUZZER] Complete sounding for the entire period |
| 3 | In case of switch to high-priority buzzer (*1) | [BZR - SBR_Legally_Required_BUZZER] N/A (Highest priority within SBR-related buzzers) [BZR - SBR_Level2_BUZZER] Stop immediately (Switching from this buzzer to SBR_Legally_Required_BUZZER happens based on state transition) (*2) [BZR - SBR_Level1_BUZZER] Stop immediately (Switching from this buzzer to SBR_Level2_BUZZER/SBR_Legally_Required_BUZZER(*2) happens based on state transition and not based on priority arbitration) (SYS OIL#140-14) [BZR - SBR_Unbuckled_Notify_BUZZER] Complete sounding for the entire period |
(*1) Since SBR-related buzzers are assigned to a separate channel from other buzzers, switching to high-priority buzzer happens only between SBR-related buzzers.
(*2) This change does not require to update the current code, but considering combination of the other seat status, possible to switch to SBR_Legally_Required_BUZZER. Refet to the impediment T38XD29284-63582: Regarding for Seat belt for the detail.
- Verification Criteria: Verify by executing test cases
- Verification Method: Code/Design Review, System Qualification Test
- Verification Owner: FV
- System Requirement State: Approved
- Primary Discipline: SW
- ASIL Rating: QM

##### TFDCX32348-90695: Detailed Operation for FMVSS208 (System Requirement)
Detailed Operation for FMVSS208
if Internal Parameter - Destination Group = G or H (New FMVSS208)
|  | Item | Requirement |
| --- | --- | --- |
| 1 | Delay to judge sound condition | None |
| 2 | In case of sound condition not met | [BZR - SBR_Level2_BUZZER] - Complete sounding current cycle, then Stop [BZR - SBR_Level1_BUZZER] - Complete sounding current cycle, then Stop |
| 3 | In case of switch to high-priority buzzer (*1) | [BZR - SBR_Level2_BUZZER] - N/A (Highest priority within SBR-related buzzers) [BZR - SBR_Level1_BUZZER] - Stop immediately (Switching from this buzzer to SBR_Level2_BUZZER happens based on state transition and not based on priority arbitration) |
(*1) Since SBR-related buzzers are assigned to a separate channel from other buzzers, switching to high-priority buzzer happens only between SBR-related buzzers.
- Verification Criteria: Verify by executing test cases
- Verification Method: Code/Design Review, System Qualification Test
- Verification Owner: FV
- System Requirement State: Approved
- Primary Discipline: SW
- ASIL Rating: QM

##### TFDCX32348-5663 (System Requirement)
Detailed Operation for Unbuckled Notification BZR
If sounding condition for Unbuckled Notification BZR is met for a certain seat while the same BZR is sounding in another seat, Meter shall ignore the succeeding trigger and shall not sound BZR for the succeeding one.
Example: P-Seat sounding condition met while BZR sounding for D-Seat
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- Verification Criteria: Verify by executing test cases
- Verification Method: Code/Design Review, System Qualification Test
- Verification Owner: FV
- System Requirement State: Approved
- Primary Discipline: SW
- ASIL Rating: QM

##### TFDCX32348-5665: Switching Buzzer - 0.3s Silent Time (System Requirement)
Switching Buzzer - 0.3s Silent Time
Meter shall decide if '0.3s Silent Time' should be applied or not based on the below table.
|  | Condition | 0.3s Silent Time |
| --- | --- | --- |
| 1 | All buzzers (incl. SBR buzzers) -> SBR buzzers | N/A |
| 2 | SBR buzzers -> Other buzzers | Applicable |
- Verification Criteria: Verify by executing test cases
- Verification Method: Code/Design Review, System Qualification Test
- Verification Owner: FV
- System Requirement State: Approved
- Primary Discipline: SW
- ASIL Rating: QM

##### TFDCX32348-5669: Sounding Synchronization While BZR Sounding for Other Seat (for Lv1,Lv2 Warning) (System Requirement)
Sounding Synchronization While BZR Sounding for Other Seat (for Lv1, Lv2 Warning)
If a BZR sounding condition is met in a certain seat while the same type of BZR is sounding in another seat,
- BZR cycle time
- BZR sound timing
shall be synchronized with the BZR that is currently sounding.
- Verification Criteria: Verify by executing test cases
- Verification Method: Code/Design Review, System Qualification Test
- Verification Owner: FV
- System Requirement State: Approved
- Primary Discipline: SW
- ASIL Rating: QM

##### TFDCX32348-5671: Volume setting for sound file (TBD) (System Requirement)
Volume setting for sound file (TBD)
Use maximum volume setting for now.
( Toyota_12.3FDC_BuzzerPriorityTable_v***.xlsx (TFDCX32348-5166: Buzzer Priority Table & Sound Files ) )
| Cfg - region_Group | Volume setting(*1) |  |
| --- | --- | --- |
| Cfg - region_Group | MET-TBZ_SEAREM-LV1-24-01.wav | MET-TBZ_SEAREM-LV2-24-01.wav |
| 0:380D | 233 | 248 |
| 2: 382D / 4: 384D | 220 | 235 |
| Other than above | not used | not used |
(*1) Same as Volume setting in Buzzer Priority Table sheet "SPLTuningResult".
- Verification Criteria: Verify by executing test cases
- Verification Method: Code/Design Review, System Qualification Test
- Verification Owner: FV
- System Requirement State: Approved
- Primary Discipline: SW
- ASIL Rating: QM

#### TFDCX32348-3266: TT Status Determination (Heading)

##### TFDCX32348-5673: State Transition for TT (D/P/FrCtr-Seat) (System Requirement)
State Transition for TT (D/P/FrCtr-Seat)
if Internal Parameter - Destination Group = A or B or C or D or E or F
Meter shall control the following state transition to determine TT output for D/P/FCTR Seat.
State transition shall be maintained for each seat individually.
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Note: 'Cond. eg' & 'Cond. eh' don't occur in actual vehicle scenarios, but they are also supposed to be implemented for future extension.
State Definition
|  | State Name | Description |
| --- | --- | --- |
| 1 | State a-1: No indication | TT output OFF. |
| 2 | State b: Wait for other buzzer sounding | Wait while higher-priority BZR is sounding. |
| 3 | State c: Legally required wait | Wait for TT output OFF while user is buckling seatbelt. |
| 4 | State d: Legally required warning | Legally required TT blinking when a seatbelt is unbuckled. |
| 5 | State e: End of legally required warning | Legally required warning TT blinking and legally required wait completed. |
| 6 | State f: Level 1 while driving | TT indication during Unbuckled notification/Level 1 BZR. |
| 7 | State g: Level 2 while driving | TT indication during Level 2 BZR. |
| 8 | State h: Level 2 completed | TT indication after Level 2 BZR completion. |
| 9 | State i: Level 1 while vehicle stopped | Unbuckled TT indication while vehicle parked |
| 10 | State j: Level 2 while vehicle stopped | Unbuckled TT indication when vehicle not parked. |
Note: Refer to TFDCX32348-3268 TT Output Control to find the details of TT output.
- Verification Criteria: Verify by executing test cases
- Verification Method: Code/Design Review, System Qualification Test
- Verification Owner: FV
- System Requirement State: Approved
- Primary Discipline: SW
- ASIL Rating: QM

##### TFDCX32348-5675: Transition Condition (System Requirement)
Transition Condition
Transition Condition for TT is maintained in the same file for BZR.
Refer to TFDCX32348-32938
- Verification Criteria: Verify by executing test cases
- Verification Method: Code/Design Review, System Qualification Test
- Verification Owner: FV
- System Requirement State: Approved
- Primary Discipline: SW
- ASIL Rating: QM

##### TFDCX32348-5677: State Transition for TT (Rear Seat) (System Requirement)
State Transition for TT (Rear Seat)
if Internal Parameter - Destination Group = A or B or C or D or E or F
Meter shall control the following state transition to determine TT output for Rear Seat.
State transition shall be maintained for each seat individually. (RR, RC, RL, R2R, R2C, R2L, R3R, R3C, R3L)
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State Definition
|  | State Name | Description |
| --- | --- | --- |
| 1 | State a-2: No indication | Rear seat TT output OFF. |
| 2 | State k: Indication for fixed time after IG-ON | TT indication for fixed time when occupant assumed in rear seat. |
| 3 | State l: Indication after door open/door close | TT indication when rear door opened and TT indication for fixed time when rear door closed edge occurs. |
| 4 | State n: Level 1 indication while vehicle stopped | TT indication when rear seatbelt unbuckled. |
| 5 | State o: Indication of state interlocked with other rear seat | TT indication when other rear seatbelt buckling state changes. |
| 6 | State p: Level 1 while driving | TT indication during Unbuckled notification/Level 1 BZR. |
| 7 | State q: Level 2 while driving | TT indication during Level 2 BZR. |
| 8 | State r: Level 2 completed | TT indication after Level 2 BZR completion. |
| 9 | State s: Level 2 indication while vehicle stopped | TT indication when vehicle not parked. |
Note: Refer to TFDCX32348-3268 TT Output Control to find the details of TT output.
- Verification Criteria: Verify by executing test cases
- Verification Method: Code/Design Review, System Qualification Test
- Verification Owner: FV
- System Requirement State: Approved
- Primary Discipline: SW
- ASIL Rating: QM

##### TFDCX32348-5678: Transition Condition (System Requirement)
Transition Condition
Transition Condition for TT is maintained in the same file for BZR.
Refer to TFDCX32348-32938
- Verification Criteria: Verify by executing test cases
- Verification Method: Code/Design Review, System Qualification Test
- Verification Owner: FV
- System Requirement State: Approved
- Primary Discipline: SW
- ASIL Rating: QM

##### TFDCX32348-89945 (System Requirement)
State Transition for TT (Rear Seat) for FMVSS208
if Internal Parameter - Destination Group = G or H (New FMVSS208)
Meter shall control the following state transition to determine TT output for Rear Seat.
State transition shall be maintained for each seat individually. (RR, RC, RL, R2R, R2C, R2L, R3R, R3C, R3L)
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State Definition
|  | State Name | Description |
| --- | --- | --- |
| 1 | State a: No indication | Driver/passenger/Rear seat TT output OFF. |
| 2 | State b: Wait for other buzzer sounding | Wait while higher-priority BZR is sounding. |
| 3 | State c: Initial warning | BZR sounding and blinking for unbuckled the driver, passenger seat. |
| 4 | State d: Initial warning finished | TT indication after Driver, Passenger initial warning blinking |
| 5 | State e: Indication for fixed time after IG-ON | TT indication for fixed time when occupant assumed in rear seat. |
| 6 | State f: Indication after door open/door close | TT indication when rear door opened and TT indication for fixed time when rear door closed edge occurs. |
| 7 | State g: Unbuckled warning display | TT blinking when driver, passenger, rear seats are unbuckled. |
| 8 | State h: Level 1 while driving | TT indication during Level 1 BZR. |
| 9 | State i: Level 2 while driving | TT indication during Level 2 BZR. |
| 10 | State j: Level 2 interrupted | TT indication during Level 2 BZR stopping. |
| 11 | State k: Level 2 completed | TT indication during Level 2 BZR for rear. |
Note: Refer to TFDCX32348-3268 TT Output Control to find the details of TT output.
- Verification Criteria: Verify by executing test cases
- Verification Method: Code/Design Review, System Qualification Test
- Verification Owner: FV
- System Requirement State: Approved
- Primary Discipline: SW
- ASIL Rating: QM

##### TFDCX32348-89946: Transition Condition for FMVSS208 (System Requirement)
Transition Condition for FMVSS208
Transition Condition for TT is maintained in the same file for BZR.
Refer to TFDCX32348-32938
- Verification Criteria: Verify by executing test cases
- Verification Method: Code/Design Review, System Qualification Test
- Verification Owner: FV
- System Requirement State: Approved
- Primary Discipline: SW
- ASIL Rating: QM

#### TFDCX32348-3268: TT Output Control (Heading)

##### TFDCX32348-5680 (System Requirement)
TT State & Output Correspondence (D/P/FrCtr-Seat)
if Internal Parameter - Destination Group = A or B or C or D or E or F
Meter shall trigger the respective TT output based on the 'State' and the below table.
| # | State Name | Output |  |  |
| --- | --- | --- | --- | --- |
| # | State Name | Internal Signal - SBRTTStatus (*1) |  |  |
| # | State Name | DRV | PSG | FCTR |
| 1 | State a-1: No indication | OFF | OFF | OFF |
| 2 | State b: Wait for other buzzer sounding | OFF | OFF | OFF |
| 3 | State c: Legally required wait | OFF | OFF | OFF |
| 4 | State d: Legally required warning | [TT1] | [TT7] | [TT7] |
| 5 | State e: End of legally required warning | OFF | OFF | OFF |
| 6 | State f: Level 1 while driving | [TT2] | [TT8] | [TT8] |
| 7 | State g: Level 2 while driving | [TT3] | [TT9] | [TT9] |
| 8 | State h: Level 2 completed | [TT4] | [TT10] | [TT10] |
| 9 | State i: Level 1 while vehicle stopped | [TT5] | [TT11] | [TT11] |
| 10 | State j: Level 2 while vehicle stopped | [TT6] | [TT12] | [TT12] |
(*1) Since the single LED TT hole is shared for D/P/FrCtr-Seats, output arbitration is required when output is different among the three seats. Refer to TFDCX32348-5684 to find the detailed requirement.
- Verification Criteria: Verify by executing test cases
- Verification Method: Code/Design Review, System Qualification Test
- Verification Owner: FV
- System Requirement State: Approved
- Primary Discipline: SW
- ASIL Rating: QM

##### TFDCX32348-5682 (System Requirement)
TT State & Output Correspondence (Rear Seat)
if Internal Parameter - Destination Group = A or B or C or D or E or F
Meter shall trigger the respective TT output based on the 'State' and the below table.
| # | State Name | Output |  |
| --- | --- | --- | --- |
| # | State Name | Internal Parameter - SBRTTStatus_R* (*1) |  |
| # | State Name | Rear (with ODS) (*2) | Rear (without ODS) (*2) |
| 1 | State a-2: No indication | OFF | OFF |
| 2 | State k: Indication for fixed time after IG-ON | N/A | [TT36] |
| 3 | State l: Indication after door open/door close | [TT37] | [TT37] |
| 4 | State n: Level 1 indication while vehicle stopped | [TT23] | [TT23] |
| 5 | State o: Indication of state interlocked with other rear seat | [TT38] | [TT38] |
| 6 | State p: Level 1 while driving | [TT20] | [TT20] |
| 7 | State q: Level 2 while driving | [TT21] | [TT21] |
| 8 | State r: Level 2 completed | [TT25] | [TT22] |
| 9 | State s: Level 2 indication while vehicle stopped | [TT24] | [TT24] |
(*1) SBRTTStatus_R* = SBRTTStatus_RR, SBRTTStatus_RC, SBRTTStatus_RL. SBRTTStatus_R2R, SBRTTStatus_R2C, SBRTTStatus_R2L. SBRTTStatus_R3R, SBRTTStatus_R3C, SBRTTStatus_R3L.
(*2) With or without ODS shall be switched for each rear seat.
Refer to TFDCX32348-32201 for rear 1st row. (RR_ODS_Availability, RC_ODR_Availablitiy, RL_ODS_Availability)
Refer to TFDCX32348-32204 for rear 2nd row. (R2R_ODS_Availability, R2C_ODR_Availablitiy, R2L_ODS_Availability)
Refer to TFDCX32348-32205 for rear 3rd row. (R3R_ODS_Availability, R3C_ODR_Availablitiy, R3L_ODS_Availability,)
- Verification Criteria: Verify by executing test cases
- Verification Method: Code/Design Review, System Qualification Test
- Verification Owner: FV
- System Requirement State: Approved
- Primary Discipline: SW
- ASIL Rating: QM

##### TFDCX32348-90708 (System Requirement)
TT State & Output Correspondence (D/P/Rear Seat) for FMVSS208
if Internal Parameter - Destination Group = G or H (New FMVSS208)
Meter shall trigger the
respective TT output based on the 'State' and the below table.
| # | State Name | Output |  |  |
| --- | --- | --- | --- | --- |
| # | State Name | Internal Signal - SBRTTStatus_DRV | Internal Signal - SBRTTStatus_PSG | Internal Parameter - SBRTTStatus_R* (*1) |
| # | State Name | Internal Signal - SBRTTStatus_DRV | Internal Signal - SBRTTStatus_PSG | Rear (without ODS) (*2) |
| 1 | State a: No indication | OFF | OFF | If ( (BlkStat_R*_TT = Unbuckled) && ( (TT state of any of other rear seats = state_e && TT36 != OFF) \|\| (TT state of any of other rear seats = state_f && TT37 != OFF) \|\| (TT state of any of other rear seats = state_g && TTF2 != OFF) \|\| (TT state of any of other rear seats = state_h && TT20 != OFF) \|\| (TT state of any of other rear seats = state_i && TT21 != OFF) \|\| (TT state of any of other rear seats = state_j && TTF3 != OFF) \|\| (TT state of any of other rear seats = state_k && TT22 != OFF) ) ) { ON } else { OFF } |
| 2 | State b: Wait for other buzzer sounding | OFF | OFF | OFF |
| 3 | State c: Initial warning | [TTF1] | [TTF1] | OFF |
| 4 | State d: Initial warning finished | [TTF1] | [TTF1] | OFF |
| 5 | State e: Indication for fixed time after IG-ON | OFF | OFF | [TT36] |
| 6 | State f: Indication after door open/door close | OFF | OFF | [TT37] |
| 7 | State g: Unbuckled warning display | [TTF2] | [TTF2] | [TTF2] |
| 8 | State h: Level 1 while driving | [TT2] | [TT8] | [TT20] |
| 9 | State i: Level 2 while driving | [TT3] | [TT9] | [TT21] |
| 10 | State j: Level 2 interrupted | [TT4] | [TT10] | [TTF3] |
| 11 | State k: Level 2 completed | OFF | OFF | If ( (BlkStat_R*_TT = Unbuckled) && ( (TT state of any of other rear seats = state_e && TT36 != OFF) \|\| (TT state of any of other rear seats = state_f && TT37 != OFF) \|\| (TT state of any of other rear seats = state_g && TTF2 != OFF) \|\| (TT state of any of other rear seats = state_h && TT20 != OFF) \|\| (TT state of any of other rear seats = state_i && TT21 != OFF) \|\| (TT state of any of other rear seats = state_j && TTF3 != OFF) ) ) { ON } else { TT22 } |
(*1) SBRTTStatus_R* = SBRTTStatus_RR, SBRTTStatus_RC, SBRTTStatus_RL. SBRTTStatus_R2R, SBRTTStatus_R2C, SBRTTStatus_R2L. SBRTTStatus_R3R, SBRTTStatus_R3C, SBRTTStatus_R3L.
(*2) With or without ODS shall be switched for each rear seat.
Refer to TFDCX32348-32201 for rear 1st row. (RR_ODS_Availability, RC_ODR_Availablitiy, RL_ODS_Availability)
Refer to TFDCX32348-32204 for rear 2nd row. (R2R_ODS_Availability, R2C_ODR_Availablitiy, R2L_ODS_Availability)
Refer to TFDCX32348-32205 for rear 3rd row. (R3R_ODS_Availability, R3C_ODR_Availablitiy, R3L_ODS_Availability,)
- Verification Criteria: Verify by executing test cases
- Verification Method: Code/Design Review, System Qualification Test
- Verification Owner: FV
- System Requirement State: Approved
- Primary Discipline: SW
- ASIL Rating: QM

##### TFDCX32348-5684 (System Requirement)
Switching TT Output - Priority Arbitration (D/P/FrCtr-Seat)
if Internal Parameter - Destination Group = A or B or C or D or E or F
Meter shall select TT output based on the below table when TT output of D-Seat & P-Seat & FCTR-Seat are different (as the single LED TT hole is shared for both seats).
|  | Priority ('1':Highest -> '9':Lowest) | TT State | Switch to High-priority TT |
| --- | --- | --- | --- |
| 1 | 1 | InternalSignal - All_Telltale_ON test = ON | Switch immediately |
| 2 | 2 | State b: Wait for other buzzer sounding | Switch immediately |
| 3 | 3 | State d: Legally required warning | Refer to TFDCX32348-5686 . |
| 4 | 4 | State g: Level 2 while driving | Refer to TFDCX32348-5686 . |
| 5 | 5 | State f: Level 1 while driving | Refer to TFDCX32348-5686 . |
| 6 | 6 | State j: Level 2 while vehicle stopped | Refer to TFDCX32348-5686 . |
| 7 | 7 | State i: Level 1 while vehicle stopped | Refer to TFDCX32348-5686 . |
| 8 | 8 | State h: Level 2 completed | Refer to TFDCX32348-5686 . |
| 9 | 9 | State c: Legally required wait | Switch immediately |
| 10 | 10 | State e: End of legally required warning | Switch immediately |
| 11 | 11 | State a-2: No indication | Switch immediately |
Example: If TT state of D-Seat is 'State b' (i.e. TT output is 'OFF') & TT state of P-Seat is 'State f' (i.e. TT output is 'Lv1-Blink') & TT state of FCTR-Seat is 'State f' , TT output finally indicated in LED TT is 'OFF'.
- Verification Criteria: Verify by executing test cases
- Verification Method: Code/Design Review, System Qualification Test
- Verification Owner: FV
- System Requirement State: Approved
- Primary Discipline: SW
- ASIL Rating: QM

##### TFDCX32348-5686 (System Requirement)
Switching TT Output - Synchronization with TT/BZR (Common to All Seats)
If TT output is about to change from one to another, Meter shall control TT output as defined below (considering TT output type, BZR output etc.).
In case of blinking,
- TT blink cycle time
- TT blink timing
shall be synchronized for all seats.
[Output about to switch to 'ON']
Turn 'ON' immediately
Example: TT for RR-Seat turns ON while TT for D-Seat is indicated as ON.
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[Output about to switch to 'Lv1-Blink']
|  | Switch Condition | Switch to Next State | Remark |
| --- | --- | --- | --- |
| 1 | When TT output of any of other seats is 'Lv1-Blink' | Start blinking while synchronizing with blink cycle of already blinking TT |  |
| 2 | When 'BZR - SBR_Level1_BUZZER' is sounding as the highest priority one among all SBR-related buzzers | Start blinking while synchronizing with sounding cycle of 'BZR - SBR_Level1_BUZZER' |  |
| 3 | other than No.1, 2 | Start blinking immediately |  |
Example: TT for RR-Seat starts blinking (Lv1) while TT for D-Seat is blinking (Lv1).
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[Output about to switch to 'Lv2-Blink']
|  | Switch Condition | Switch to Next State | Remark |
| --- | --- | --- | --- |
| 1 | When TT output of any of other seats is 'Lv2-Blink' | Start blinking while synchronizing with blink cycle of already blinking TT |  |
| 2 | When 'BZR - SBR_Level2_BUZZER' is sounding as the highest priority one among all SBR-related buzzers | Start blinking while synchronizing with sounding cycle of 'BZR - SBR_Level2_BUZZER' |  |
| 3 | other than No.1, 2 | Start blinking immediately |  |
Example: TT for RR-Seat starts blinking (Lv2) while TT for D-Seat is blinking (Lv2).
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- Verification Criteria: Verify by executing test cases
- Verification Method: Code/Design Review, System Qualification Test
- Verification Owner: FV
- System Requirement State: Approved
- Primary Discipline: SW
- ASIL Rating: QM

##### TFDCX32348-33006 (System Requirement)
Rear Seat Belt Indicator Type Determination
| # | Input |  | Output |
| --- | --- | --- | --- |
| # | MCUCONST - MCUID1138 | Internal Parameter - Destination Group | HMI - RearBeltIndType |
| 1 | 0 | G or H | BELT_401 |
| 2 | 0 | Other than G or H | BELT_233_294 |
| 3 | 1 | G or H | BELT_401 |
| 4 | 1 | Other than G or H | BELT_233_235 |
| 5 | 2 | G or H | BELT_402 |
| 6 | 2 | Other than G or H | BELT_233_XXX |
| 7 | 3 (other than above) | G or H | BELT_403 |
| 8 | 3 (other than above) | Other than G or H | BELT_233_NONE |
- Verification Criteria: Verify by executing test cases
- Verification Method: Code/Design Review, System Qualification Test
- Verification Owner: FV
- System Requirement State: Approved
- Primary Discipline: SW
- ASIL Rating: QM

##### TFDCX32348-34617: Seat Belt Indicator On/Off Status Output (System Requirement)
Seat Belt Indicator On/Off Status Output
if Internal Parameter - Destination Group = A or B or C or D or E or F
Front Seat Belt Indicator
| # | Input | Output | Remarks |
| --- | --- | --- | --- |
| # | Internal Parameter - SBRTTStatus ( TFDCX32348-5680) | HMI - SBRTelltale_DRV | Remarks |
| 1 | OFF | OFF |  |
| 2 | ON | ON |  |
| 3 | OFF period of Lv1/Lv2-blink | OFF |  |
| 4 | ON period of Lv1/Lv2-blink | ON |  |
Rear Seat Belt Indicator
| # | Input | Output | Remarks |
| --- | --- | --- | --- |
| # | Internal Parameter - SBRTTStatus_R* (*1) ( TFDCX32348-5682 ) | HMI - SBRTelltale_R* (*1) | Remarks |
| 1 | OFF | OFF |  |
| 2 | ON | ON |  |
| 3 | OFF period of Lv1/Lv2-blink | OFF |  |
| 4 | ON period of Lv1/Lv2-blink | ON |  |
(*1)
SBRTTStatus_R* = SBRTTStatus_RL, SBRTTStatus_RC, SBRTTStatus_RR, SBRTTStatus_R2L, SBRTTStatus_R2C, SBRTTStatus_R2R, SBRTTStatus_R3L, SBRTTStatus_R3C, SBRTTStatus_R3R
SBRTelltale_R* = SBRTelltale_RL, SBRTelltale_RC, SBRTelltale_RR, SBRTelltale_R2L, SBRTelltale_R2C, SBRTelltale_R2R, SBRTelltale_R3L, SBRTelltale_R3C, SBRTelltale_R3R respectively.
Rear Seat Belt Indicator Frame
| # | Input | Output | Remarks |
| --- | --- | --- | --- |
| # | Internal Parameter - SBRTTStatus_R* (*1) | HMI - SBRBlinkStatus | Remarks |
| 1 | All of the statuses are OFF | OFF |  |
| 2 | Any of the status is ON or Lv1/Lv2-blink | ON | Output ON even during the OFF period of Lv1/Lv2-blink. |
(*1) SBRTTStatus_R* = Any of SBRTTStatus_RL, SBRTTStatus_RC, SBRTTStatus_RR, SBRTTStatus_R2L, SBRTTStatus_R2C, SBRTTStatus_R2R, SBRTTStatus_R3L, SBRTTStatus_R3C, SBRTTStatus_R3R
- Verification Criteria: Verify by executing test cases
- Verification Method: Code/Design Review, System Qualification Test
- Verification Owner: FV
- System Requirement State: Approved
- Primary Discipline: SW
- ASIL Rating: QM

##### TFDCX32348-95099 (System Requirement)
Seat Belt Indicator On/Off Status Output for FMVSS208
if Internal Parameter - Destination Group = G or H (New FMVSS208)
Front Seat Belt Indicator
| # | Input | Output | Remarks |
| --- | --- | --- | --- |
| # | Internal Parameter - SBRTTStatus_DRV ( TFDCX32348-90708 ) | HMI - SBRTelltale_DRV | Remarks |
| 1 | OFF or OFF period of Lv1/Lv2-blink | OFF |  |
| 2 | ON or ON period of Lv1/Lv2-blink | ON | if SBRTTStatus DRV is ON or blink, iHMI_SBRTelltale_DRV is ON. |
| # | Input | Output | Remarks |
| --- | --- | --- | --- |
| # | Internal Parameter - SBRTTStatus_PSG ( TFDCX32348-90708 ) | HMI - SBRTelltale_PSG | Remarks |
| 1 | OFF or OFF period of Lv1/Lv2-blink | OFF |  |
| 2 | ON or ON period of Lv1/Lv2-blink | ON | if SBRTTStatus PSG is ON or blink, iHMI_SBRTelltale_PSG is ON. |
| # | Input |  | Output | Remarks |
| --- | --- | --- | --- | --- |
| # | Internal Parameter - SBRTTStatus_DRV | Internal Parameter - SBRTTStatus_PSG | Internal Parameter - SBRTTStatus | Remarks |
| 1 | OFF | OFF | OFF |  |
| 2 | Lv1/Lv2-blink | X | Lv1/Lv2-blink (SBRTTStatus_DRV) | if SBRTTStatus PSG is ON or blink, iHMI_SBRTelltale_PSG is ON. |
| 3 | ON | Lv1/Lv2-blink | Lv1/Lv2-blink (SBRTTStatus_PSG) |  |
| 4 | ON | Other than above | ON |  |
Rear Seat Belt Indicator
| # | Input | Output | Remarks |
| --- | --- | --- | --- |
| # | Internal Parameter - SBRTTStatus_R* (*1) ( TFDCX32348-90708 ) | HMI - SBRTelltale_R* (*1) | Remarks |
| 1 | OFF or OFF period of Lv1/Lv2-blink | OFF |  |
| 2 | ON or ON period of Lv1/Lv2-blink | ON |  |
(*1)
SBRTTStatus_R* = SBRTTStatus_RL, SBRTTStatus_RC, SBRTTStatus_RR, SBRTTStatus_R2L, SBRTTStatus_R2C, SBRTTStatus_R2R, SBRTTStatus_R3L, SBRTTStatus_R3C, SBRTTStatus_R3R
SBRTelltale_R* = SBRTelltale_RL, SBRTelltale_RC, SBRTelltale_RR, SBRTelltale_R2L, SBRTelltale_R2C, SBRTelltale_R2R, SBRTelltale_R3L, SBRTelltale_R3C, SBRTelltale_R3R respectively.
Rear Seat Belt Indicator Frame
| # | Input |  |  | Output | Remarks |
| --- | --- | --- | --- | --- | --- |
| # | Internal Parameter - SBRTTStatus_DRV | Internal Parameter - SBRTTStatus_PSG | Internal Parameter - SBRTTStatus_R* (*1) | HMI - SBRBlinkStatus | Remarks |
| 1 | OFF | OFF | All of the statuses are OFF | OFF |  |
| 2 | Other than above |  |  | ON | Output ON even during the OFF period of Lv1/Lv2-blink. |
(*1) SBRTTStatus_R* = Any of SBRTTStatus_RL, SBRTTStatus_RC, SBRTTStatus_RR, SBRTTStatus_R2L, SBRTTStatus_R2C, SBRTTStatus_R2R, SBRTTStatus_R3L, SBRTTStatus_R3C, SBRTTStatus_R3R
- Verification Criteria: Verify by executing test cases
- Verification Method: Code/Design Review, System Qualification Test
- Verification Owner: FV
- System Requirement State: Approved
- Primary Discipline: SW
- ASIL Rating: QM

#### TFDCX32348-3270: CAN Output (Heading)

##### TFDCX32348-5690 (System Requirement)
DSWN (Driver Seatbelt Warning) - DBKLAB used as input (Dropped)
|  | Input |  | Output |
| --- | --- | --- | --- |
|  | InternalSignal - IgnMode | CANSignal - DBKLAB (*1) | CANSignal - DSWN |
| 1 | OFF | X | 00b |
| 2 | ON | 10b or 11b | 00b |
| 3 | ON | 00b | 10b |
| 4 | ON | 01b | 11b |
(*1) In case of 'Communication Failure Status'=1 (Failed), use '10b' for DBKLAB, and as for 'Never Received Status', refer to .
- Verification Criteria: Verify by executing test cases
- Verification Method: Code/Design Review, System Qualification Test
- Verification Owner: FV
- System Requirement State: Rejected
- Primary Discipline: SW
- ASIL Rating: QM

##### TFDCX32348-5500 (System Requirement)
DSWN (Driver Seatbelt Warning) - DI_AL_DRV_SEAT_BUCKLE used as input (Dropped)
|  | Input |  | Output | Remark |
| --- | --- | --- | --- | --- |
|  | InternalSignal - IgnMode | HW - DI_AL_DRV_SEAT_BUCKLE | CANSignal - DSWN | Remark |
| 1 | OFF | X | 00b |  |
| 2 | ON | Until 1st Input determination from Data Reset (*1) | 00b |  |
| 3 | ON | OFF | 10b |  |
| 4 | ON | ON continues for [T3] or more | 11b |  |
| 5 | ON | other than above | Previous Value | Until No.4 is fixed (SYS OIL#140-19) |
(*1) Refer to to find 'Data Reset' timing.
- Verification Criteria: Verify by executing test cases
- Verification Method: Code/Design Review, System Qualification Test
- Verification Owner: FV
- System Requirement State: Rejected
- Primary Discipline: SW
- ASIL Rating: QM

##### TFDCX32348-5502 (System Requirement)
PSWN (Passenger Seatbelt Warning) - PBKLAB & POSW used as input (Dropped)
|  | Input |  |  | Output | Remark |
| --- | --- | --- | --- | --- | --- |
|  | InternalSignal - IgnMode | CANSignal - PBKLAB (*1) | CANSignal - POSW (*1) | CANSignal - PSWN | Remark |
| 1 | OFF | X | X | 00b |  |
| 2 | ON | 10b or 11b | X | 00b |  |
| 3 | ON | X | 10b or 11b | 00b |  |
| 4 | ON | 00b | 00b | 10b |  |
| 5 | ON | 00b | 01b | 10b |  |
| 6 | ON | 01b | 00b | 10b |  |
| 7 | ON | 01b | 01b continues for [T31] or more | 11b |  |
| 8 | ON | other than above |  | Previous Value | Until No.7 is fixed |
(*1) In case of 'Communication Failure Status'=1 (Failed), use '10b' for PBKLAB and '10b' for POSW, and as for 'Never Received Status', refer to .
- Verification Criteria: Verify by executing test cases
- Verification Method: Code/Design Review, System Qualification Test
- Verification Owner: FV
- System Requirement State: Approved
- Primary Discipline: SW
- ASIL Rating: QM

##### TFDCX32348-5504 (System Requirement)
PSWN (Passenger Seatbelt Warning) - BPKL_PDC & POSW used as input (Dropped)
|  | Input |  |  | Output | Remark |
| --- | --- | --- | --- | --- | --- |
|  | InternalSignal - IgnMode | CANSignal - PBKL_PDC (*1) | CANSignal - POSW (*1) | CANSignal - PSWN | Remark |
| 1 | OFF | X | X | 00b |  |
| 2 | ON | 10b or 11b | X | 00b |  |
| 3 | ON | X | 10b or 11b | 00b |  |
| 4 | ON | 00b | 00b | 10b |  |
| 5 | ON | 00b | 01b | 10b |  |
| 6 | ON | 01b | 00b | 10b |  |
| 7 | ON | 01b continues for [T30] or more | 01b continues for [T31] or more | 11b |  |
| 8 | ON | other than above |  | Previous Value | Until No.7 is fixed |
(*1) In case of 'Communication Failure Status'=1 (Failed), use '10b' for PBKL_PDC and '10b' for POSW, and as for 'Never Received Status', refer to .
- Verification Criteria: Verify by executing test cases
- Verification Method: Code/Design Review, System Qualification Test
- Verification Owner: FV
- System Requirement State: Approved
- Primary Discipline: SW
- ASIL Rating: QM

##### TFDCX32348-5506 (System Requirement)
DBKL_MET (Driver Seatbelt Buckle Status) - DBKLAB used as input
(38xD SYS OIL#140-20)
|  | Input |  | Output |
| --- | --- | --- | --- |
|  | InternalSignal - IgnMode | CANSignal - DBKLAB (*1) | CANSignal - DBKL_MET |
| 1 | OFF | X | 10b |
| 2 | ON | 00b | 00b |
| 3 | ON | 01b | 01b |
| 4 | ON | 11b | 11b |
| 5 | ON | 10b | 10b |
(*1) In case of 'Communication Failure Status'=1 (Failed), use '10b' for DBKLAB, and as for 'Never Received Status', refer to TFDCX32348-3255 Data Reset .
- Verification Criteria: Verify by executing test cases
- Verification Method: Code/Design Review, System Qualification Test
- Verification Owner: FV
- System Requirement State: Approved
- Primary Discipline: SW
- ASIL Rating: QM

##### TFDCX32348-34516 (System Requirement)
DBKL_MET (Driver Seatbelt Buckle Status) - DBKLSW used as input
Refer to TFDCX32348-3251 for the CAN input selection.
|  | Input |  | Output |
| --- | --- | --- | --- |
|  | InternalSignal - IgnMode | CANSignal - DBKLSW (*1) | CANSignal - DBKL_MET |
| 1 | OFF | X | 10b |
| 2 | ON | 00b | 00b |
| 3 | ON | 01b | 01b |
| 4 | ON | 10b or 11b | 10b |
(*1) In case of 'Communication Failure Status'=1 (Failed), use '10b' for DBKLSW, and as for 'Never Received Status', refer to TFDCX32348-3255 Data Reset .
- Verification Criteria: Verify by executing test cases
- Verification Method: Code/Design Review, System Qualification Test
- Verification Owner: FV
- System Requirement State: Approved
- Primary Discipline: SW
- ASIL Rating: QM

##### TFDCX32348-5508 (System Requirement)
DBKL_MET (Driver Seatbelt Buckle Status) - DI_AL_DRV_SEAT_BUCKLE used as input (Dropped)
|  | Input |  | Output |
| --- | --- | --- | --- |
|  | InternalSignal - IgnMode | HW - DI_AL_DRV_SEAT_BUCKLE | CANSignal - DBKL_MET |
| 1 | OFF | X | 10b |
| 2 | ON | ON | 01b |
| 3 | Less than 500ms passed from OFF -> ON | OFF | 10b |
| 4 | 500ms or more passed from OFF -> ON | OFF | 00b |
- Verification Criteria: Verify by executing test cases
- Verification Method: Code/Design Review, System Qualification Test
- Verification Owner: FV
- System Requirement State: Rejected
- Primary Discipline: SW
- ASIL Rating: QM

##### TFDCX32348-5510 (System Requirement)
PBKL_MET (Passenger Seatbelt Buckle Status) - PBKLAB used as input
(38xD SYS OIL#140-20)
|  | Input |  | Output |
| --- | --- | --- | --- |
|  | InternalSignal - IgnMode | CANSignal - PBKLAB (*1) | CANSignal - PBKL_MET |
| 1 | OFF | X | 10b |
| 2 | ON | 00b | 00b |
| 3 | ON | 01b | 01b |
| 4 | ON | 11b | 11b |
| 5 | ON | 10b | 10b |
(*1) In case of 'Communication Failure Status'=1 (Failed), use '10b' for PBKLAB, and as for 'Never Received Status', refer to TFDCX32348-3255 Data Reset .
- Verification Criteria: Verify by executing test cases
- Verification Method: Code/Design Review, System Qualification Test
- Verification Owner: FV
- System Requirement State: Approved
- Primary Discipline: SW
- ASIL Rating: QM

##### TFDCX32348-5512 (System Requirement)
PBKL_MET (Passenger Seatbelt Buckle Status) - PBKL_PDC used as input
(38xD SYS OIL#140-20)
|  | Input |  | Output |
| --- | --- | --- | --- |
|  | InternalSignal - IgnMode | CANSignal - PBKL_PDC (*1) | CANSignal - PBKL_MET |
| 1 | OFF | X | 10b |
| 2 | ON | 01b | 01b |
| 3 | ON | 00b | 00b |
| 4 | ON | 10b or 11b | 10b |
(*1) In case of 'Communication Failure Status'=1 (Failed), use '10b' for PBKL_PDC, and as for 'Never Received Status', refer to TFDCX32348-3255 Data Reset .
- Verification Criteria: Verify by executing test cases
- Verification Method: Code/Design Review, System Qualification Test
- Verification Owner: FV
- System Requirement State: Approved
- Primary Discipline: SW
- ASIL Rating: QM

##### TFDCX32348-5514 (System Requirement)
RLBKLMET (Rear-Left Seatbelt Buckle Status)
|  | Input |  | Output |
| --- | --- | --- | --- |
|  | InternalSignal - IgnMode | CANSignal - RLBKLPDC (*1) | CANSignal - RLBKLMET |
| 1 | OFF | X | 10b |
| 2 | ON | 00b | 00b |
| 3 | ON | 01b | 01b |
| 4 | ON | 10b | 10b |
| 5 | ON | 11b | 11b |
(*1) In case of 'Communication Failure Status'=1 (Failed), use '10b' for RLBKLPDC, and as for 'Never Received Status', refer to TFDCX32348-3255 Data Reset .
- Verification Criteria: Verify by executing test cases
- Verification Method: Code/Design Review, System Qualification Test
- Verification Owner: FV
- System Requirement State: Approved
- Primary Discipline: SW
- ASIL Rating: QM

##### TFDCX32348-5516 (System Requirement)
RCBKLMET (Rear-Center Seatbelt Buckle Status)
|  | Input |  | Output |
| --- | --- | --- | --- |
|  | InternalSignal - IgnMode | CANSignal - RCBKLPDC (*1) | CANSignal - RCBKLMET |
| 1 | OFF | X | 10b |
| 2 | ON | 00b | 00b |
| 3 | ON | 01b | 01b |
| 4 | ON | 10b | 10b |
| 5 | ON | 11b | 11b |
(*1) In case of 'Communication Failure Status'=1 (Failed), use '10b' for RCBKLPDC, and as for 'Never Received Status', refer to TFDCX32348-3255 Data Reset .
- Verification Criteria: Verify by executing test cases
- Verification Method: Code/Design Review, System Qualification Test
- Verification Owner: FV
- System Requirement State: Approved
- Primary Discipline: SW
- ASIL Rating: QM

##### TFDCX32348-5518 (System Requirement)
RRBKLMET (Rear-Right Seatbelt Buckle Status)
|  | Input |  | Output |
| --- | --- | --- | --- |
|  | InternalSignal - IgnMode | CANSignal - RRBKLPDC (*1) | CANSignal - RRBKLMET |
| 1 | OFF | X | 10b |
| 2 | ON | 00b | 00b |
| 3 | ON | 01b | 01b |
| 4 | ON | 10b | 10b |
| 5 | ON | 11b | 11b |
(*1) In case of 'Communication Failure Status'=1 (Failed), use '10b' for RRBKLPDC, and as for 'Never Received Status', refer to TFDCX32348-3255 Data Reset .
- Verification Criteria: Verify by executing test cases
- Verification Method: Code/Design Review, System Qualification Test
- Verification Owner: FV
- System Requirement State: Approved
- Primary Discipline: SW
- ASIL Rating: QM

##### TFDCX32348-34517 (System Requirement)
BKL3LMET (Rear 2nd Row-Left Seatbelt Buckle Status)
|  | Input |  | Output |
| --- | --- | --- | --- |
|  | InternalSignal - IgnMode | CANSignal - LR2BCKL (*1) | CANSignal - BKL3LMET |
| 1 | OFF | X | 10b |
| 2 | ON | 00b | 00b |
| 3 | ON | 01b | 01b |
| 4 | ON | 10b | 10b |
| 5 | ON | 11b | 11b |
(*1) In case of 'Communication Failure Status'=1 (Failed), use '10b' for LR2BCKL, and as for 'Never Received Status', refer to TFDCX32348-3255 Data Reset .
- Verification Criteria: Verify by executing test cases
- Verification Method: Code/Design Review, System Qualification Test
- Verification Owner: FV
- System Requirement State: Approved
- Primary Discipline: SW
- ASIL Rating: QM

##### TFDCX32348-34555 (System Requirement)
BKL3CMET (Rear 2nd Row-Center Seatbelt Buckle Status)
|  | Input |  | Output |
| --- | --- | --- | --- |
|  | InternalSignal - IgnMode | CANSignal - CR2BCKL (*1) | CANSignal - BKL3CMET |
| 1 | OFF | X | 10b |
| 2 | ON | 00b | 00b |
| 3 | ON | 01b | 01b |
| 4 | ON | 10b | 10b |
| 5 | ON | 11b | 11b |
(*1) In case of 'Communication Failure Status'=1 (Failed), use '10b' for CR2BCKL, and as for 'Never Received Status', refer to TFDCX32348-3255 Data Reset .
- Verification Criteria: Verify by executing test cases
- Verification Method: Code/Design Review, System Qualification Test
- Verification Owner: FV
- System Requirement State: Approved
- Primary Discipline: SW
- ASIL Rating: QM

##### TFDCX32348-34556 (System Requirement)
BKL3RMET (Rear 2nd Row-Right Seatbelt Buckle Status)
|  | Input |  | Output |
| --- | --- | --- | --- |
|  | InternalSignal - IgnMode | CANSignal - RR2BCKL (*1) | CANSignal - BKL3RMET |
| 1 | OFF | X | 10b |
| 2 | ON | 00b | 00b |
| 3 | ON | 01b | 01b |
| 4 | ON | 10b | 10b |
| 5 | ON | 11b | 11b |
(*1) In case of 'Communication Failure Status'=1 (Failed), use '10b' for RR2BCKL, and as for 'Never Received Status', refer to TFDCX32348-3255 Data Reset .
- Verification Criteria: Verify by executing test cases
- Verification Method: Code/Design Review, System Qualification Test
- Verification Owner: FV
- System Requirement State: Approved
- Primary Discipline: SW
- ASIL Rating: QM

#### TFDCX32348-34590: CXPI Output (Heading)

##### TFDCX32348-34591 (System Requirement)
CXPI - RLTT (Rear 1st Row-Left Seat Belt Indicator Status)
| # | Input | Output | Remarks |
| --- | --- | --- | --- |
| # | HMI - SBRTelltale_RL | CXPI - RLTT | Remarks |
| 1 | OFF | 0 | OFF or OFF duration of Lv1/Lv2 blink. |
| 2 | ON | 1 | ON or ON duration of Lv1/Lv2 blink. |
- Verification Criteria: Verify by executing test cases
- Verification Method: Software Qualification Test, System Qualification Test, Unit Test
- Verification Owner: FV, SW
- System Requirement State: Approved
- Primary Discipline: SW
- ASIL Rating: QM

##### TFDCX32348-34599 (System Requirement)
CXPI - RCTT (Rear 1st Row-Center Seat Belt Indicator Status)
| # | Input | Output | Remarks |
| --- | --- | --- | --- |
| # | HMI - SBRTelltale_RC | CXPI - RCTT | Remarks |
| 1 | OFF | 0 | OFF or OFF duration of Lv1/Lv2 blink. |
| 2 | ON | 1 | ON or ON duration of Lv1/Lv2 blink. |
- Verification Criteria: Verify by executing test cases
- Verification Method: Software Qualification Test, System Qualification Test, Unit Test
- Verification Owner: FV, SW
- System Requirement State: Approved
- Primary Discipline: SW
- ASIL Rating: QM

##### TFDCX32348-34600 (System Requirement)
CXPI - RRTT (Rear 1st Row-Right Seat Belt Indicator Status)
| # | Input | Output | Remarks |
| --- | --- | --- | --- |
| # | HMI - SBRTelltale_RR | CXPI - RRTT | Remarks |
| 1 | OFF | 0 | OFF or OFF duration of Lv1/Lv2 blink. |
| 2 | ON | 1 | ON or ON duration of Lv1/Lv2 blink. |
- Verification Criteria: Verify by executing test cases
- Verification Method: Software Qualification Test, System Qualification Test, Unit Test
- Verification Owner: FV, SW
- System Requirement State: Approved
- Primary Discipline: SW
- ASIL Rating: QM

##### TFDCX32348-34601 (System Requirement)
CXPI - RL2TT (Rear 2nd Row-Left Seat Belt Indicator Status)
| # | Input | Output | Remarks |
| --- | --- | --- | --- |
| # | HMI - SBRTelltale_R2L | CXPI - RL2TT | Remarks |
| 1 | OFF | 0 | OFF or OFF duration of Lv1/Lv2 blink. |
| 2 | ON | 1 | ON or ON duration of Lv1/Lv2 blink. |
- Verification Criteria: Verify by executing test cases
- Verification Method: Software Qualification Test, System Qualification Test, Unit Test
- Verification Owner: FV, SW
- System Requirement State: Approved
- Primary Discipline: SW
- ASIL Rating: QM

##### TFDCX32348-34604 (System Requirement)
CXPI - RC2TT (Rear 2nd Row-Center Seat Belt Indicator Status)
| # | Input | Output | Remarks |
| --- | --- | --- | --- |
| # | HMI - SBRTelltale_R2C | CXPI - RC2TT | Remarks |
| 1 | OFF | 0 | OFF or OFF duration of Lv1/Lv2 blink. |
| 2 | ON | 1 | ON or ON duration of Lv1/Lv2 blink. |
- Verification Criteria: Verify by executing test cases
- Verification Method: Software Qualification Test, System Qualification Test, Unit Test
- Verification Owner: FV, SW
- System Requirement State: Approved
- Primary Discipline: SW
- ASIL Rating: QM

##### TFDCX32348-34606 (System Requirement)
CXPI - RR2TT (Rear 2nd Row-Right Seat Belt Indicator Status)
| # | Input | Output | Remarks |
| --- | --- | --- | --- |
| # | HMI - SBRTelltale_R2R | CXPI - RR2TT | Remarks |
| 1 | OFF | 0 | OFF or OFF duration of Lv1/Lv2 blink. |
| 2 | ON | 1 | ON or ON duration of Lv1/Lv2 blink. |
- Verification Criteria: Verify by executing test cases
- Verification Method: Software Qualification Test, System Qualification Test, Unit Test
- Verification Owner: FV, SW
- System Requirement State: Approved
- Primary Discipline: SW
- ASIL Rating: QM

##### TFDCX32348-34607 (System Requirement)
CXPI - RL3TT (Rear 3rd Row-Left Seat Belt Indicator Status)
| # | Input | Output | Remarks |
| --- | --- | --- | --- |
| # | HMI - SBRTelltale_R3L | CXPI - RL3TT | Remarks |
| 1 | OFF | 0 | OFF or OFF duration of Lv1/Lv2 blink. |
| 2 | ON | 1 | ON or ON duration of Lv1/Lv2 blink. |
- Verification Criteria: Verify by executing test cases
- Verification Method: Software Qualification Test, System Qualification Test, Unit Test
- Verification Owner: FV, SW
- System Requirement State: Approved
- Primary Discipline: SW
- ASIL Rating: QM

##### TFDCX32348-34608 (System Requirement)
CXPI - RC3TT (Rear 3rd Row-Center Seat Belt Indicator Status)
| # | Input | Output | Remarks |
| --- | --- | --- | --- |
| # | HMI - SBRTelltale_R3C | CXPI - RC3TT | Remarks |
| 1 | OFF | 0 | OFF or OFF duration of Lv1/Lv2 blink. |
| 2 | ON | 1 | ON or ON duration of Lv1/Lv2 blink. |
- Verification Criteria: Verify by executing test cases
- Verification Method: Software Qualification Test, System Qualification Test, Unit Test
- Verification Owner: FV, SW
- System Requirement State: Approved
- Primary Discipline: SW
- ASIL Rating: QM

##### TFDCX32348-34609 (System Requirement)
CXPI - RR3TT (Rear 3rd Row-Right Seat Belt Indicator Status)
| # | Input | Output | Remarks |
| --- | --- | --- | --- |
| # | HMI - SBRTelltale_R3R | CXPI - RR3TT | Remarks |
| 1 | OFF | 0 | OFF or OFF duration of Lv1/Lv2 blink. |
| 2 | ON | 1 | ON or ON duration of Lv1/Lv2 blink. |
- Verification Criteria: Verify by executing test cases
- Verification Method: Software Qualification Test, System Qualification Test, Unit Test
- Verification Owner: FV, SW
- System Requirement State: Approved
- Primary Discipline: SW
- ASIL Rating: QM

##### TFDCX32348-34610 (System Requirement)
CXPI - REARINDI (Rear Seat Belt Indicator Background Status)
| # | Input | Output | Remarks |
| --- | --- | --- | --- |
| # | HMI - SBRBlinkStatus | CXPI - REARINDI | Remarks |
| 1 | OFF | 0 | All of the rear seat belt indicatiors are OFF. |
| 2 | ON | 1 | Any of the rear seat belt indicator is ON or Lv1/Lv2 blink. |
- Verification Criteria: Verify by executing test cases
- Verification Method: Software Qualification Test, System Qualification Test, Unit Test
- Verification Owner: FV, SW
- System Requirement State: Approved
- Primary Discipline: SW
- ASIL Rating: QM

### TFDCX32348-1466: SBR Buzzer Output History Logging (Heading)

#### TFDCX32348-3272: <Summary of this function> (Information)
<Summary of this function>
This function logs the date and time history of the seat belt reminder buzzser for past 10 times.
SeatBeltReminderLogs[] array is used to store the history information.
The logged history information can be read by DID$11A2 of DIAG$22 service.

#### TFDCX32348-3274: SBR Buzzer History Logging Memory (Heading)

##### TFDCX32348-5520: Usage of UINT8 SeatBeltReminderLogs[80] (System Requirement)
| # | Data | Byte# | Data Storage | Data Meaning |  | Range | Remarks |
| --- | --- | --- | --- | --- | --- | --- | --- |
| 1 | History 1 | 1 | SeatBeltReminderLogs[0] | Timestamp - YEAR |  | BCD 0x00 to 0x99 | 0x00 corresponds to year 2000. |
| 2 | History 1 | 2 | SeatBeltReminderLogs[1] | Timestamp - MONTH |  | BCD 0x01 to 0x12 |  |
| 3 | History 1 | 3 | SeatBeltReminderLogs[2] | Timestamp - DAY |  | BCD 0x01 to 0x31 |  |
| 4 | History 1 | 4 | SeatBeltReminderLogs[3] | Timestamp - HOUR |  | BCD 0x00 to 0x23 |  |
| 5 | History 1 | 5 | SeatBeltReminderLogs[4] | Timestamp - MIN |  | BCD 0x00 to 0x59 |  |
| 6 | History 1 | 6 | SeatBeltReminderLogs[5] | Timestamp - SEC |  | BCD 0x00 to 0x59 |  |
| 7 | History 1 | 7 | SeatBeltReminderLogs[6] | bit 7 | SBR buzzer status for Driver seat | 0:OFF, 1:ON |  |
| 8 | History 1 | 7 | SeatBeltReminderLogs[6] | bit 6 | SBR buzzer status for Front center seat | 0:OFF, 1:ON |  |
| 9 | History 1 | 7 | SeatBeltReminderLogs[6] | bit 5 | SBR buzzer status for Passenger seat | 0:OFF, 1:ON |  |
| 10 | History 1 | 7 | SeatBeltReminderLogs[6] | bit 4 | SBR buzzer status for rear right seat | 0:OFF, 1:ON |  |
| 11 | History 1 | 7 | SeatBeltReminderLogs[6] | bit 3 | SBR buzzer status for rear center seat | 0:OFF, 1:ON |  |
| 12 | History 1 | 7 | SeatBeltReminderLogs[6] | bit 2 | SBR buzzer status for rear left seat | 0:OFF, 1:ON |  |
| 13 | History 1 | 7 | SeatBeltReminderLogs[6] | bit 1 | SBR buzzer status for rear 2nd right seat | 0:OFF, 1:ON |  |
| 14 | History 1 | 7 | SeatBeltReminderLogs[6] | bit 0 | SBR buzzer status for rear 2nd center seat | 0:OFF, 1:ON |  |
| 15 | History 1 | 8 | SeatBeltReminderLogs[7] | bit 7 | SBR buzzer status for rear 2nd left seat | 0:OFF, 1:ON |  |
| 16 | History 1 | 8 | SeatBeltReminderLogs[7] | bit 6-0 | Reserved | all 0 |  |
| 17 | History 2 | 9-16 | SeatBeltReminderLogs[8]to[15] | Same as Byte 1 to 8 |  |  | 1 older data |
| 18 | History 3 | 17-24 | SeatBeltReminderLogs[16]to[23] | Same as Byte 1 to 8 |  |  | 2 older data |
| 19 | History 4 | 25-32 | SeatBeltReminderLogs[17]to[31] | Same as Byte 1 to 8 |  |  | 3 older data |
| 20 | History 5 | 33-40 | SeatBeltReminderLogs[18]to[39] | Same as Byte 1 to 8 |  |  | 4 older data |
| 21 | History 6 | 41-48 | SeatBeltReminderLogs[19]to[47] | Same as Byte 1 to 8 |  |  | 5 older data |
| 22 | History 7 | 49-56 | SeatBeltReminderLogs[20]to[55] | Same as Byte 1 to 8 |  |  | 6 older data |
| 23 | History 8 | 57-64 | SeatBeltReminderLogs[21]to[63] | Same as Byte 1 to 8 |  |  | 7 older data |
| 24 | History 9 | 65-73 | SeatBeltReminderLogs[22]to[72] | Same as Byte 1 to 8 |  |  | 8 older data |
| 25 | History 10 | 74-80 | SeatBeltReminderLogs[23]to[79] | Same as Byte 1 to 8 |  |  | 9 older data |
Note 1) The data format complies reply data frame #4 - #83 of DID$11A2.
Note 2) SeatBeltReminderLogs[] data shall be stored into backup RAM.
Note 3) All the data of SeatBeltReminderLogs[] shall be 0 cleared at battery reconnect.
Note 4) Bits for rear 3rd row seat belts are not defined in the output data format, since rear 3rd row seats are reseved for future extention.
- Verification Criteria: Verify by executing test cases
- Verification Method: Code/Design Review, System Qualification Test
- Verification Owner: FV
- System Requirement State: Approved
- Primary Discipline: SW
- ASIL Rating: QM

#### TFDCX32348-3276: SBR Buzzer History Logging Condition (Heading)

##### TFDCX32348-5523: SBR Buzzer History Logging Condition (System Requirement)
SBR Buzzer History Logging Condition
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(*1) The target seats are DRV, PSG, FCTR, Rear Right, Rear Center, Rear, Left, Rear-2nd-Row Right, Center, Left. Left, Rear-3rd-Row Right, Center, Left. Refer to TFDCX32348-5653: State Transition for BZR, TFDCX32348-89836: State Transition for BZR.
(*2) Execute TFDCX32348-5525: Update SBR Buzzer History.
(*3) Ver 1.0a : Removed state G according to Toyota [38xD] [APP] Update of the seat belt judgment logic - Impediment (2016583).
- Verification Criteria: Verify by executing test cases
- Verification Method: Code/Design Review, System Qualification Test
- Verification Owner: FV
- System Requirement State: Approved
- Primary Discipline: SW
- ASIL Rating: QM

#### TFDCX32348-3278: Update SBR Buzzer History (Heading)

##### TFDCX32348-5525: Update SBR Buzzer History (System Requirement)
Update SBR Buzzer History
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Box (1) - Transfer each history data to one older storage. Refer to TFDCX32348-5520 .
Box (2) - Refer to TFDCX32348-5527 [Destination Group = A or B or C or D or E or F] , TFDCX32348-95783 [Destination Group = G or H (New FMVSS208)].
- Verification Criteria: Verify by executing test cases
- Verification Method: Code/Design Review, System Qualification Test
- Verification Owner: FV
- System Requirement State: Approved
- Primary Discipline: SW
- ASIL Rating: QM

##### TFDCX32348-5527: Creation of SBR Buzzer History Data (System Requirement)
Creation of SBR Buzzer History Data
if Internal Parameter - Destination Group = A or B or C or D or E or F
| # | Data | Byte# | Data Storage |  | Set Value |
| --- | --- | --- | --- | --- | --- |
| 1 | History 1 | 1 | SeatBeltReminderLogs[0] |  | CAN Signal - D_YEAR (*1) |
| 2 | History 1 | 2 | SeatBeltReminderLogs[1] |  | CAN Signal - D_MONT (*1) |
| 3 | History 1 | 3 | SeatBeltReminderLogs[2] |  | CAN Signal - D_DAY (*1) |
| 4 | History 1 | 4 | SeatBeltReminderLogs[3] |  | CAN Signal - D_HOUR (*1) |
| 5 | History 1 | 5 | SeatBeltReminderLogs[4] |  | CAN Signal - D_MIN (*1) |
| 6 | History 1 | 6 | SeatBeltReminderLogs[5] |  | CAN Signal - D_SEC (*1) |
| 7 | History 1 | 7 | SeatBeltReminderLogs[6] | bit 7 | If ("buzzer status of DRV seat" is state F or H or I) then 1 else 0 (*2) |
| 8 | History 1 | 7 | SeatBeltReminderLogs[6] | bit 6 | If ("buzzer status of FCTR seat" is state F or H or I) then 1 else 0 (*2) |
| 9 | History 1 | 7 | SeatBeltReminderLogs[6] | bit 5 | If ("buzzer status of PSG seat" is state F or H or I) then 1 else 0 (*2) |
| 10 | History 1 | 7 | SeatBeltReminderLogs[6] | bit 4 | If ("buzzer status of Rear Right seat" is state F or H or I) then 1 else 0 (*2) |
| 11 | History 1 | 7 | SeatBeltReminderLogs[6] | bit 3 | If ("buzzer status of Rear Center seat" is state F or H or I) then 1 else 0 (*2) |
| 12 | History 1 | 7 | SeatBeltReminderLogs[6] | bit 2 | If ("buzzer status of Rear Left seat" is state F or H or I) then 1 else 0 (*2) |
| 13 | History 1 | 7 | SeatBeltReminderLogs[6] | bit 1 | If ("buzzer status of Rear 2nd Row Right seat" is state F or H or I) then 1 else 0 (*2) |
| 14 | History 1 | 7 | SeatBeltReminderLogs[6] | bit 0 | If ("buzzer status of Rear 2nd Row Center seat" is state F or H or I) then 1 else 0 (*2) |
| 15 | History 1 | 8 | SeatBeltReminderLogs[7] | bit 7 | If ("buzzer status of Rear 2nd Row Left seat" is state F or H or I) then 1 else 0 (*2) |
| 16 | History 1 | 8 | SeatBeltReminderLogs[7] | bit 6-0 | 0x00 |
(*1) These CAN signals are assigned to same CAN frame and they have same timeout time.
Check CAN signal status for D_YEAR, and if the status is "never received" or "communication failure", set 0xFF to these all bytes instead of CAN signal value.
(*2) The value is determined according to the buzzer status of each seat. Refer to TFDCX32348-5653: State Transition for BZR.
Ver 1.0a : Removed state G according to Toyota [38xD] [APP] Update of the seat belt judgment logic - Impediment (2016583).
Note: SBR buzzer history log is updated when SBR buzzer status is changed from no sounding to sounding. At this timing, if the buzzer is started for multiple seats, multiple bits of SeatBetRemindeLogs[6] are set.
Even if target seat is increased while SBR buzzer is sounding, the log shall not be updated.
Note: Output bits for rear 3rd row seat are not defined in the output data format, and no need to refect the status to output data. Support of the rear 3rd row seats are for future expansion.
- Verification Criteria: Verify by executing test cases
- Verification Method: Code/Design Review, System Qualification Test
- Verification Owner: FV
- System Requirement State: Approved
- Primary Discipline: SW
- ASIL Rating: QM

##### TFDCX32348-95783 (System Requirement)
Creation of SBR Buzzer History Data for FMVSS208
if Internal Parameter - Destination Group = G or H (New FMVSS208)
| # | Data | Byte# | Data Storage |  | Set Value |
| --- | --- | --- | --- | --- | --- |
| 1 | History 1 | 1 | SeatBeltReminderLogs[0] |  | CAN Signal - D_YEAR (*1) |
| 2 | History 1 | 2 | SeatBeltReminderLogs[1] |  | CAN Signal - D_MONT (*1) |
| 3 | History 1 | 3 | SeatBeltReminderLogs[2] |  | CAN Signal - D_DAY (*1) |
| 4 | History 1 | 4 | SeatBeltReminderLogs[3] |  | CAN Signal - D_HOUR (*1) |
| 5 | History 1 | 5 | SeatBeltReminderLogs[4] |  | CAN Signal - D_MIN (*1) |
| 6 | History 1 | 6 | SeatBeltReminderLogs[5] |  | CAN Signal - D_SEC (*1) |
| 7 | History 1 | 7 | SeatBeltReminderLogs[6] | bit 7 | If ("buzzer status of DRV seat" is state E or G or H) then 1 else 0 (*2) |
| 8 | History 1 | 7 | SeatBeltReminderLogs[6] | bit 6 | Set "0" due to “FCTR seat" is not applicable. |
| 9 | History 1 | 7 | SeatBeltReminderLogs[6] | bit 5 | If ("buzzer status of PSG seat" is state E or G or H) then 1 else 0 (*2) |
| 10 | History 1 | 7 | SeatBeltReminderLogs[6] | bit 4 | If ("buzzer status of Rear Right seat" is state E or G or H) then 1 else 0 (*2) |
| 11 | History 1 | 7 | SeatBeltReminderLogs[6] | bit 3 | If ("buzzer status of Rear Center seat" is state E or G or H) then 1 else 0 (*2) |
| 12 | History 1 | 7 | SeatBeltReminderLogs[6] | bit 2 | If ("buzzer status of Rear Left seat" is state E or G or H) then 1 else 0 (*2) |
| 13 | History 1 | 7 | SeatBeltReminderLogs[6] | bit 1 | If ("buzzer status of Rear 2nd Row Right seat" is state E or G or H) then 1 else 0 (*2) |
| 14 | History 1 | 7 | SeatBeltReminderLogs[6] | bit 0 | If ("buzzer status of Rear 2nd Row Center seat" is state E or G or H) then 1 else 0 (*2) |
| 15 | History 1 | 8 | SeatBeltReminderLogs[7] | bit 7 | If ("buzzer status of Rear 2nd Row Left seat" is state E or G or H) then 1 else 0 (*2) |
| 16 | History 1 | 8 | SeatBeltReminderLogs[7] | bit 6-0 | 0x00 |
(*1) These CAN signals are assigned to same CAN frame and they have same timeout time.
Check CAN signal status for D_YEAR, and if the status is "never received" or "communication failure", set 0xFF to these all bytes instead of CAN signal value.
(*2) The value is determined according to the buzzer status of each seat. Refer to TFDCX32348-89836: State Transition for BZR.
Ver 1.0a : Removed state G according to Toyota [38xD] [APP] Update of the seat belt judgment logic - Impediment (2016583).
Note: SBR buzzer history log is updated when SBR buzzer status is changed from no sounding to sounding. At this timing, if the buzzer is started for multiple seats, multiple bits of SeatBetRemindeLogs[6] are set.
Even if target seat is increased while SBR buzzer is sounding, the log shall not be updated.
Note: Output bits for rear 3rd row seat are not defined in the output data format, and no need to reflect the status to output data. Support of the rear 3rd row seats are for future expansion.
- Verification Criteria: Verify by executing test cases
- Verification Method: Code/Design Review, System Qualification Test
- Verification Owner: FV
- System Requirement State: Approved
- Primary Discipline: SW
- ASIL Rating: QM

# Json2ReqIF Transformation

# Specification: GUI_OdoTrip_Oil mileage
- JDA Snapshot Date: 2025-09-04 02:53:36

## TFDCX32348-27225: GUI_OdoTrip_Oil mileage (Heading)

## TFDCX32348-27227: History (Heading)

### TFDCX32348-27228: Table (Information)
| Version | Date | Name | Description of change | Baseline |
| --- | --- | --- | --- | --- |
| 0.1 | Jun/4/2024 | Hiromune Wachi | Newly create [SYS-Story] : TFDCX32348-26421: [SYS][12.3FDC][GUI][Trip Computer] Odo trip meter | BL_20240627_01 |
| 0.2 | Dec/05/2024 | Masaki Kubo | Added the OIL mileage navigation [SYS-Story] : TFDCX32348-55934: [SYS][12.3FDC][GUI][VMID] Oil mileage navigation system | BL_20241216_01 |
| 0.3 | Dec/04/2024 | Takuya Tamura | Changed Odometer display method from zero suppressed to zero padding. [SYS-Story] : TFDCX32348-59467: [SYS][12.3FDC][GUI][Trip Computer] Odo trip meter (for CV) | BL_20241216_01 |
| 0.4 | Dec/18/2024 | Takuya Tamura | Added the POWER_ON and ACCESSORY. [SYS-Story] : TFDCX32348-59720: [SYS][12.3FDC][GUI][Trip Computer] POWER ON and ACCESSORY | BL_20250120_01 |
| 0.5 | Feb/25/2025 | Rani Simon | TFDCX32348-64214: [SYS][12.3FDC][R4][GUI]Function Animation - Left mid content change, ONS, Widget, General cursor Added section Animation Specification | BL_20250327_01 |
| 0.6 | 2025/June/17 | Rani Simon | TFDCX32348-93417: [SYS][12.3FDC][IMP][GUI][Trip Computer] Update Odo display logic to support FUEL_OW_ADV_NOTICE, FUEL_OVER_WRITE TFDCX32348-27313 TFDCX32348-27241 TFDCX32348-93474 | BL_20250620_01 |
| 0.7 | 2025/Aug/25 | Rani Simon | TFDCX32348-102875: [SYS][12.3FDC][OIL][GUI][Trip Computer] Remove zero padding from Odo display TFDCX32348-27241 Impediment - TFDCX32348-103387: No requirement mentioned valid value to valid value ( Other than Blank and OFF) - whether need to animate or not. TFDCX32348-70411 | BL_20250826_01 |

## TFDCX32348-27229: Reference Document (Heading)

### TFDCX32348-27230: External Sources (Heading)

#### TFDCX32348-27232: Table - External Sources (Information)
| # | Category | Name |
| --- | --- | --- |
| 1 | PSD | 240423_19V3_Toyota_2DUI_Number_icon\OdoTrip.psd 240423_19V3_Toyota_2DUI_Number_icon\Oil_maintenance.psd 20240716_PSDdata\20240716時点PSDデータ\S_003_01_00_POWER.psd |
| 2 | Screen display specification |  |

### TFDCX32348-27231: Internal Sources (Heading)

#### TFDCX32348-27233: Table - Internal Sources (Information)
| # | Category | Name |
| --- | --- | --- |
| 1 | Application logic | TRIP_Odometer, TRIP_Trip meter VMID_Oil Milege Navi |
| 2 | Screen Navigation | Screen Navigation - Screen Mode (TOP Level) Screen Navigation - Display Area Control |
| 3 | Design Spec | Toyota_12.3Inch_Odo_Trip_v2 |

## TFDCX32348-27234: Input Requirements (Heading)

### TFDCX32348-27236: HMI - HMI_TOTAL_ODO_VALUE (System Interface)

### TFDCX32348-27237: InternalSignal - HMI_TRIPA_ODO_VALUE (System Interface)

### TFDCX32348-27238: InternalSignal - HMI_TRIPB_ODO_VALUE (System Interface)

### TFDCX32348-27239: InternalSignal - Display_Distance_Unit (System Interface)

### TFDCX32348-27240: HMI - HMI_ScreenMode (System Interface)

### TFDCX32348-27242: HMI - HMI_OdoType (System Interface)

### TFDCX32348-55966: HMI – OILMIL_DISTANCE_VALUE... (System Interface)
HMI – OILMIL_DISTANCE_VALUE

### TFDCX32348-55967: HMI – OILMIL_REVERSAL_OFFON... (System Interface)
HMI – OILMIL_REVERSAL_OFFON

### TFDCX32348-55968: HMI – OILMIL_UNIT_VALUE... (System Interface)
HMI – OILMIL_UNIT_VALUE

### TFDCX32348-55969: HMI – OILMIL_DISTANCE_AREA_STATUS... (System Interface)
HMI – OILMIL_DISTANCE_AREA_STATUS

## TFDCX32348-27235: Output Requirements (Heading)

### TFDCX32348-27288: Screen Layout (Heading)

#### TFDCX32348-27290: Screen Layout (System Requirement)
Screen Layout
| Layout name | Screen Layout |
| --- | --- |
| [Layout1 : 0&1dial&2dial_ODO_Trip] | [Odo 999999km]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 [Trip A 9999.9km]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 [Trip B 9999.9mi]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 |
| [Layout_2 : 0&1dial&2dial_Oil_maintenance] | [Oil maintenance 56789 km]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 [Oil maintenance 99999 highlight mi]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 |
| [Layout_3 : 0&1dial&2dial_acc_power] | [ACCESSORY]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 [POWER ON]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 |
- Verification Criteria: Verify by executing test cases
- Verification Method: Software Qualification Test, System Qualification Test, Unit Test
- Verification Owner: FV, SW
- System Requirement State: Approved
- Primary Discipline: SW
- ASIL Rating: QM

#### TFDCX32348-27291: Elements (System Requirement)
| Example use case | Display image |
| --- | --- |
| Odo 999999km display |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 |
| Trip A 9999.9km display |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 |
| Trip B 9999.9mi display |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 |
| Oil maintenance 56789 km display |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 |
| Oil maintenance -1234 mile display |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 |
| ACCESSORY display |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 |
| POWER ON display |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 |
| # | Elements | Text or Image | Remarks |
| --- | --- | --- | --- |
| 1 | Odo distance | Image |  |
| 2 | Trip distance | Image |  |
| 3 | Unit | Image |  |
| 4 | A/B mark | Image |  |
| 5 | Maintenance icon | Image |  |
| 6 | Distance | Image |  |
| 7 | Unit | Text |  |
| 8 | Highlight | Image |  |
| 9 | ACCESSORY | Text |  |
| 10 | POWER ON | Text |  |
| 11 | POWER ON Background | Image |  |
- Verification Criteria: Verify by executing test cases
- Verification Method: Software Qualification Test, System Qualification Test, Unit Test
- Verification Owner: FV, SW
- System Requirement State: Approved
- Primary Discipline: SW
- ASIL Rating: QM

### TFDCX32348-27289: Display logic (Heading)

#### TFDCX32348-27312: Applicability (Heading)

##### TFDCX32348-27313: Table for Determination the screen layout (System Requirement)
When ODO is displayed in rental car mode, ODO is displayed even when IG is OFF, so do not check ScreenMode.
| # | Input | Output |  |  |
| --- | --- | --- | --- | --- |
| # | HMI - HMI_OdoType | OdoTrip | Reference to Design Spec (GLTF group) | Remarks |
| 1 | ODO | Display | [Layout1: 0&1dial&2dial_ODO_Trip] grp_0_1_2_dial_odo_trip | Display ODO value and unit |
| 2 | TRIP_A | Display | [Layout1: 0&1dial&2dial_ODO_Trip] grp_0_1_2_dial_odo_trip | Display Trip value and unit |
| 3 | TRIP_B | Display | [Layout1: 0&1dial&2dial_ODO_Trip] grp_0_1_2_dial_odo_trip | Display Trip value and unit |
| 4 | FUEL_OW_ADV_NOTICE | Display | [Layout1: 0&1dial&2dial_ODO_Trip] grp_0_1_2_dial_odo_trip | Display ODO value without unit |
| 5 | FUEL_OVER_WRITE | Display | [Layout1: 0&1dial&2dial_ODO_Trip] grp_0_1_2_dial_odo_trip | Blink ODO value without unit at 2Hz |
| 6 | OILMIL_DISTANCE_INT or OILMIL_DISTANCE | Display | [Layout2: 0&1dial&2dial_Oil_maintenance] | Display Oil maintenance distance |
| 7 | POWER_STATUS_ACC | Display | [Layout_3 : 0&1dial&2dial_acc_power] | Display ACCESSORY |
| 8 | POWER_STATUS_ON | Display | [Layout_3 : 0&1dial&2dial_acc_power] | Display POWER |
| 9 | Other than above | Do not display | Not applicable |  |
- Verification Criteria: Verify by executing test cases
- Verification Method: Software Qualification Test, System Qualification Test, Unit Test
- Verification Owner: FV, SW
- System Requirement State: Approved
- Primary Discipline: SW
- ASIL Rating: QM

#### TFDCX32348-27314: #1 : Odo distance (Heading)

##### TFDCX32348-27241: Table - Odo distance (System Requirement)
Odometer displays zero padding. Refer メータMID表示ルールブック_v1.0.docx
Odometer shall be displayed without zero padding.
| # | Input |  | Output | Design Spec Reference |
| --- | --- | --- | --- | --- |
| # | HMI - HMI_OdoType | HMI - HMI_TOTAL_ODO_VALUE | Sample display | GLTF element |
| 1 | ODO or FUEL_OW_ADV_NOTICE or FUEL_OVER_WRITE | 0 ~ 9 |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 | img_0_1_2_dial_odo_digit_p1_0 ~ 9 img_0_1_2_dial_odo_digit_p2_0 img_0_1_2_dial_odo_digit_p3_0 img_0_1_2_dial_odo_digit_p4_0 img_0_1_2_dial_odo_digit_p5_0 img_0_1_2_dial_odo_digit_p6_0 |
| 2 | ODO or FUEL_OW_ADV_NOTICE or FUEL_OVER_WRITE | 10 ~ 99 |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 | img_0_1_2_dial_odo_digit_p1_0 ~ 9 img_0_1_2_dial_odo_digit_p2_0 ~ 9 img_0_1_2_dial_odo_digit_p3_0 img_0_1_2_dial_odo_digit_p4_0 img_0_1_2_dial_odo_digit_p5_0 img_0_1_2_dial_odo_digit_p6_0 |
| 3 | ODO or FUEL_OW_ADV_NOTICE or FUEL_OVER_WRITE | 100 ~ 999 |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 | img_0_1_2_dial_odo_digit_p1_0 ~ 9 img_0_1_2_dial_odo_digit_p2_0 ~ 9 img_0_1_2_dial_odo_digit_p3_0 ~ 9 img_0_1_2_dial_odo_digit_p4_0 img_0_1_2_dial_odo_digit_p5_0 img_0_1_2_dial_odo_digit_p6_0 |
| 4 | ODO or FUEL_OW_ADV_NOTICE or FUEL_OVER_WRITE | 1000 ~ 9999 |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 | img_0_1_2_dial_odo_digit_p1_0 ~ 9 img_0_1_2_dial_odo_digit_p2_0 ~ 9 img_0_1_2_dial_odo_digit_p3_0 ~ 9 img_0_1_2_dial_odo_digit_p4_0 ~ 9 img_0_1_2_dial_odo_digit_p5_0 img_0_1_2_dial_odo_digit_p6_0 |
| 5 | ODO or FUEL_OW_ADV_NOTICE or FUEL_OVER_WRITE | 10000 ~ 99999 |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 | img_0_1_2_dial_odo_digit_p1_0 ~ 9 img_0_1_2_dial_odo_digit_p2_0 ~ 9 img_0_1_2_dial_odo_digit_p3_0 ~ 9 img_0_1_2_dial_odo_digit_p4_0 ~ 9 img_0_1_2_dial_odo_digit_p5_0 ~ 9 img_0_1_2_dial_odo_digit_p6_0 |
| 6 | ODO or FUEL_OW_ADV_NOTICE or FUEL_OVER_WRITE | 100000 ~ 999999 |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 | img_0_1_2_dial_odo_digit_p1_0 ~ 9 img_0_1_2_dial_odo_digit_p2_0 ~ 9 img_0_1_2_dial_odo_digit_p3_0 ~ 9 img_0_1_2_dial_odo_digit_p4_0 ~ 9 img_0_1_2_dial_odo_digit_p5_0 ~ 9 img_0_1_2_dial_odo_digit_p6_0 ~ 9 |
| 7 | ODO or FUEL_OW_ADV_NOTICE or FUEL_OVER_WRITE | 0xFFFFFFFF | No display | Not applicable |
| 8 | Other than above | Not applicable | No display | Not applicable |
- Verification Criteria: Verify by executing test cases
- Verification Method: Software Qualification Test, System Qualification Test, Unit Test
- Verification Owner: FV, SW
- System Requirement State: Approved
- Primary Discipline: SW
- ASIL Rating: QM

##### TFDCX32348-93474 (System Requirement)
FUEL_OVER_WRITE shall be displayed with blink.
Blink specification : 2Hz 50% duty, start with OFF state.
Example Behavior :
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- Verification Criteria: Verify by executing test cases
- Verification Method: Software Qualification Test, System Qualification Test, Unit Test
- Verification Owner: FV, SW
- System Requirement State: Draft
- Primary Discipline: SW
- ASIL Rating: QM

#### TFDCX32348-27317: #2 : Trip distance (Heading)

##### TFDCX32348-27318: Table - Trip distance (System Requirement)
Tripmeter displays zero suppression. Refer メータMID表示ルールブック_v1.0.docx
| # | Input |  |  | Output | Design Spec Reference |
| --- | --- | --- | --- | --- | --- |
| # | HMI - HMI_OdoType | HMI - HMI_TRIPA_ODO_VALUE | HMI - HMI_TRIPB_ODO_VALUE | Sample display | GLTF element |
| 1 | TRIP_A | 0.0 ~ 9.9 | Not applicable |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 | img_0_1_2_dial_trip_digit_p1_0 ~ 9 img_0_1_2_dial_trip_dot img_0_1_2_dial_trip_digit_p2_0 ~ 9 |
| 2 | TRIP_A | 10.0 ~ 99.9 | Not applicable |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 | img_0_1_2_dial_trip_digit_p1_0 ~ 9 img_0_1_2_dial_trip_dot img_0_1_2_dial_trip_digit_p2_0 ~ 9 img_0_1_2_dial_trip_digit_p3_0 ~ 9 |
| 3 | TRIP_A | 100.0 ~ 999.9 | Not applicable |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 | img_0_1_2_dial_trip_digit_p1_0 ~ 9 img_0_1_2_dial_trip_dot img_0_1_2_dial_trip_digit_p2_0 ~ 9 img_0_1_2_dial_trip_digit_p3_0 ~ 9 img_0_1_2_dial_trip_digit_p4_0 ~ 9 |
| 4 | TRIP_A | 1000.0 ~ 9999.9 | Not applicable |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 | img_0_1_2_dial_trip_digit_p1_0 ~ 9 img_0_1_2_dial_trip_dot img_0_1_2_dial_trip_digit_p2_0 ~ 9 img_0_1_2_dial_trip_digit_p3_0 ~ 9 img_0_1_2_dial_trip_digit_p4_0 ~ 9 img_0_1_2_dial_trip_digit_p5_0 ~ 9 |
| 5 | TRIP_A | 0xFFFFFFFF | Not applicable | No display | Not applicable |
| 6 | TRIP_B | Not applicable | 0.0 ~ 9.9 |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 | img_0_1_2_dial_trip_digit_p1_0 ~ 9 img_0_1_2_dial_trip_dot img_0_1_2_dial_trip_digit_p2_0 ~ 9 |
| 7 | TRIP_B | Not applicable | 10.0 ~ 99.9 |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 | img_0_1_2_dial_trip_digit_p1_0 ~ 9 img_0_1_2_dial_trip_dot img_0_1_2_dial_trip_digit_p2_0 ~ 9 img_0_1_2_dial_trip_digit_p3_0 ~ 9 |
| 8 | TRIP_B | Not applicable | 100.0 ~ 999.9 |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 | img_0_1_2_dial_trip_digit_p1_0 ~ 9 img_0_1_2_dial_trip_dot img_0_1_2_dial_trip_digit_p2_0 ~ 9 img_0_1_2_dial_trip_digit_p3_0 ~ 9 img_0_1_2_dial_trip_digit_p4_0 ~ 9 |
| 9 | TRIP_B | Not applicable | 1000.0 ~ 9999.9 |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 | img_0_1_2_dial_trip_digit_p1_0 ~ 9 img_0_1_2_dial_trip_dot img_0_1_2_dial_trip_digit_p2_0 ~ 9 img_0_1_2_dial_trip_digit_p3_0 ~ 9 img_0_1_2_dial_trip_digit_p4_0 ~ 9 img_0_1_2_dial_trip_digit_p5_0 ~ 9 |
| 10 | TRIP_B | Not applicable | 0xFFFFFFFF | No display | Not applicable |
| 11 | Other than above | Not applicable | Not applicable | No display | Not applicable |
- Verification Criteria: Verify by executing test cases
- Verification Method: Software Qualification Test, System Qualification Test, Unit Test
- Verification Owner: FV, SW
- System Requirement State: Approved
- Primary Discipline: SW
- ASIL Rating: QM

#### TFDCX32348-27321: #3 : Unit (Heading)

##### TFDCX32348-27322: Table - Unit (System Requirement)
| # | Input |  |  |  |  | Output | Design Spec Reference |
| --- | --- | --- | --- | --- | --- | --- | --- |
| # | HMI - HMI_OdoType | HMI - HMI_TOTAL_ODO_VALUE | HMI - HMI_TRIPA_ODO_VALUE | HMI - HMI_TRIPB_ODO_VALUE | InternalSignal - Display_Distance_Unit | Sample display | GLTF element |
| 1 | ODO | 0xFFFFFFFF | Not applicable | Not applicable | Not applicable | No display | Not applicable |
| 2 | ODO | Other than above | Not applicable | Not applicable | 0 [km] |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 | img_0_1_2_dial_odo_unit_km |
| 3 | ODO | Other than above | Not applicable | Not applicable | 1 [mile] |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 | img_0_1_2_dial_odo_unit_mi |
| 4 | TRIP_A | Not applicable | 0xFFFFFFFF | Not applicable | Not applicable | No display | Not applicable |
| 5 | TRIP_A | Not applicable | Other than above | Not applicable | 0 [km] |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 | img_0_1_2_dial_trip_unit_km |
| 6 | TRIP_A | Not applicable | Other than above | Not applicable | 1 [mile] |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 | img_0_1_2_dial_trip_unit_mi |
| 7 | TRIP_B | Not applicable | Not applicable | 0xFFFFFFFF | Not applicable | No display | Not applicable |
| 8 | TRIP_B | Not applicable | Not applicable | Other than above | 0 [km] |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 | img_0_1_2_dial_trip_unit_km |
| 9 | TRIP_B | Not applicable | Not applicable | Other than above | 1 [mile] |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 | img_0_1_2_dial_trip_unit_mi |
- Verification Criteria: Verify by executing test cases
- Verification Method: Software Qualification Test, System Qualification Test, Unit Test
- Verification Owner: FV, SW
- System Requirement State: Approved
- Primary Discipline: SW
- ASIL Rating: QM

#### TFDCX32348-27353: #4 : A/B mark (Heading)

##### TFDCX32348-27354: Table - A/B mark (System Requirement)
| # | Input |  |  | Output | Design Spec Reference |
| --- | --- | --- | --- | --- | --- |
| # | HMI - HMI_OdoType | HMI - HMI_TRIPA_ODO_VALUE | HMI - HMI_TRIPB_ODO_VALUE | Sample display | GLTF element |
| 1 | ODO | Not applicable | Not applicable | No display | Not applicable |
| 2 | TRIP_A | 0xFFFFFFFF | Not applicable | No display | Not applicable |
| 3 | TRIP_A | Other then 0xFFFFFFFF | Not applicable |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 | img_0_1_2_dial_trip_icon_a |
| 4 | TRIP_B | Not applicable | 0xFFFFFFFF | No display | Not applicable |
| 5 | TRIP_B | Not applicable | Other then 0xFFFFFFFF |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 | img_0_1_2_dial_trip_icon_b |
- Verification Criteria: Verify by executing test cases
- Verification Method: Software Qualification Test, System Qualification Test, Unit Test
- Verification Owner: FV, SW
- System Requirement State: Approved
- Primary Discipline: SW
- ASIL Rating: QM

#### TFDCX32348-56055: #5 : Maintenance icon (Heading)

##### TFDCX32348-56056: Table - Maintenance icon (System Requirement)
| # | Input | Output | Design Spec Reference |
| --- | --- | --- | --- |
| # | HMI - HMI_OdoType | Sample Image | GLTF element |
| 1 | OILMIL_DISTANCE_INT or OILMIL_DISTANCE | Display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 | img_0_1_2_dial_oil_mainte_icon |
| 2 | Other than above | No display |  |
- Verification Criteria: Verify by executing test cases
- Verification Method: Software Qualification Test, System Qualification Test, Unit Test
- Verification Owner: FV, SW
- System Requirement State: Approved
- Primary Discipline: SW
- ASIL Rating: QM

#### TFDCX32348-56060: #6,7 : Distance, Unit (Heading)

##### TFDCX32348-56061: Table - Distance, Unit (System Requirement)
| # | Input |  |  |  | Output |  | Design Spec Reference |
| --- | --- | --- | --- | --- | --- | --- | --- |
| # | HMI - HMI_OdoType | HMI - OILMIL_DISTANCE_AREA_STATUS | HMI - OILMIL_DISTANCE_VALUE | HMI - OILMIL_UNIT_VALUE | Distance (**) | Unit (**) | GLTF element |
| 1 | OILMIL_DISTANCE or OILMIL_DISTANCE_INT | 0 (OFF) | x | x | blank | blank |  |
| 2 | OILMIL_DISTANCE or OILMIL_DISTANCE_INT | 1 (NO_DISP_DISTANCE) | x | x | blank | blank |  |
| 3 | OILMIL_DISTANCE or OILMIL_DISTANCE_INT | 2 (DISTANCE) | 0000h-7FFFh 8004h-FFFFh | 0 (km) | 0000h-7FFFh (*) 8004h-FFFFh (*) | km | img_0_1_2_dial_oil_mainte_white_digit_p*_1～9 img_0_1_2_dial_oil_mainte_unit_km |
| 4 | OILMIL_DISTANCE or OILMIL_DISTANCE_INT | 2 (DISTANCE) | 0000h-7FFFh 8004h-FFFFh | 1 (mile) | 0000h-7FFFh (*) 8004h-FFFFh (*) | mi | img_0_1_2_dial_oil_mainte_white_digit_p*_1～9 img_0_1_2_dial_oil_mainte_unit_mi |
| 5 | OILMIL_DISTANCE or OILMIL_DISTANCE_INT | 2 (DISTANCE) | 0000h-7FFFh 8004h-FFFFh | 2 (invalid) | x | blank |  |
| 6 | OILMIL_DISTANCE or OILMIL_DISTANCE_INT | 3 (ERROR) | x | 0 (km) | blank | km | img_0_1_2_dial_oil_mainte_unit_km |
| 7 | OILMIL_DISTANCE or OILMIL_DISTANCE_INT | 3 (ERROR) | x | 1 (mile) | blank | mi | img_0_1_2_dial_oil_mainte_unit_mi |
| 8 | OILMIL_DISTANCE or OILMIL_DISTANCE_INT | 3 (ERROR) | x | 2 (invalid) | x | blank |  |
| 9 | OILMIL_DISTANCE or OILMIL_DISTANCE_INT | 4 (CALC) | x | 0 (km) | "-----" (Display 5 of '-') | km | img_0_1_2_dial_oil_mainte_white_digit_p*_blank img_0_1_2_dial_oil_mainte_unit_km |
| 10 | OILMIL_DISTANCE or OILMIL_DISTANCE_INT | 4 (CALC) | x | 1 (mile) | "------" (Display 5 of '-') | mi | img_0_1_2_dial_oil_mainte_white_digit_p*_blank img_0_1_2_dial_oil_mainte_unit_mi |
| 11 | OILMIL_DISTANCE or OILMIL_DISTANCE_INT | 4 (CALC) | x | 2 (invalid) | x | blank |  |
| 12 | Other than above | X | X | X | No display | No display |  |
Note:
(*) For distance value, Invert display shall be applied conditionally.
For details, refer to "TFDCX32348-56063 Highlight".
Note that HMI - OILMIL_DISTANCE_VALUE is a signed integer
(**) For both of the output, different textboxes are assigned.
Distance corresponds to larger textbox.
Unit corresponds to smaller textbox.
- Verification Criteria: Verify by executing test cases
- Verification Method: Software Qualification Test, System Qualification Test, Unit Test
- Verification Owner: FV, SW
- System Requirement State: Approved
- Primary Discipline: SW
- ASIL Rating: QM

#### TFDCX32348-56062: #8 : Highlight (Heading)

##### TFDCX32348-56063: Table - Highlight (System Requirement)
| # | Input |  |  | Output | Design Spec Reference |
| --- | --- | --- | --- | --- | --- |
| # | HMI - HMI_OdoType | HMI - OILMIL_DISTANCE_AREA_STATUS | OILMIL_REVERSAL_OFFON | Sample Image | GLTF element |
| 1 | OILMIL_DISTANCE or OILMIL_DISTANCE_INT | 2 (DISTANCE) | ON |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 Distance value is displayed with black color on white background | grp_0_1_2_dial_oil_mainte_black_digit |
| 2 | OILMIL_DISTANCE or OILMIL_DISTANCE_INT | 2 (DISTANCE) | OFF |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 Distance value is displayed normally | grp_0_1_2_dial_oil_mainte_white_digit |
| 3 | OILMIL_DISTANCE or OILMIL_DISTANCE_INT | Other than above | X |  |  |
| 4 | Other than above | X | X | No display |  |
Note: The highlight will change width depending on the number of digits.
2 digits:
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5 digits:
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- Verification Criteria: Verify by executing test cases
- Verification Method: Software Qualification Test, System Qualification Test, Unit Test
- Verification Owner: FV, SW
- System Requirement State: Approved
- Primary Discipline: SW
- ASIL Rating: QM

#### TFDCX32348-62030: #9 : ACCESSORY (Heading)

##### TFDCX32348-62039: Table - ACCESSORY (System Requirement)
Table - ACCESSORY
| # | Input | Output |  | Design Spec Reference |
| --- | --- | --- | --- | --- |
| # | HMI - HMI_OdoType | Text : Visteon Request ID | Sample Text (English（USA)) | GLTF element |
| 1 | POWER_STATUS_ACC | TXT_O_EIGCON_REQ02 | “ACCESSORY“ | txt_0_1_2_dial_power_accessories |
| 2 | Other than above | - | No display |  |
- Verification Criteria: Verify by executing test cases
- Verification Method: Software Qualification Test, System Qualification Test, Unit Test
- Verification Owner: FV, SW
- System Requirement State: Approved
- Primary Discipline: SW
- ASIL Rating: QM

#### TFDCX32348-62032: #10 : POWER ON (Heading)

##### TFDCX32348-62037: Table - POWER ON (System Requirement)
Table - POWER ON
| # | Input | Output |  | Design Spec Reference |
| --- | --- | --- | --- | --- |
| # | HMI - HMI_OdoType | Text : Visteon Request ID | Sample Text (English（USA)) | GLTF element |
| 1 | POWER_STATUS_ON | TXT_O_EIGCON_REQ04 | “POWER ON“ | txt_0_1_2_dial_power_ignition_on |
| 2 | Other than above | - | No display |  |
- Verification Criteria: Verify by executing test cases
- Verification Method: Software Qualification Test, System Qualification Test, Unit Test
- Verification Owner: FV, SW
- System Requirement State: Approved
- Primary Discipline: SW
- ASIL Rating: QM

#### TFDCX32348-62033: #11 : POWER ON Background (Heading)

##### TFDCX32348-62034: Table - POWER ON Background (System Requirement)
Table - POWER ON Background
| # | Input | Output | Design Spec Reference |
| --- | --- | --- | --- |
| # | HMI - HMI_OdoType | Sample Image | GLTF element |
| 1 | POWER_STATUS_ON | Display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 | img_0_1_2_dial_power_bg |
| 2 | Other than above | No display |  |
- Verification Criteria: Verify by executing test cases
- Verification Method: Software Qualification Test, System Qualification Test, Unit Test
- Verification Owner: FV, SW
- System Requirement State: Approved
- Primary Discipline: SW
- ASIL Rating: QM

## TFDCX32348-70410: Animation Specification (Heading)
- System Requirement State: Draft
- Primary Discipline: TBD
- ASIL Rating: TBD

### TFDCX32348-70411: Animation Specification (System Requirement)
Animation Specification
| # | Animation Specification |  |  |
| --- | --- | --- | --- |
| 1 | Animating element |  | Entire group |
| 2 | Frame rate |  | 30 fps |
| 3.a | Trigger | HMI_OdoType changes from any state to BLANK | Remove the content immediately |
| 3.b | Trigger | HMI_OdoType changes from (any state other than BLANK) to OFF | Remove the content with Fade-out. Refer Table_1 for Opacity control. |
| 3.c | Trigger | BLANK to (any state other than OFF) | This shall be displayed with Fade-in. This is covered in IG ON Animation. Refer SRD "GUI_Transition Animations" |
| 3.d | Trigger | OFF to (any state other than BLANK) | Display with Fade-in. Linear opacity control. 333ms (10 frames). |
| 3.e | Trigger | Changes among values other than BLANK and OFF | No animation |
| 4 | Remarks |  | If a new trigger is received during an ongoing animation, the animation should stop immediately, transition to its final state and initiate the next animation. |
Table_1 (ON to OFF)
| Frame # | Opacity (%) |
| --- | --- |
| (Initial) | 100 |
| 1 | 75 |
| 2 | 57 |
| 3 | 42 |
| 4 | 29 |
| 5 | 20 |
| 6 | 12 |
| 7 | 7 |
| 8 | 3 |
| 9 | 1 |
| 10 | 0 |
- System Requirement State: Draft
- Primary Discipline: TBD
- ASIL Rating: TBD

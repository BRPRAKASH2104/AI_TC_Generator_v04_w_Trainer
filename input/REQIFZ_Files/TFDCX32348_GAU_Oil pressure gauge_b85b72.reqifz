# Json2ReqIF Transformation

# Specification: GAU_Oil pressure gauge
- JDA Snapshot Date: 2025-09-04 02:41:50

## TFDCX32348-73469: GAU_Oil pressure gauge (Heading)

## TFDCX32348-73631: History (Heading)

### TFDCX32348-73632: Table (Information)
| Version | Date | Name | Description of change | Baseline |
| --- | --- | --- | --- | --- |
| 0.1 | Mar/7/2025 | Hiromune Wachi | Newly create for 12.3inch FDC. [SYS-Story] : TFDCX32348-64395: [SYS][12.3FDC][R4][APP][Trip Computer] Oil pressure gauge | BL_20250324_01 |
| 0.2 | Jul/24/2025 | Hiromune Wachi | ・Added application conditions for B_POM_113 and B_POM_1EA. ・Deleted the “[B] Function presence/absence judgment“ process. [SYS-Story] : TFDCX32348-96483: [SYS][12.3FDC][R5.2][STDQA3302][APP][Trip Computer] Added frame reception condition for B_POM | BL_20250728_01 |

## TFDCX32348-73470: Overview (Heading)

### TFDCX32348-73471: This SRD defines the requirements for Oil pressure gauge. (Information)

## TFDCX32348-73472: Reference Document (Heading)

### TFDCX32348-73473: External Sources (Heading)

#### TFDCX32348-73474: MET-M_OILP-CSTD-A0-00-A-C1.doc (Information)

## TFDCX32348-73475: Input Requirements (Heading)

### TFDCX32348-73478: InternalSignal - IgnMode (System Interface)
- System Requirement State: Approved

### TFDCX32348-73479: InternalSignal - ReadytoTravelFlag (System Interface)
- System Requirement State: Approved

### TFDCX32348-101148: Internal Signal - PTSysTypeFlag (System Interface)
- System Requirement State: Approved

### TFDCX32348-73677: CANSignal - B_POM_113 (System Interface)
- System Requirement State: Approved

### TFDCX32348-73679: CANSignal - B_POM_1EA (System Interface)
- System Requirement State: Approved

### TFDCX32348-101150: MCUCONST - MCUID0025 (System Interface)
- System Requirement State: Approved

### TFDCX32348-73683: MCUCONST - MCUID0833 (System Interface)
- System Requirement State: Approved

### TFDCX32348-73684: MCUCONST - MCUID0834 (System Interface)
- System Requirement State: Approved

### TFDCX32348-73686: MCUCONST - MCUID0835 (System Interface)
- System Requirement State: Approved

### TFDCX32348-73687: MCUCONST - MCUID0836 (System Interface)
- System Requirement State: Approved

### TFDCX32348-73688: MCUCONST - MCUID0837 (System Interface)
- System Requirement State: Approved

### TFDCX32348-73689: MCUCONST - MCUID0838 (System Interface)
- System Requirement State: Approved

### TFDCX32348-73690: MCUCONST - MCUID0839 (System Interface)
- System Requirement State: Approved

### TFDCX32348-73691: MCUCONST - MCUID0840 (System Interface)
- System Requirement State: Approved

## TFDCX32348-73476: Output Requirements (Heading)

### TFDCX32348-73726: HMI - HMI_OIL_PRESSURE_BAR (System Interface)
HMI - HMI_OIL_PRESSURE_BAR
Range : 0[0.0%], 1[0.1%], ..., 1000[100.0%], -1[No data]
- System Requirement State: Approved

### TFDCX32348-73732: InternalSignal - OilPressureGauge_Prsnt (System Interface)
InternalSignal - OilPressureGauge_Prsnt
Range : 0[NOT_PRSNT], 1[PRSNT]
- System Requirement State: Approved

## TFDCX32348-73477: Performance Requirements (Heading)

### TFDCX32348-73633: General (Heading)

#### TFDCX32348-73640: Processing block structure (Heading)

##### TFDCX32348-73642: Figure (System Requirement)
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- Verification Criteria: Verify by design review
- Verification Method: Code/Design Review
- Verification Owner: SW
- System Requirement State: Approved
- Primary Discipline: SW
- ASIL Rating: QM

##### TFDCX32348-73643: Table (System Requirement)
| # | Signal name | Range |
| --- | --- | --- |
| ① | CANInputType | 0[Undetermined], 1[113 : ENG1G17], 2[1EA : ENG1S98] |
| ②-1 | SamplingUpdateFlag | 0[No update], 1[Updated] |
| ②-2 | B_POM_In | -1[No data], 0[0.000kPa], 1[0.625kPa], ..., 1280[800.000kPa] |
| ③ | Average_B_POM | -1[No data], 0[0.000kPa], 1[0.625kPa], ..., 1280[800.000kPa] |
| ④ | Final_B_POM | -1[No data], 0[0.000kPa], 1[0.625kPa], ..., 1280[800.000kPa] |
- Verification Criteria: Verify by design review
- Verification Method: Code/Design Review
- Verification Owner: SW
- System Requirement State: Approved
- Primary Discipline: SW
- ASIL Rating: QM

#### TFDCX32348-73641: Parameters (Heading)

##### TFDCX32348-74570: Table - Parameters (System Requirement)
| # | Parameter name | Value |
| --- | --- | --- |
| 1 | 【L02SCL】 | MCUID0833 x 10 Note : Set the resolution to 0.1% |
| 2 | 【L08SCL】 | MCUID0834 x 10 Note : Set the resolution to 0.1% |
| 3 | 【OPR1】 | MCUID0835 x 10000 Note : Set the resolution to 0.001kPa |
| 4 | 【OPR2】 | MCUID0836 x 10000 Note : Set the resolution to 0.001kPa |
| 5 | 【OPR3】 | MCUID0837 x 10000 Note : Set the resolution to 0.001kPa |
| 3 | 【OLP_TM】 | MCUID0838 Note : If MCUID0838 is greater than 10, replace it with 10. |
| 4 | 【N_AVE】 | MCUID0839 Note : If MCUID0839 is greater than 10, replace it with 10. |
- Verification Criteria: Verify by design review
- Verification Method: Code/Design Review
- Verification Owner: SW
- System Requirement State: Approved
- Primary Discipline: SW
- ASIL Rating: QM

### TFDCX32348-73634: Process (Heading)

#### TFDCX32348-73742: [A] Initialization (Heading)

##### TFDCX32348-73745: Table - Initialization (System Requirement)
| # | Name | Initilize @ Battery Connect / Cold Reset | Initialize @ Module Wake-Up | IgnMode change from ON to OFF | Init Value | Remark |
| --- | --- | --- | --- | --- | --- | --- |
| 1 | HMI - HMI_OIL_PRESSURE_BAR | 〇 | 〇 | 〇 | -1[No data] | Output signal of this module |
| 2 | InternalSignal - OilPressureGauge_Prsnt | 〇 | 〇 | X | [*1] | Output signal of this module |
| 3 | CANInputType | 〇 | X | X | 0[Undetermined] | Output of [B] block |
| 4 | SamplingTimingCnt (Range : 0, 1, ..., 9) | 〇 | 〇 | 〇 | 0 | Variable of [C] block |
| 5 | SamplingUpdateFlag | 〇 | 〇 | 〇 | 0[No update] | Output of [C] block |
| 6 | B_POM_In | 〇 | 〇 | 〇 | -1[No data] | Output of [C] block |
| 7 | BufferIndex (Range : 0, 1, ..., 9) | 〇 | 〇 | 〇 | 0 | Variable of [D] block |
| 8 | BufferStatusFlag (Range : -1[No data], 0[Not full], 1[Full]) | 〇 | 〇 | 〇 | -1[No data] | Variable of [D] block |
| 9 | SampleBuffer[10] (Range of each data : -1[No data], 0[0.000kPa], 1[0.625kPa], ..., 1280[800.000kPa]) | 〇 | 〇 | 〇 | Clear all data (Set -1[No data] to all data) | Variable of [D] block |
| 10 | Average_B_POM | 〇 | 〇 | 〇 | -1[No data] | Output of [D] block |
| 11 | DivNum (Range : 1, 2, ..., 10) | 〇 | 〇 | 〇 | 1 | Variable of [E] block |
| 12 | Final_B_POM | 〇 | 〇 | 〇 | -1[No data] | Output of [E] block |
| 13 | OilPressureValue (Range : 0[0.000kPa] - 800000[800.000kPa]) | 〇 | 〇 | 〇 | 0[0.000kPa] | Variable of [F] block |
[*1] : Follow the table below.
| # | Input | Output |
| --- | --- | --- |
| # | MCUID0840 | OilPressureGauge_Prsnt |
| 1 | 1[with] | 1[PRSNT] |
| 2 | Other than above | 0[NOT_PRSNT] |
- Verification Criteria: Verify by executing test cases
- Verification Method: System Qualification Test, Unit Test
- Verification Owner: FV, SW
- System Requirement State: Approved
- Primary Discipline: SW
- ASIL Rating: QM

#### TFDCX32348-101454: [B] CAN input applicability judgment (Heading)

##### TFDCX32348-101455: Table - Function presence/absence judgment (System Requirement)
| # | Input |  |  | Output |
| --- | --- | --- | --- | --- |
| # | IgnMode | PTSysTypeFlag | MCUID0025 | CANInputType |
| 1 | OFF | X | X | No change |
| 2 | ON | 0001b (CONV) | Other than 6[070D] | 2[1EA : ENG1S98] |
| 3 | ON | 0010b (S&S) | Other than 6[070D] | 2[1EA : ENG1S98] |
| 4 | ON | Other than above |  | 1[113 : ENG1G17] |
- Verification Criteria: Verify by executing test cases
- Verification Method: System Qualification Test, Unit Test
- Verification Owner: FV, SW
- System Requirement State: Approved
- Primary Discipline: SW
- ASIL Rating: QM

#### TFDCX32348-73743: [B] Function presence/absence judgment (Heading)
- System Requirement State: Rejected

##### TFDCX32348-73744 (System Requirement)
Table - Function presence/absence judgment
| # | Input |  | Output |
| --- | --- | --- | --- |
| # | IgnMode | MCUID0840 | OilPressureGauge_Prsnt |
| 1 | OFF → ON | 1[with] | 1[PRSNT] |
| 2 | OFF → ON | Other than above | 0[NOT_PRSNT] |
| 3 | Other than above |  | No change |
- System Requirement State: Rejected

#### TFDCX32348-73746: Main operation (Heading)

##### TFDCX32348-73747 (System Requirement)
Each block of the main operation shall be executed when all of the following conditions are met.
- OilPressureGauge_Prsnt == 1[PRSNT]
- IgnMode == ON
- ReadytoTravelFlag == ON
- 【OLP_TM】 != 0[0msec]
- 【N_AVE】 != 0[0times]
- CANInputType = “1[113 : ENG1G17] or 2[1EA : ENG1S98]”
If any of the above conditions are not met, set the HMI_OIL_PRESSURE_BAR as follows:
- HMI_OIL_PRESSURE_BAR = -1[No data]
- Verification Criteria: Verify by executing test cases
- Verification Method: System Qualification Test, Unit Test
- Verification Owner: FV, SW
- System Requirement State: Approved
- Primary Discipline: SW
- ASIL Rating: QM

##### TFDCX32348-73750: [C] Sampling process (Heading)

###### TFDCX32348-73813: Table - Sampling process (System Requirement)
| # | Input |  |  |  | Output |  |  |
| --- | --- | --- | --- | --- | --- | --- | --- |
| # | SamplingTimingCnt | CANInputType | CAN Signal Communication Status - B_POM_1EA | CAN Signal Communication Status - B_POM_113 | B_POM_In | SamplingUpdateFlag | SamplingTimingCnt |
| 1 | 0 | 1[113 : ENG1G17] | X Never received (Never Received: 1 Communication Failure: 0) OR Communication failure (Never Received: x Communication Failure: 1) | Never received (Never Received: 1 Communication Failure: 0) OR Communication failure (Never Received: x Communication Failure: 1) | -1[No data] | 1[Updated] | 0 |
| 2 | 0 | 1[113 : ENG1G17] | X Never received (Never Received: 1 Communication Failure: 0) OR Communication failure (Never Received: x Communication Failure: 1) | Normal (Never Received: 0 Communication Failure: 0) | CANSignal - B_POM_113 | 1[Updated] | [*1] |
| 3 | 0 | 2[1EA : ENG1S98] | Never received (Never Received: 1 Communication Failure: 0) OR Communication failure (Never Received: x Communication Failure: 1) | X | -1[No data] | 1[Updated] | 0 |
| 4 | 0 | 2[1EA : ENG1S98] | Normal (Never Received: 0 Communication Failure: 0) | X | CANSignal - B_POM_1EA | 1[Updated] | [*1] |
| 5 | Other than 0 | 1[113 : ENG1G17] | X Never received (Never Received: 1 Communication Failure: 0) OR Communication failure (Never Received: x Communication Failure: 1) | Never received (Never Received: 1 Communication Failure: 0) OR Communication failure (Never Received: x Communication Failure: 1) | -1[No data] | 1[Updated] | 0 |
| 6 | Other than 0 | 1[113 : ENG1G17] | X Never received (Never Received: 1 Communication Failure: 0) OR Communication failure (Never Received: x Communication Failure: 1) | Normal (Never Received: 0 Communication Failure: 0) | No change | 0[No update] | [*1] |
| 7 | Other than 0 | 2[1EA : ENG1S98] | Never received (Never Received: 1 Communication Failure: 0) OR Communication failure (Never Received: x Communication Failure: 1) | X | -1[No data] | 1[Updated] | 0 |
| 8 | Other than 0 | 2[1EA : ENG1S98] | Normal (Never Received: 0 Communication Failure: 0) | X | No change | 0[No update] | [*1] |
[*1] : Set according to the table below.
| # | Input | Output |
| --- | --- | --- |
| # | SamplingTimingCnt | SamplingTimingCnt |
| 1 | SamplingTimingCnt <（【OLP_TM】 - 1) | Increment by 1 |
| 2 | (【OLP_TM】 - 1) ≦ SamplingTimingCnt | 0 |
- Verification Criteria: Verify by executing test cases
- Verification Method: System Qualification Test, Unit Test
- Verification Owner: FV, SW
- System Requirement State: Approved
- Primary Discipline: SW
- ASIL Rating: QM

##### TFDCX32348-73752: [D] Averaging process (Heading)

###### TFDCX32348-73902: Table - Averaging process (System Requirement)
| # | Input |  |  |  | Output |  |  |
| --- | --- | --- | --- | --- | --- | --- | --- |
| # | SamplingUpdateFlag | B_POM_In | BufferIndex | BufferStatusFlag | SampleBuffer[] | BufferIndex [*1] | BufferStatusFlag |
| 1 | 1[Updated] | -1[No data] | X | X | Clear all data (Set -1[No data] to all data) | 0 | -1[No data] |
| 2 | 1[Updated] | Other than -1[No data] | BufferIndex >=(【N_AVE】 - 1) | X | Store B_POM_In value in SampleBuffer[【N_AVE】 - 1] | 0 | 1[Full] |
| 3 | 1[Updated] | Other than -1[No data] | BufferIndex < (【N_AVE】 - 1) | 1[Full] | Store B_POM_In value in SampleBuffer[BufferIndex] | Increment by 1 | No change |
| 4 | 1[Updated] | Other than -1[No data] | BufferIndex < (【N_AVE】 - 1) | Other than 1[Full] | Store B_POM_In value in SampleBuffer[BufferIndex] | Increment by 1 | 0[Not full] |
| 5 | Other than above |  |  |  | No change | No change | No change |
[*1] : Update BufferIndex after updating SampleBuffer.
- Verification Criteria: Verify by executing test cases
- Verification Method: System Qualification Test, Unit Test
- Verification Owner: FV, SW
- System Requirement State: Approved
- Primary Discipline: SW
- ASIL Rating: QM

###### TFDCX32348-73959: Calculation of average data (System Requirement)
Cluster shall calculate the averaged data according to the following calculation:
Case of “BufferStatusFlag == -1[No data]“
Average_B_POM = -1[No data]
Case of “BufferStatusFlag == 0[Not full]“
Average_B_POM = Round{(“Sum of SampleBuffer[0] to SampleBuffer[BufferIndex - 1]” / BufferIndex), 0}
Case of “BufferStatusFlag == 1[Full]“
Average_B_POM = Round{(“Sum of SampleBuffer[0] to SampleBuffer[【N_AVE】 - 1]” / 【N_AVE】), 0}
- Verification Criteria: Verify by executing test cases
- Verification Method: System Qualification Test, Unit Test
- Verification Owner: FV, SW
- System Requirement State: Approved
- Primary Discipline: SW
- ASIL Rating: QM

##### TFDCX32348-73753: [E] Gradual change processing (Heading)

###### TFDCX32348-74065: Table - Gradual change processing (System Requirement)
| ＃ | Input |  |  | Output |  |
| --- | --- | --- | --- | --- | --- |
| ＃ | SamplingUpdateFlag | Average_B_POM | DivNum | DivNum | Final_B_POM [*2] |
| 1 | 1[Updated] | -1[No data] | X | 1 | -1[No data] |
| 2 | 1[Updated] | Other than -1[No data] | X | 【OLP_TM】 | Final_B_POM[*1] + Round{((Average_B_POM-Final_B_POM[*1]) / DivNum), 0} |
| 3 | Other than 1[Updated] | -1[No data] | X | 1 | -1[No data] |
| 4 | Other than 1[Updated] | Other than -1[No data] | 1 | No change | No change |
| 5 | Other than 1[Updated] | Other than -1[No data] | DivNum > 1 | Decrement by 1 | Final_B_POM[*1]+ Round{((Average_B_POM-Final_B_POM[*1]) / DivNum), 0} |
[*1] : The previous value of Final_B_POM.
[*2] : This column is performed after updating DivNum.
- Verification Criteria: Verify by executing test cases
- Verification Method: System Qualification Test, Unit Test
- Verification Owner: FV, SW
- System Requirement State: Approved
- Primary Discipline: SW
- ASIL Rating: QM

##### TFDCX32348-73754: [F] Update display data (Heading)

###### TFDCX32348-74076 (System Requirement)
Cluster shall calculate output data for each of the following conditions.
Case of “Final_B_POM == -1[No data]“:
HMI_OIL_PRESSURE_BAR = -1[No data]
Case of “Final_B_POM != -1[No data]“:
Step1
OilPressureValue = Final_B_POM x 625
Note : Set the resolution to 0.001kPa
Step2
Cluster shall calculate HMI_OIL_PRESSURE_BAR according to the table below.
| # | Input | Output | Remarks |
| --- | --- | --- | --- |
| # | OilPressureValue [a] | HMI_OIL_PRESSURE_BAR | Remarks |
| 1 | 0 | 0[0.0%] | - |
| 2 | 0 < [a] < 【OPR1】 | 【L02SCL】 x [a] / 【OPR1】 | Calculate with interpolation method |
| 3 | 【OPR1】 ≦ [a] ≦ 【OPR2】 | 【L02SCL】 | - |
| 4 | 【OPR2】 < [a] < 【OPR3】 | 【L02SCL】 + (【L08SCL】 - 【L02SCL】) x ([a] - 【OPR2】) / (【OPR3】 - 【OPR2】) | Calculate with interpolation method |
| 5 | 【OPR3】 ≦ [a] | 【L08SCL】 | - |
- Verification Criteria: Verify by executing test cases
- Verification Method: System Qualification Test, Unit Test
- Verification Owner: FV, SW
- System Requirement State: Approved
- Primary Discipline: SW
- ASIL Rating: QM

###### TFDCX32348-74197: Customer spec - Indication specifications (Information)
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
# Json2ReqIF Transformation

# Specification: TT_Taillight Telltale
- JDA Snapshot Date: 2025-10-29 07:19:02

## TFDCX32348-955: TT_Taillight Telltale (Heading)

## TFDCX32348-957: History (Heading)

### TFDCX32348-1467: Version (Information)
| Version | Date | Name | Description of change | Baseline |
| --- | --- | --- | --- | --- |
| 0.1 | APR/18/2024 | Takeshi Yamane | Newly create TFDCX32348-23735 [SYS][12.3FDC][APP][Telltale] TAIL indicator (CAN communication or linear connection) | BL_20240521_01 |
| 0.2 | Oct/30/2024 | Takuya Tamura | TFDCX32348-54350: [SYS][12.3FDC][APP][Telltale] Change telltale icons by country code Added InternalSignal - TT_DESTVali and determination | BL_20241106_01 |
| 0.3 | Aug/26/2025 | Syuta Matsuoka | Change in symbol determination method [SYS-Task] TFDCX32348-89338: [SYS][12.3FDC][R6.1][D3576][APP][Telltale] Destination variation list (Telltale) | BL_20250828_01 |

## TFDCX32348-959: Reference Document (Heading)

### TFDCX32348-1469: MET-B_TTAIL-CSTD-0-01-A-C1.doc (Information)

### TFDCX32348-1470: MET-B_TTAIL-CSTD-0-XX-X-C1-ALL-a.docx (Information)

### TFDCX32348-1472: DMS_MET-B_TTAIL-CSTD-0-01-A-C1.xls (Information)

### TFDCX32348-54220: MET-M_DESTVARI-CSTD-A0-11-A-C0.xlsx (Information)

## TFDCX32348-960: Overview (Heading)

### TFDCX32348-1474: This SRD defines Telltale of Taillight (Information)

## TFDCX32348-962: Input Requirements (Heading)

### TFDCX32348-1476: InternalSignal – IgnMode (System Interface)
- Verification Criteria: Verify by design review

### TFDCX32348-1477: InternalSignal – AppMode (System Interface)
- Verification Criteria: Verify by design review

### TFDCX32348-1479: CANSignal – TAIL (Message Label: BDB1... (System Interface)
CANSignal – TAIL (Message Label: BDB1S03)
- Verification Criteria: Verify by design review

### TFDCX32348-54024: InternalSignal - TT_DESTVali (System Interface)

### TFDCX32348-105743: InternalSignal - DESTID0029 (System Interface)

## TFDCX32348-964: Output Requirements (Heading)

### TFDCX32348-1485: TT – Taillight_Telltale Meaning: Th... (System Interface)
TT – Taillight_Telltale
Meaning: This parameter indicates the display state of the Taillight Telltale.
Range: OFF, ON
Initial Value: OFF
- Verification Criteria: Verify by design review

### TFDCX32348-1487: InternalSignal – TailLamp_TT_State M... (System Interface)
InternalSignal – TailLamp_TT_State
Meaning: This parameter indicates the display state of the Taillight Telltale.
Range: FALSE, TRUE
Initial Value: FALSE
Note: This internal signal is used for CAN bus wake-up/sleep control.
- Verification Criteria: Verify by design review

### TFDCX32348-106480: InternalSignal - TLHD_Select (System Interface)

## TFDCX32348-966: Performance Requirements (Heading)

### TFDCX32348-1491: Display Symbol (Heading)

#### TFDCX32348-3280: Display Symbol: Display Color: Pure ... (Information)
1. Display Symbol:
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2. Display Color: Pure Green
3. Destination: All [North America(CONV)_USA, North America(HEV)_USA, North America(CONV)_CANADA, Middle East(CONV), General(CONV), Australia(HEV), Middle East(HEV), General(HEV)]

### TFDCX32348-1493: Bulb Check (Heading)

#### TFDCX32348-3282: None (System Requirement)
- ASIL Rating: QM

### TFDCX32348-1495: Initial Process (Heading)

#### TFDCX32348-3285: When +B is connected or when Meter wa... (System Requirement)
When +B is connected or when Meter wake up:
Turn off the Taillight telltale until the lighting signal received.
- Verification Criteria: Verify by executing test cases
- Verification Method: System Qualification Test, Unit Test
- Verification Owner: FV, SW
- System Requirement State: Approved
- Secondary Disciplines: FV, SW
- Primary Discipline: SW
- ASIL Rating: QM

### TFDCX32348-1498: Telltale Control (Heading)

#### TFDCX32348-3289: CAN Signal TAIL Determination (Heading)

##### TFDCX32348-5529: Table - CAN Signal TAIL Determination (System Requirement)
| # | Input |  | Output |
| --- | --- | --- | --- |
| # | InternalSignal -DESTID0029 | InternalSignal - TT_DESTVali | InternalSignal - TLHD_Select |
| 1 | (Initialize at CPU reset or wakeup) |  | TAIL |
| 2 | 0 | x | TAIL |
| 3 | 1 | x | HEAD |
| 4 | Other than above | 0 | HEAD |
| 5 | Other than above | 1 | TAIL |
| # | Input |  |  |  |  |  |  | Output |  | Remark |
| --- | --- | --- | --- | --- | --- | --- | --- | --- | --- | --- |
| # | InternalSignal - TLHD_Select InternalSignal - TT_DESTVali | Internal Signal - AppMode | CAN Signal - TAIL never received status | CAN Signal - TAIL communication failure status | CAN Signal - TAIL | Internal Signal - IgnMode | TT - Taillight_Telltale | Internal Signal - TailLamp_TT_State |  | Remark |
| 1 | (Initialize at CPU reset or wakeup) |  |  |  |  |  | OFF | FALSE | Initialization |  |
| 2 | HEAD | X | X | X | X | X | OFF | FALSE | - |  |
| 3 | TAIL | Normal Network Mode | 1(Never Received) | 0(Normal) | X | X | No change | No change | Before 1st CAN reception. |  |
| 4 | TAIL | Normal Network Mode | X | 1(Communication Failure) | X | OFF | OFF | FALSE | Communication failure during IG OFF. |  |
| 5 | TAIL | Normal Network Mode | X | 1(Communication Failure) | X | ON | No change | No change | Communication failure during IG ON. |  |
| 6 | TAIL | Normal Network Mode | 0(Received) | 0(Normal) | 0b | X | OFF | FALSE |  |  |
| 7 | TAIL | Normal Network Mode | 0(Received) | 0(Normal) | Within 300ms after receiving 1b | X | No change | No change |  |  |
| 8 | TAIL | Normal Network Mode | 0(Received) | 0(Normal) | 1b continued for 300ms | X | ON | TRUE |  |  |
| 9 | TAIL | Normal Standalone Mode | X | X | X | X | No change | No change | If entered CAN sleep during TAIL TT ON, maintain the TT ON. |  |
| 10 | TAIL | Sleep Mode | X | X | X | X | OFF | FALSE |  |  |
Note:
Never Received and Communication Failurelisted in CAN General SRD.
Please check the CAN General SRD for details.
- Verification Criteria: Verify by executing test cases
- Verification Method: System Qualification Test, Unit Test
- Verification Owner: FV, SW
- System Requirement State: Approved
- Secondary Disciplines: FV, SW
- Primary Discipline: SW
- ASIL Rating: QM

##### TFDCX32348-5530: Seq-CAN Signal TAIL Determination (Sample behavior) (Information)
Sample behavior
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- Verification Criteria: Verify by design review Verify all of conditions in the table (need fault injection)
- Verification Method: TBD
- Verification Owner: FV, SW
- System Requirement State: Approved
- Secondary Disciplines: TBD
- Primary Discipline: SW
- ASIL Rating: QM

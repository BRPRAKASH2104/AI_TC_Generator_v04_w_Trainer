# Json2ReqIF Transformation

# Specification: GAU_AT_Oil_Temp_Gauge
- JDA Snapshot Date: 2025-09-04 02:41:01

## TFDCX32348-59724: GAU_AT_Oil_Temp_Gauge (Heading)

## TFDCX32348-59725: History (Heading)

### TFDCX32348-59731: Version (Information)
| Version | Date | Name | Description of change | Baseline |
| --- | --- | --- | --- | --- |
| 0.1 | 05/Dec/2024 | Syuta Matsuoka | Newly create [SYS-Story] : TFDCX32348-34212: [SYS][12.3FDC][APP][Trip Computer] Display of AT oil temperature (gauge) | BL_20250508_01 |
| 0.2 | 17/July/2025 | Syuta Matsuoka | Px_Ratio_xx should round Use Flash Start for Determining Blinking [SYS-Task] TFDCX32348-97149: [SYS][12.3FDC][IMP][APP][Trip Computer] Display of AT oil temperature (Changed by TFDCX32348-94455) | BL_20250718_01 |

## TFDCX32348-59726: Reference Document (Heading)

### TFDCX32348-59732: External Sources (Heading)

#### TFDCX32348-59733: MET-D_ATTEMP-CSTD-A0-00-A-C1.xlsm (Information)
MET-D_ATTEMP-CSTD-A0-00-A-C1.xlsm
DMS_MET-D_ATTEMP-CSTD-A0-00-A-C1.xls
MET-D_ATTEMP-CSTD-A0-00-A-C1_Appendix.docx

## TFDCX32348-59727: Overview (Heading)

### TFDCX32348-59734: This SRD defines (Information)
This SRD defines Automatic Transmission Oil Temperature indicator.

## TFDCX32348-59728: Input Requirements (Heading)

### TFDCX32348-59736 (System Interface)
CANSignal – B_THOCL (9bit, Message Label: ECT1G92)
9bit data, offset: -40, resolution: 0.625
Range: 0x000h [-40℃] to 0x140h [160℃]
Initial: 0x000h [-40℃], Fail: 0x000h [-40℃]
Below is just a information (In this SRD, not use the actual value)
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
### TFDCX32348-59735: InternalSignal - IgnMode (System Interface)

### TFDCX32348-59861: MCUCONST - MCUID0593 (System Interface)

### TFDCX32348-59862: MCUCONST - MCUID0594 (System Interface)

### TFDCX32348-59863: MCUCONST - MCUID0595 (System Interface)

### TFDCX32348-59864: MCUCONST - MCUID0596 (System Interface)

### TFDCX32348-59865: MCUCONST - MCUID0597 (System Interface)

### TFDCX32348-59866: MCUCONST - MCUID0598 (System Interface)

### TFDCX32348-59867: MCUCONST - MCUID0599 (System Interface)

### TFDCX32348-76347: InternalSignal - TransmissionTypeFlag (System Interface)

### TFDCX32348-76748: MCUCONST - MCUID1122 (System Interface)

## TFDCX32348-59729: Output Requirements (Heading)

### TFDCX32348-59857: HMI - ATTEMP_RATIO_OUT (System Interface)
HMI - ATTEMP_RATIO_OUT
Range:{0, 1, 2, …59, 60}
Note: Increases the drawing area by 3px for every 1 increase in value

### TFDCX32348-60003: HMI - ATTEMP_BLINK_FLAG (System Interface)
HMI - ATTEMP_BLINK_FLAG
Range: {OFF, ON}

### TFDCX32348-59859: HMI - ATTEMP_RED_ZONE (System Interface)
HMI - ATTEMP_RED_ZONE
Range:{0, 1, 2, …59, 60}
Note: Increases the drawing area by 3px for every 1 increase in value

### TFDCX32348-77134: InternalSignal - ATOilTempGauge_Prsnt (System Interface)
InternalSignal - ATOilTempGauge_Prsnt
Range:{NOT_PRSNT, PRSNT}

## TFDCX32348-60728: Local Parameters (Heading)

### TFDCX32348-61833: LocalParameter - B_THOCL_Status (System Interface)
LocalParameter - B_THOCL_Status
Meaning: This local parameter indicates the status of CANSignal - B_THOCL.
Range: 0 [Not Normal], 1 [Normal]

### TFDCX32348-61856: LocalParameter - DATA1_forAve (System Interface)
LocalParameter - DATA1_forAve
Meaning: This local parameter indicates one of the recent 4 input data for moving average of B_THOCL.
Range: 0x000h [-40℃] to 0x140h [160℃]

### TFDCX32348-61858: LocalParameter - DATA2_forAve (System Interface)
LocalParameter - DATA2_forAve
Meaning: This local parameter indicates one of the recent 4 input data for moving average of B_THOCL.
Range: 0x000h [-40℃] to 0x140h [160℃]

### TFDCX32348-61860: LocalParameter - DATA3_forAve (System Interface)
LocalParameter - DATA3_forAve
Meaning: This local parameter indicates one of the recent 4 input data for moving average of B_THOCL.
Range: 0x000h [-40℃] to 0x140h [160℃]

### TFDCX32348-61861: LocalParameter - DATA4_forAve (System Interface)
LocalParameter - DATA4_forAve
Meaning: This local parameter indicates one of the recent 4 input data for moving average of B_THOCL.
Range: 0x000h [-40℃] to 0x140h [160℃]

### TFDCX32348-60729: LocalParameter - AveATTEMP (System Interface)
LocalParameter - AveATTEMP
Meaning: This local parameter indicates the moving average temperature of the latest four values of B_THOCL.
Range: 0 [-40℃] to 200 [160℃]

### TFDCX32348-76023: LocalParameter - Px_Ratio_Hi (System Interface)
LocalParameter - Px_Ratio_Hi
Meaning: Temperature every 3 pixels from half of gauge to maximum

### TFDCX32348-77170: LocalParameter - Px_Ratio_Lo (System Interface)
LocalParameter - Px_Ratio_Lo
Meaning: Temperature every 3 pixels from minimum of gauge to half

### TFDCX32348-61493: LocalParameter - Target_Ratio (System Interface)
LocalParameter - Target_Ratio
Meaning: This local parameter indicates the target ratio of the gauge display.
Range : {0, 1, 2, … 59, 60}

### TFDCX32348-77458: LocalParameter - Blink_Stop_Ratio (System Interface)
LocalParameter - Blink_Stop_Ratio
Meaning: This local parameter indicates the blink ratio of the gauge display.

### TFDCX32348-98577: LocalParameter - Blink_Start_Ratio (System Interface)
LocalParameter - Blink_Start_Ratio
Meaning: This local parameter indicates the blink ratio of the gauge display.

## TFDCX32348-59730: Performance Requirements (Heading)

### TFDCX32348-61546: General (Heading)

#### TFDCX32348-61520: Processing block structure (Heading)

##### TFDCX32348-61521: Figure (System Requirement)
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| # | Signal name |
| --- | --- |
| ① | AveATTEMP |
| ②-1 | Px_Ratio_Lo |
| ②-2 | Px_Ratio_Hi |
| ③ | Target_Ratio |
| ④ | ATTEMP_RATIO_OUT |
- Verification Criteria: Verify by executing test cases
- Verification Method: System Qualification Test, Unit Test
- Verification Owner: FV, SW
- System Requirement State: Approved
- Primary Discipline: SW
- ASIL Rating: QM

#### TFDCX32348-59953: Parameters (Heading)

##### TFDCX32348-59954: Table - Parameters (System Requirement)
| # | Parameter name(Use this SRD) | Value | Remarks |
| --- | --- | --- | --- |
| 1 | 【ATTEMP_LO】 | MCUCONST - MCUID0593 | Bar display lower limit |
| 2 | 【ATTEMP_MIDL】 | MCUCONST - MCUID0594 | Bar display middle stable range lower limit |
| 3 | 【ATTEMP_MIDH】 | MCUCONST - MCUID0595 | Bar display middle stable range upper limit |
| 4 | 【ATTEMP_HI】 | MCUCONST - MCUID0596 | Bar display upper limit |
| 5 | 【Flash_Start】 | MCUCONST - MCUID0597 | Bar display flashing start threshold |
| 6 | 【Flash_Stop】 | MCUCONST - MCUID0598 | Bar display flashing stop threshold |
| 7 | 【Red_Zone_Start】 | MCUCONST - MCUID0599 | Red zone start position |
Note: Above all parameters resolution are 1.
- Verification Criteria: Verify by executing test cases
- Verification Method: System Qualification Test, Unit Test
- Verification Owner: FV, SW
- System Requirement State: Approved
- Primary Discipline: SW
- ASIL Rating: QM

### TFDCX32348-61548: Processing (Heading)

#### TFDCX32348-59873: [A] Initialization (Heading)

##### TFDCX32348-61552: [A-A] Data Initialize (Heading)

###### TFDCX32348-59877: At IGN (System Requirement)
At IGN change From OFF to ON, initialize below;
HMI - ATTEMP_RATIO_OUT = 0 [0.00%]
HMI - ATTEMP_BLINK_FLAG = OFF
HMI - ATTEMP_RED_ZONE = 60 [100.00%]
LocalParameter - B_THOCL_Status = 0 [Not Normal]
LocalParameter - DATA1_forAve = 0x000h [-40℃]
LocalParameter - DATA2_forAve = 0x000h [-40℃]
LocalParameter - DATA3_forAve = 0x000h [-40℃]
LocalParameter - DATA4_forAve = 0x000h [-40℃]
LocalParameter - AveATTEMP = 0 [-40℃]
LocalParameter - Target_Ratio = 0 [0.00%]
LocalParameter - Blink_Ratio = 60 [100.00%]
- Verification Criteria: Verify by executing test cases
- Verification Method: System Qualification Test, Unit Test
- Verification Owner: FV, SW
- System Requirement State: Approved
- Primary Discipline: SW
- ASIL Rating: QM

##### TFDCX32348-76236: [A-B]Function presence/absence judgment (Heading)

###### TFDCX32348-76346: # (System Requirement)
| # | Input |  | Output |
| --- | --- | --- | --- |
| # | MCUID1122 | TransmissionTypeFlag | ATOilTempGauge_Prsnt |
| 1 | Initilization at Battery Connect |  | NOT_PRSNT |
| 2 | 1[Exist] | 0001b or 0010b or 0101b | PRSNT |
| 3 | Other than above |  | NOT_PRSNT |
- Verification Criteria: Verify by executing test cases
- Verification Method: System Qualification Test, Unit Test
- Verification Owner: FV, SW
- System Requirement State: Approved
- Primary Discipline: SW
- ASIL Rating: QM

#### TFDCX32348-59874: [B] Normal Operation (Heading)

##### TFDCX32348-77139 (System Requirement)
Each block of the main operation shall be executed when all of the following conditions are met.
ATOilTempGauge_Prsnt == 1[PRSNT]
IgnMode == ON
- Verification Criteria: Verify by executing test cases
- Verification Method: System Qualification Test, Unit Test
- Verification Owner: FV, SW
- System Requirement State: Approved
- Primary Discipline: SW
- ASIL Rating: QM

##### TFDCX32348-61554: [B-A] Sampling and averaging (Heading)

###### TFDCX32348-59880: Sampling B_THOCL (Heading)

###### TFDCX32348-61555: Sampling : every 1000ms while IgnMode=ON (System Requirement)
| # | Input |  |  |  |  |  |  | Output |  |  |  |  |
| --- | --- | --- | --- | --- | --- | --- | --- | --- | --- | --- | --- | --- |
| # | InternalSignal – IgnMode | CAN Signal Communication Status - B_THOCL | CANSignal - B_THOCL | LocalParameter - B_THOCL _Status(Previous) | LocalParameter - DATA2_forAve(Previous) | LocalParameter - DATA3_forAve(Previous) | LocalParameter - DATA4_forAve(Previous) | LocalParameter - B_THOCL _Status | LocalParameter - DATA1_forAve | LocalParameter - DATA2_forAve | LocalParameter - DATA3_forAve | LocalParameter - DATA4_forAve |
| 1 | OFF | x | x | x | x | x | x | 1[Not Normal] | 0x000h | 0x000h | 0x000h | 0x000h |
| 2 | ON | Communication starting Never Received: 1 Communication Failure: 0 | x | x | x | x | x | 1[Not Normal] | 0x000h | 0x000h | 0x000h | 0x000h |
| 3 | ON | Communication abnormality Never Received: x Communication Failure: 1 | x | x | x | x | x | 1[Not Normal] | 0x000h | 0x000h | 0x000h | 0x000h |
| 4 | ON | Communication establishment Never Received: 0 Communication Failure: 0 | 0x140h [160℃] < B_THOCL | x | x | x | x | No change | No change | No change | No change | No change |
| 5 | ON | Communication establishment Never Received: 0 Communication Failure: 0 | B_THOCL <= 0x140h [160℃] | 1[Not Normal] | x | x | x | 0[Normal] | B_THOCL | B_THOCL | B_THOCL | B_THOCL |
| 6 | ON | Communication establishment Never Received: 0 Communication Failure: 0 | B_THOCL <= 0x140h [160℃] | 0[Normal] | Any value | Any value | Any value | 0[Normal] | DATA2_forAve(Previous) | DATA3_forAve(Previous) | DATA4_forAve(Previous) | B_THOCL |
- Verification Criteria: Verify by executing test cases
- Verification Method: System Qualification Test, Unit Test
- Verification Owner: FV, SW
- System Requirement State: Approved
- Primary Discipline: SW
- ASIL Rating: QM

###### TFDCX32348-59891: Moving Average of resent 4 input data - AveATTEMP (Heading)

###### TFDCX32348-61557: Calculate moving average of 4 input data (System Requirement)
| # | Input |  |  |  |  | Output |
| --- | --- | --- | --- | --- | --- | --- |
| # | InternalSignal – IgnMode | LocalParameter - DATA1_forAve | LocalParameter - DATA2_forAve | LocalParameter - DATA3_forAve | LocalParameter - DATA4_forAve | LocalParameter - AveATTEMP (*1) |
| 1 | OFF | x | x | x | x | 0[-40℃] |
| 2 | ON | Any Value | Any Value | Any Value | Any Value | Round((Ave(DATA1_forAve, DATA2_forAve, DATA3_forAve, DATA4_forAve))*0.625), 0) |
(*1) Ave(DATA1_forAve, DATA2_forAve, DATA3_forAve, DATA4_forAve) resolution is 0.625 and AveATTEMP resolution is 1.
Ave(DATA1_forAve, DATA2_forAve, DATA3_forAve, DATA4_forAve) = 320[160℃] → 320*0.625=200 → AveATTEMP = 200[160℃]
- Verification Criteria: Verify by executing test cases
- Verification Method: System Qualification Test, Unit Test
- Verification Owner: FV, SW
- System Requirement State: Approved
- Primary Discipline: SW
- ASIL Rating: QM

###### TFDCX32348-59895: Example (Information)
Example of Temp input procedure to understand the calculation
| Data check timing | CAN Signal Communication Status - B_THOCL | B_THOCL | LocalParameter - AveATTEMP |
| --- | --- | --- | --- |
| x | Communication starting Never Received: 1 Communication Failure: 0 | x | 0 (Initial value) |
| data_1 | Communication establishment Never Received: 0 Communication Failure: 0 | 0x140h < B_THOCL | (No update) |
| data_2 | Communication establishment Never Received: 0 Communication Failure: 0 | 0x140h < B_THOCL | (No update) |
| data_3 | Communication establishment Never Received: 0 Communication Failure: 0 | B_THOCL <= 0x140h | Round((Ave((data_3)*4)*0.625), 0) |
| data_4 | Communication establishment Never Received: 0 Communication Failure: 0 | B_THOCL <= 0x140h | Round((Ave((data_3)*3, data_4)*0.625), 0) |
| data_5 | Communication establishment Never Received: 0 Communication Failure: 0 | B_THOCL <= 0x140h | Round((Ave((data_3)*2, data_4, data_5)*0.625), 0) |
| data_6 | Communication establishment Never Received: 0 Communication Failure: 0 | B_THOCL <= 0x140h | Round((Ave(data_3, data_4, data_5, data_6)*0.625), 0) |
| data_7 | Communication establishment Never Received: 0 Communication Failure: 0 | B_THOCL <= 0x140h | Round((Ave(data_4, data_5, data_6, data_7)*0.625), 0) |
| data_8 | Communication establishment Never Received: 0 Communication Failure: 0 | B_THOCL <= 0x140h | Round((Ave(data_5, data_6, data_7, data_8)*0.625), 0) |
| data_4 | Communication establishment Never Received: 0 Communication Failure: 0 | 0x140h < B_THOCL | (No update) |
| data_10 | Communication establishment Never Received: 0 Communication Failure: 0 | 0x140h < B_THOCL | (No update) |
| data_11 | Communication establishment Never Received: 0 Communication Failure: 0 | B_THOCL <= 0x140h | Round((Ave(data_6, data_7, data_8, data_11)*0.625), 0) |
| data_12 | Communication establishment Never Received: 0 Communication Failure: 0 | B_THOCL <= 0x140h | Round((Ave(data_7, data_8, data_11, data_12)*0.625), 0) |
| data_13 | Communication establishment Never Received: 0 Communication Failure: 0 | B_THOCL <= 0x140h | Round((Ave(data_8, data_11, data_12, data_13)*0.625), 0) |
| data_14 | Communication establishment Never Received: 0 Communication Failure: 0 | B_THOCL <= 0x140h | Round((Ave(data_11, data_12, data_13, data_14)*0.625), 0) |
| data_15 | Communication establishment Never Received: 0 Communication Failure: 0 | B_THOCL <= 0x140h | Round((Ave(data_12, data_13, data_14 data_15)*0.625), 0) |
| ～ |  |  |  |
| data_46 | Communication establishment Never Received: 0 Communication Failure: 0 | B_THOCL <= 0x140h | Round((Ave(data_43, data_44, data_45, data_46)*0.625), 0) |
| data_47 | Communication abnormality Never Received: x Communication Failure: 1 | x | 0 |
| data_48 | Communication establishment Never Received: 0 Communication Failure: 0 | 0x140h < B_THOCL | (No update) |
| data_44 | Communication establishment Never Received: 0 Communication Failure: 0 | 0x140h < B_THOCL | (No update) |
| data_50 | Communication establishment Never Received: 0 Communication Failure: 0 | B_THOCL <= 0x140h | Round((Ave((data_50)*4)*0.625), 0) |
| data_51 | Communication establishment Never Received: 0 Communication Failure: 0 | B_THOCL <= 0x140h | Round((Ave((data_50)*3, data_51)*0.625), 0) |
| data_52 | Communication establishment Never Received: 0 Communication Failure: 0 | B_THOCL <= 0x140h | Round((Ave((data_50)*2, data_51, data_52)*0.625), 0) |
| data_53 | Communication establishment Never Received: 0 Communication Failure: 0 | B_THOCL <= 0x140h | Round((Ave(data_51, data_52, data_53, data_54)*0.625), 0) |
| ～ |  |  |  |
| data_96 | Communication establishment Never Received: 0 Communication Failure: 0 | B_THOCL <= 0x140h | Round((Ave(data_93, data_94, data_95, data_96)*0.625), 0) |
| data_97 | Communication establishment Never Received: 0 Communication Failure: 0 | B_THOCL <= 0x140h | Round((Ave(data_94, data_95, data_96, data_97)*0.625), 0) |
| data_98 | Communication establishment Never Received: 0 Communication Failure: 0 | B_THOCL <= 0x140h | Round((Ave(data_95, data_96, data_97, data_98)*0.625), 0) |
| data_99 | Communication abnormality Never Received: x Communication Failure: 1 | x | 0 |
| data_100 | Communication establishment Never Received: 0 Communication Failure: 0 | B_THOCL <= 0x140h | Round((Ave((data_100)*4)*0.625), 0) |
| data_101 | Communication establishment Never Received: 0 Communication Failure: 0 | B_THOCL <= 0x140h | Round((Ave((data_100)*3, data_101)*0.625), 0) |
| data_102 | Communication establishment Never Received: 0 Communication Failure: 0 | B_THOCL <= 0x140h | Round((Ave((data_100)*2, data_101, data_102)*0.625), 0) |
| data_103 | Communication establishment Never Received: 0 Communication Failure: 0 | B_THOCL <= 0x140h | Round((Ave(data_101, data_102, data_103, data_104)*0.625), 0) |

##### TFDCX32348-76214: [B-B]Get Temperture value per 3px (Heading)

###### TFDCX32348-76219 (System Requirement)
At IGN change From OFF to ON, set below 2 data;
Px_Ratio_Lo = Round{(ATTEMP_MIDL - ATTEMP_LO)/30, 2}
Px_Ratio_Hi = Round{(ATTEMP_HI - ATTEMP_MIDL )/30, 2}
- Verification Criteria: Verify by executing test cases
- Verification Method: System Qualification Test, Unit Test
- Verification Owner: FV, SW
- System Requirement State: Approved
- Primary Discipline: SW
- ASIL Rating: QM

##### TFDCX32348-60894: [B-C] Get Target_Ratio (Heading)

###### TFDCX32348-60009: Table - Target Ratio (System Requirement)
| # | Input | Output |
| --- | --- | --- |
| # | AveATTEMP | Target_Ratio |
| 1 | AveATTEMP <= ATTEMP_LO | 0 [0.00%] |
| 2 | ATTEMP_LO < AveATTEMP < ATTEMP_MIDL | Round((AveATTEMP-ATTEMP_LO)/Px_Ratio_Lo) |
| 3 | ATTEMP_MIDL <= AveATTEMP <= ATTEMP_MIDH | 30 [50.00%] |
| 4 | ATTEMP_MIDH < AveATTEMP < ATTEMP_HI | Round((AveATTEMP-ATTEMP_MIDH)/Px_Ratio_HI))+30 |
| 5 | ATTEMP_HI = AveATTEMP | 60 [100.00%] |
| 6 | ATTEMP_HI < AveATTEMP | 0 [0.00%] |
- Verification Criteria: Verify by executing test cases
- Verification Method: System Qualification Test, Unit Test
- Verification Owner: FV, SW
- System Requirement State: Approved
- Primary Discipline: SW
- ASIL Rating: QM

##### TFDCX32348-60891: [B-D] Update Display Output (Heading)

###### TFDCX32348-60892: Update Display by below table (System Requirement)
Update Display by below table
| # | Input Condition |  |  | Output |
| --- | --- | --- | --- | --- |
| # | InternalSignal - IgnMode | LocalParameter - B_THOCL_Status(*1) | Other Condition(Compare Target_Ratio and ATTEMP_RATIO_OUT) | HMI - ATTEMP_RATIO_OUT(*2) |
| 1 | (Initialization at CPU Reset or wakeup) |  |  | 0 |
| 2 | OFF | x | x | 0 |
| 3 | ON | 0[Not Normal] | x | Target_Ratio |
| 4 | ON | 0[Not Normal] → 1[Normal] | x | Target_Ratio |
| 5 | ON | 1[Normal] → 1[Normal] | Target_Ratio < ATTEMP_RATIO_OUT | Decrement by 1 |
| 6 | ON | 1[Normal] → 1[Normal] | ATTEMP_RATIO_OUT < Target_Ratio | Increment by 1 |
| 7 | ON | 1[Normal] → 1[Normal] | Target_Ratio == ATTEMP_RATIO_OUT | No change |
Note:
(*1) xx → yy does not represent on edge, but a comparison between one previous status (xx) and the current status (yy).
(*2)Update the ATTEMP_RATIO_OUT value every 500 ms until Dispray_Ratio is equal to Target_Ratio.
- Verification Criteria: Verify by executing test cases
- Verification Method: System Qualification Test, Unit Test
- Verification Owner: FV, SW
- System Requirement State: Approved
- Primary Discipline: SW
- ASIL Rating: QM

##### TFDCX32348-60004: [B-E] Determining Blinking (Heading)

###### TFDCX32348-59942: Table - Blinking Logic (System Requirement)
| # | Input | Output |
| --- | --- | --- |
| # | Flash_Start | LocalParameter - Blink_Strat_Ratio |
| 1 | Flash_Start <= ATTEMP_LO | 0 [0.00%] |
| 2 | ATTEMP_LO < Flash_Start < ATTEMP_MIDL | Round((Flash_Start-ATTEMP_LO)/Px_Ratio_Lo) |
| 3 | ATTEMP_MIDL <= Flash_Start <= ATTEMP_MIDH | 30 [50.00%] |
| 4 | ATTEMP_MIDH < Flash_Start < ATTEMP_HI | Round((Flash_Start-ATTEMP_MIDH)/Px_Ratio_HI))+30 |
| 5 | ATTEMP_HI <= Flash_Start | 60 [100.00%] |
| # | Input | Output |
| --- | --- | --- |
| # | Flash_Stop | LocalParameter -Blink_Stop_Ratio |
| 1 | Flash_Stop <= ATTEMP_LO | 0 [0.00%] |
| 2 | ATTEMP_LO < Flash_Stop < ATTEMP_MIDL | Round((Flash_Stop-ATTEMP_LO)/Px_Ratio_Lo) |
| 3 | ATTEMP_MIDL <= Flash_Stop <= ATTEMP_MIDH | 30 [50.00%] |
| 4 | ATTEMP_MIDH < Flash_Stop < ATTEMP_HI | Round((Flash_Stop-ATTEMP_MIDH)/Px_Ratio_HI))+30 |
| 5 | ATTEMP_HI <= Flash_Stop | 60 [100.00%] |
| # | Input |  |  | Output |
| --- | --- | --- | --- | --- |
| # | HMI - ATTEMP_BLINK_FLAG (Previous) | ATTEMP_RATIO_OUT and Blink_Strat_Ratio | ATTEMP_RATIO_OUT and Blink_Stop_Ratio | HMI - ATTEMP_BLINK_FLAG |
| 1 | OFF | ATTEMP_RATIO_OUT < Blink_Start_Ratio | x | No change OFF |
| 2 | OFF | Blink_Start_Ratio <= ATTEMP_RATIO_OUT | x | ON |
| 3 | ON | x | ATTEMP_RATIO_OUT <= Blink_Stop_Ratio | OFF |
| 4 | ON | x | ATTEMP_RATIO_OUT = Blink_Ratio | No change |
| 5 | ON | x | Blink_Stop_Ratio < ATTEMP_RATIO_OUT | No change ON |
- Verification Criteria: Verify by executing test cases
- Verification Method: System Qualification Test, Unit Test
- Verification Owner: FV, SW
- System Requirement State: Approved
- Primary Discipline: SW
- ASIL Rating: QM

###### TFDCX32348-59943: Blinking Control(move to GUISRD) (System Requirement)
Blinking Control(move to GUISRD)
Move to TFDCX32348-98444
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- Verification Criteria: Verify by executing test cases
- Verification Method: System Qualification Test, Unit Test
- Verification Owner: FV, SW
- System Requirement State: Rejected
- Primary Discipline: SW
- ASIL Rating: QM

##### TFDCX32348-59944: [B-F] Determining Red Zone (Heading)

###### TFDCX32348-59945: Red Zone Logic (System Requirement)
| # | Input | Output |
| --- | --- | --- |
| # | RED_ZONE_Start | ATTEMP_RED_ZONE |
| 1 | RED_ZONE_Start <= ATTEMP_LO | 0 [0.00%] |
| 2 | ATTEMP_LO < RED_ZONE_Start < ATTEMP_MIDL | Round((RED_ZONE_Start-ATTEMP_LO)/Px_Ratio_Lo) |
| 3 | ATTEMP_MIDL <= RED_ZONE_Start <= ATTEMP_MIDH | 30 [50.00%] |
| 4 | ATTEMP_MIDH < RED_ZONE_Start < ATTEMP_HI | Round((RED_ZONE_Start-ATTEMP_MIDH)/Px_Ratio_HI))+30 |
| 5 | ATTEMP_HI <= RED_ZONE_Start | 60 [100.00%] |
- Verification Criteria: Verify by executing test cases
- Verification Method: System Qualification Test, Unit Test
- Verification Owner: FV, SW
- System Requirement State: Approved
- Primary Discipline: SW
- ASIL Rating: QM

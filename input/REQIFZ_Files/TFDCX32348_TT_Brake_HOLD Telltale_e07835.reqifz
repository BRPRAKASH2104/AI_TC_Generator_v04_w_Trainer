# Json2ReqIF Transformation

# Specification: TT_Brake_HOLD Telltale
- JDA Snapshot Date: 2025-10-29 07:15:27

## TFDCX32348-1014: TT_Brake_HOLD Telltale (Heading)

## TFDCX32348-1016: History (Heading)

### TFDCX32348-2461: Version Date Name Description of chan... (Information)
| Version | Date | Name | Description of change | Baseline |
| --- | --- | --- | --- | --- |
| 0.1 | Jun/19/2024 | Kazuya Nagata | Newly create (Based on 38XD) TFDCX32348-23777 [SYS][12.3FDC][APP][Telltale] Brake Hold (after 21 PF) Change point: 1. TFDCX32348-1660 /TFDCX32348-1671/TFDCX32348-1672/TFDCX32348-1678/TFDCX32348-1680/TFDCX32348-1682/TFDCX32348-1695/TFDCX32348-1697: Removed Brake HOLD Telltale Brightness adjustment | BL_20240627_01 |

## TFDCX32348-1018: Reference Document (Heading)

### TFDCX32348-2463: MET-C_BRKHLD-CSTD-1-03-A-C0.xlsm (Information)

### TFDCX32348-2465: DMS_MET-C_BRKHLD-CSTD-1-03-A-C0.xlsx (Information)

## TFDCX32348-1020: Overview (Heading)

### TFDCX32348-1655: This SRD defines Telltale of Brake HOLD. (Information)

## TFDCX32348-1022: Input Requirements (Heading)

### TFDCX32348-1658: InternalSignal - IgnMode (System Interface)
- Verification Criteria: Verify by design review
- System Requirement State: Approved

### TFDCX32348-1660: InternalSignal - IlumDayNightStatus ... (System Interface)
InternalSignal - IlumDayNightStatus
Meaning: This parameter indicates the illumination luminance status.
Range: $0 (UNKNOWN), $1 (DAY), $2 (NIGHT)
- System Requirement State: Rejected

### TFDCX32348-1662: CANSignal – B_DAINDP (Message Label: ... (System Interface)
CANSignal – B_DAINDP (Message Label: VSC1S95)
- Verification Criteria: Verify by design review
- System Requirement State: Approved

### TFDCX32348-1664: CANSignal – BHEXIST (Message Label: V... (System Interface)
CANSignal – BHEXIST (Message Label: VSC1S95)
- Verification Criteria: Verify by design review
- System Requirement State: Approved

### TFDCX32348-1667: NVM - NVM_BHEXIST_Flag (System Interface)
- Verification Criteria: Verify by design review
- System Requirement State: Approved

### TFDCX32348-1671: InternalSignal - LVSD2 (System Interface)
- Verification Criteria: Verify by code review
- System Requirement State: Rejected

### TFDCX32348-1672: InternalSignal - HVSD2 (System Interface)
- Verification Criteria: Verify by code review
- System Requirement State: Rejected

## TFDCX32348-1024: Output Requirements (Heading)

### TFDCX32348-1674: TT – Brake_HOLD_Telltale Meaning: T... (System Interface)
TT – Brake_HOLD_Telltale
Meaning: This parameter indicates the display state of Brake HOLD Telltale.
Range: OFF, ON, Blinking
Initial Value: OFF
- Verification Criteria: Verify by design review
- System Requirement State: Approved

### TFDCX32348-1675: NVM – NVM_BHEXIST_Flag Meaning: Thi... (System Interface)
NVM – NVM_BHEXIST_Flag
Meaning: This NVM parameter indicates that the Brake Hold system is either equipped or unequipped.
Range: Unequipped, Equipped
Initial Value: Unequipped
- Verification Criteria: Verify by design review
- System Requirement State: Approved

### TFDCX32348-1678: HW - PWM - HOLD_TT_MCUOUT Meaning: ... (System Interface)
HW - PWM - HOLD_TT_MCUOUT
Meaning: This output is used to adjust the brightness of the Brake HOLD telltale.
Setting PWM Frequency: 200H
- Verification Criteria: Verify by design review
- System Requirement State: Rejected

## TFDCX32348-1026: NVM Requirements (Heading)

### TFDCX32348-1680: NVM - NVM_AmberDayDuty (Read Only) (System Interface)
- Verification Criteria: Verify by code review
- System Requirement State: Rejected

### TFDCX32348-1682: NVM - NVM_AmberNightDuty (Read Only) (System Interface)
- Verification Criteria: Verify by code review
- System Requirement State: Rejected

## TFDCX32348-70743: Function Entry (Heading)
- System Requirement State: Draft
- Primary Discipline: TBD
- ASIL Rating: TBD

### TFDCX32348-70744: Function Entry - fn_reset_BrakeHold_existance() (System Interface)
- System Requirement State: Draft
- Primary Discipline: TBD
- ASIL Rating: TBD

## TFDCX32348-1028: Performance Requirements (Heading)

### TFDCX32348-1684: Display Symbol (Heading)

#### TFDCX32348-3063: Display Symbol: Display Color: Amber... (Information)
1. Display Symbol:
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2. Display Color: Amber
3. Destination: All [ North America (CONV)_USA, North America (HEV)_USA, North America (CONV)_CANADA, Middle East (CONV), General (CONV), Australia (HEV), Middle East (HEV), General (HEV) ]

### TFDCX32348-1686: Bulb Check (Heading)

#### TFDCX32348-3065: None (System Requirement)
- ASIL Rating: ASIL B

### TFDCX32348-1688: Initial Process (Heading)

#### TFDCX32348-3067: When the ON of the internal signal Ig... (System Requirement)
When the ON of the internal signal IgnMode is detected, the telltale is turn off until a lighting signal is received.
- Verification Criteria: Verify by executing test cases
- Verification Method: System Qualification Test, Unit Test
- Verification Owner: FV, SW
- System Requirement State: Approved
- Primary Discipline: SW
- ASIL Rating: ASIL B

### TFDCX32348-1691: Telltale Control (Heading)

#### TFDCX32348-3069: CAN Signal B_DAINDP Judgment (Heading)

##### TFDCX32348-5439: No. Input Output System Status Int... (System Requirement)
| No. | Input |  |  |  | Output |
| --- | --- | --- | --- | --- | --- |
| No. | NVM - NVM_BHEXIST_Flag | InternalSignal - IgnMode | CAN Signal Communication Status – B_DAINDP | Receive CAN Signal B_DAINDP | TT – Brake_HOLD_Telltale |
| 1 | Equipped | OFF | - | - | OFF |
| 2 | Equipped | ON | Communication starting Never Received: 1 Communication Failure: 0 | x | OFF |
| 3 | Equipped | ON | Communication establishment Never Received: 0 Communication Failure: 0 | 00b | OFF |
| 4 | Equipped | ON | Communication establishment Never Received: 0 Communication Failure: 0 | 10b | ON |
| 5 | Equipped | ON | Communication establishment Never Received: 0 Communication Failure: 0 | 11b | Blinking (TFDCX32348-5445)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 |
| 6 | Equipped | ON | Communication establishment Never Received: 0 Communication Failure: 0 | 01b | OFF |
| 7 | Equipped | ON | Communication abnormality Never Received: x Communication Failure: 1 | x | Blinking |
| 8 | Unequipped | - | - | - | OFF |
Note:
Never Received and Communication Failure listed in CAN General SRD.
Please check the CAN General SRD for details.
- Verification Criteria: Verify by executing test cases
- Verification Method: System Qualification Test, Unit Test
- Verification Owner: FV, SW
- System Requirement State: Approved
- Primary Discipline: SW
- ASIL Rating: ASIL B

#### TFDCX32348-3071: Blinking Control (Heading)

##### TFDCX32348-5441: ON Duty Ratio (Heading)

###### TFDCX32348-6939: ON duty ratio is 50%. (System Requirement)
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ON duty ratio is 50%.
- Verification Criteria: Verify by executing test cases
- Verification Method: Software Qualification Test, System Qualification Test, Unit Test
- Verification Owner: FV, SW
- System Requirement State: Approved
- Primary Discipline: SW
- ASIL Rating: ASIL B

##### TFDCX32348-5443: Blinking Pattern (Heading)

###### TFDCX32348-5445 (System Requirement)
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- Verification Criteria: Verify by executing test cases
- Verification Method: System Qualification Test, Unit Test
- Verification Owner: FV, SW
- System Requirement State: Approved
- Primary Discipline: SW
- ASIL Rating: ASIL B

### TFDCX32348-1693: Equipment Determination (Heading)

#### TFDCX32348-3074: No (System Requirement)
| No. | Input |  |  | Output |
| --- | --- | --- | --- | --- |
| No. | InternalSignal – IgnMode | NVM – NVM_BHEXIST_Flag | CAN Signal BHEXIST | NVM – NVM_BHEXIST_Flag |
| 1 | OFF | x | x | No Change |
| 2 | ON | 0 [Unequipped] | Received 2 consecutive signals 1b within 700ms | 1 [Equipped] |
| 3 | ON | 1 [Equipped] | Received 2 consecutive signals other than 1b within 700ms | 0 [Unequipped] |
| 4 | ON | Other than above |  | No Change |
| Function Entry | NVM – NVM_BHEXIST_Flag |
| --- | --- |
| fn_reset_BrakeHold_existance() | 0 [Unequipped] |
Timing Chart
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- Verification Criteria: Verify by executing test cases
- Verification Method: System Qualification Test, Unit Test
- Verification Owner: FV, SW
- System Requirement State: Approved
- Primary Discipline: SW
- ASIL Rating: ASIL B

### TFDCX32348-1695: Brake HOLD Telltale Brightness adjust... (Heading)
Brake HOLD Telltale Brightness adjustment

#### TFDCX32348-1697: Adjust brightness with H/W PWM – HOLD... (System Requirement)
Adjust brightness with H/W PWM – HOLD_TT_MCUOUT when Brake HOLD telltale is ON/OFF.
| No. | Input |  |  | Output |
| --- | --- | --- | --- | --- |
| No. | InternalSignal -LVSD2/HVSD2 | TT – Brake_HOLD_Telltale | InternalSignal - IlumDayNightStatus | H/W PWM – HOLD_TT_MCUOUT |
| No. | InternalSignal -LVSD2/HVSD2 | TT – Brake_HOLD_Telltale | InternalSignal - IlumDayNightStatus | Output Duty |
| 1 | X | OFF | ｘ | 0% |
| 2 | LVSD2 == NOT_OK or HVSD2 == NOT_OK | X | X | 0% |
| 3 | LVSD2 == OK and HVSD2 == OK | ON | UNKNOWN | NVM_AmberDayDuty |
| 4 | LVSD2 == OK and HVSD2 == OK | ON | DAY | NVM_AmberDayDuty |
| 5 | LVSD2 == OK and HVSD2 == OK | ON | NIGHT | NVM_AmberNightDuty |
Note: PWM Frequency is 200Hz.
- Verification Criteria: Verify by executing test cases
- Verification Method: System Qualification Test, Unit Test
- Verification Owner: FV, SW
- System Requirement State: Rejected
- Primary Discipline: SW
- ASIL Rating: ASIL B

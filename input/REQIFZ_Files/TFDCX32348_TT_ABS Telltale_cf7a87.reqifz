# Json2ReqIF Transformation

# Specification: TT_ABS Telltale
- JDA Snapshot Date: 2025-10-29 07:14:39

## TFDCX32348-909: TT_ABS Telltale (Heading)

## TFDCX32348-911: History (Heading)

### TFDCX32348-1309: Version Date Name Description of chan... (Information)
| Version | Date | Name | Description of change | Baseline |
| --- | --- | --- | --- | --- |
| 0.1 | Jun/21/2024 | Kazuya Nagata | Newly create (Based on 38XD) TFDCX32348-23726 [SYS][12.3FDC][APP][Telltale] ABS Warning Change point: 1. TFDCX32348-1321/TFDCX32348-3009/TFDCX32348-3011: Removed AppMode 2. TFDCX32348-1323/TFDCX32348-3009: Removed All_Telltale_ON test | BL_20240627_01 |
| 0.2 | Oct/30/2024 | Takuya Tamura | TFDCX32348-54350: [SYS][12.3FDC][APP][Telltale] Change telltale icons by country code Added InternalSignal - TT_DESTVali and determination | BL_20241106_01 |
| 0.3 | Aug/20/2025 | Syuta Matsuoka | Change in symbol determination method [SYS-Task] TFDCX32348-89338: [SYS][12.3FDC][R6.1][D3576][APP][Telltale] Destination variation list (Telltale) | BL_20250828_01 |

## TFDCX32348-913: Reference Document (Heading)

### TFDCX32348-1312: MET-C_ABS-CSTD-0-01-A-C0.xlsm (Information)

### TFDCX32348-1315: DMS_MET-C_ABS-CSTD-0-01-A-C0.xlsx (Information)

### TFDCX32348-28184: MET-M_DESTVARI-CSTD-A0-11-A-C0.xlsx (Information)

## TFDCX32348-914: Overview (Heading)

### TFDCX32348-1317: This SRD defines Telltale of ABS. (Information)

## TFDCX32348-915: Input Requirements (Heading)

### TFDCX32348-1319: InternalSignal - IgnMode (System Interface)

### TFDCX32348-1325: CANSignal - B_ABS (Message Label: VSC1S95) (System Interface)

### TFDCX32348-54230: InternalSignal - TT_DESTVali (System Interface)

### TFDCX32348-105552: InternalSignal - DESTID0027 (System Interface)

## TFDCX32348-917: Output Requirements (Heading)

### TFDCX32348-1327: TT - ABSTelltale (System Interface)
Range: {OFF, Txt, Txt_Blinking1, Txt_Blinking2, Img, Img_Blinking1, Img_Blinking2}

## TFDCX32348-919: Performance Requirements (Heading)

### TFDCX32348-1328: Display Symbol (Heading)

#### TFDCX32348-3096: Display Symbol1 : (Heading)

##### TFDCX32348-3003: Display Symbol: ABS Display Color: A... (Information)
1. Display Symbol: ABS
2. Display Color: Amber
3. Destination: FMVSS Applicable [North America(CONV)_USA, North America(HEV)_USA]

#### TFDCX32348-3005: Display Symbol2: (Heading)

##### TFDCX32348-3007: Display Symbol: Display Color: Amber... (Information)
1. Display Symbol:
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2. Display Color: Amber
3. Destination: Other than FMVSS [North America(CONV)_CANADA, Middle East(CONV), General(CONV), Australia(HEV), Middle East(HEV), General(HEV)]

### TFDCX32348-1330: Bulb Check (Heading)

#### TFDCX32348-1332: None (System Requirement)
- ASIL Rating: ASIL B

### TFDCX32348-1334: Table - ABS (Heading)

#### TFDCX32348-3009: No. Input Output Description Internal... (System Requirement)
| No. | Input |  |  | Output | Description |  |
| --- | --- | --- | --- | --- | --- | --- |
| No. | InternalSignal - Ign_Mode | CAN Signal Communication Status – B_ABS | CANSignal - B_ABS Value | InternalSignal - ABSTelltale_jdg | Blinking Cycle | ABS System Status |
| 1 | OFF | x | x | OFF | - | - |
| 2 | ON | Communication starting Never Received: 1 Communication Failure: 0 | x | OFF | - | - |
| 3 | ON | Communication establishment Never Received: 0 Communication Failure: 0 | 000b | OFF | - | Normal |
| 4 | ON | Communication establishment Never Received: 0 Communication Failure: 0 | 001b | OFF | - | Normal |
| 5 | ON | Communication establishment Never Received: 0 Communication Failure: 0 | 010b | Blinking1 | 250ms | Test Mode |
| 6 | ON | Communication establishment Never Received: 0 Communication Failure: 0 | 011b | ON | - | ABS control is unavailable |
| 7 | ON | Communication establishment Never Received: 0 Communication Failure: 0 | 100b | Blinking2 | 1000ms | Test Mode (Learning) |
| 8 | ON | Communication establishment Never Received: 0 Communication Failure: 0 | 111b | ON | - | ABS system failure |
| 9 | ON | Communication establishment Never Received: 0 Communication Failure: 0 | Other than above | OFF |  | ABS system failure |
| 10 | ON | Communication abnormality Never Received: x Communication Failure: 1 | x | ON | - | ABS system failure |
Note:
Never Received and Communication Failurelisted in CAN General SRD.
Please check the CAN General SRD for details.
| # | Input |  |  | Output |
| --- | --- | --- | --- | --- |
| # | InternalSignal - ABSTelltale_jdg | InternalSignal - DESTID0027 | InternalSignal - TT_DESTVali | TT - ABSTelltale |
| 1 | ON | 1 | x | Txt |
| 2 | ON | 0 | x | Img |
| 3 | ON | Other than above | 0[FMVSS] | Txt |
| 4 | ON | Other than above | 1[Other than FMVSS] | Img |
| 5 | Blinking1 | 1 | x | Txt_Blinking1 |
| 6 | Blinking1 | 0 | x | Img_Blinking1 |
| 7 | Blinking1 | Other than above | 0[FMVSS] | Txt_Blinking1 |
| 8 | Blinking1 | Other than above | 1[Other than FMVSS] | Img_Blinking1 |
| 9 | Blinking2 | 1 | x | Txt_Blinking2 |
| 10 | Blinking2 | 0 | x | Img_Blinking2 |
| 11 | Blinking2 | Other than above | 0[FMVSS] | Txt_Blinking2 |
| 12 | Blinking2 | Other than above | 1[Other than FMVSS] | Img_Blinking2 |
| 13 | OFF |  | x | OFF |
- Verification Criteria: Verify by executing test cases
- Verification Method: System Qualification Test, Unit Test
- Verification Owner: FV, SW
- System Requirement State: Approved
- Primary Discipline: SW
- ASIL Rating: ASIL B

### TFDCX32348-1336: Lighting and blinking control (Heading)

#### TFDCX32348-3013: Blinking control (Heading)

##### TFDCX32348-3015: Note: Tun off the Telltale immediatel... (System Requirement)
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Note:
Tun off the Telltale immediately when the telltale off or blinking end conditions are met.
- Verification Criteria: Verify by executing test cases
- Verification Method: System Qualification Test, Unit Test
- Verification Owner: FV, SW
- System Requirement State: Approved
- Primary Discipline: SW
- ASIL Rating: ASIL B

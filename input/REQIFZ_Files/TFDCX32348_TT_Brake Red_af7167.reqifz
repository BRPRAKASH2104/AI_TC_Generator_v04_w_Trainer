# Json2ReqIF Transformation

# Specification: TT_Brake Red
- JDA Snapshot Date: 2025-10-29 07:15:21

## TFDCX32348-1002: TT_Brake Red (Heading)

## TFDCX32348-1004: History (Heading)

### TFDCX32348-2412: Version Date Name Description of chan... (Information)
| Version | Date | Name | Description of change | Baseline |
| --- | --- | --- | --- | --- |
| 0.1 | JUN/13/2024 | Kazuya Nagata | Newly create (Based on 38XD) TFDCX32348-23753 [SYS][12.3FDC][APP][Telltale] Brake warning Change point: 1. TFDCX32348-2426/TFDCX32348-5408/TFDCX32348-5412/TFDCX32348-5422/TFDCX32348-6934/TFDCX32348-6938: Removed AppMode 2. TFDCX32348-5420: Change parameter name NVM_PTSysTypeFlag to PTSysTypeFlag 3. TFDCX32348-2443/TFDCX32348-5432/TFDCX32348-5436: Removed All_Telltale_ON test 4. TFDCX32348-5408/TFDCX32348-5412: Changed Comm. Failure detection behavior | BL_20240620_01 |
| 0.2 | OCT/30/2024 | Takuya Tamura | TFDCX32348-54350: [SYS][12.3FDC][APP][Telltale] Change telltale icons by country code Added InternalSignal - TT_DESTVali and determination TFDCX32348-54349: [SYS][12.3FDC][APP][Telltale] Negative pressure drop warning system ・Deleted HW Signals and related items ・Changed two CAN Singals and the Logic of Vacuum Warning System at low level | BL_20241106_01 |
| 0.3 | Aug/26/2025 | Syuta Matsuoka | Change in symbol determination method Move TT priority logic from GUI [SYS-Task] TFDCX32348-89338: [SYS][12.3FDC][R6.1][D3576][APP][Telltale] Destination variation list (Telltale) | BL_20250828_01 |

## TFDCX32348-1007: Reference Document (Heading)

### TFDCX32348-2416: MET-C_BRLV-CSTD-1- (Information)
MET-C_BRLV-CSTD-1-02-A-C0.xlsm
DMS_MET-C_BRLV-CSTD-1-02-A-C0.xlsx

### TFDCX32348-2420: MET-C_BRK-CSTD-1- (Information)
MET-C_BRK-CSTD-1-01-B-C0.xlsm
DMS_MET-C_BRK-CSTD-1-01-B-C0.xlsx

### TFDCX32348-2418: MET-C_BRK-CSTD-A0- (Information)
MET-C_BRK-CSTD-A0-03-A-C0.xlsm
MET-C_BRK-CSTD-A0-03-A-C0_en.xlsm
DMS_MET-C_BRK-CSTD-A0-03-A-C0.xlsx

### TFDCX32348-54218: MET-M_DESTVARI-CSTD-A0-06-A-C0.xlsx (Information)

## TFDCX32348-1008: Overview (Heading)

### TFDCX32348-2422: This SRD defines Telltale of Brake Red. (Information)

## TFDCX32348-1009: Input Requirements (Heading)

### TFDCX32348-2424: InternalSignal - IgnMode (System Interface)

### TFDCX32348-2429: InternalSignal – VacuumSWTestMode (System Interface)
InternalSignal – VacuumSWTestMode
Meaning: This parameter indicates the VacuumSW Test Mode status.
Range: 0 (OFF), 1 (ON)

### TFDCX32348-2430: InternalSignal - ReadytoTravelFlag (System Interface)

### TFDCX32348-2433: CANSignal – B_BRLV (Message Label: VS... (System Interface)
CANSignal – B_BRLV (Message Label: VSC1S95)

### TFDCX32348-2435: CANSignal – B_BRLV2 (Message Label: V... (System Interface)
CANSignal – B_BRLV2 (Message Label: VSC1S97)

### TFDCX32348-63180: CANSignal – B_BRKW (System Interface)
CANSignal – B_BRKW (Message Label: VSC1S95)

### TFDCX32348-63181: CANSignal – B_BRKW2 (System Interface)
CANSignal – B_BRKW2 (Message Label: VSC1S97)

### TFDCX32348-2437: CANSignal – BVWRSW (Message Label: ZN11S17) (System Interface)

### TFDCX32348-2438: CANSignal – BVWRSW_V (Message Label: ZN11S17) (System Interface)

### TFDCX32348-54229: InternalSignal - TT_DESTVali (System Interface)

### TFDCX32348-106557: InternalSignal - Electrical_brake_pad_wear_indicator_Telltale_jdg (System Interface)

### TFDCX32348-106558: InternalSignal - DESTID0026 (System Interface)

## TFDCX32348-1010: Output Requirements (Heading)

### TFDCX32348-2448: TT – BrakeRedWarningTelltale (System Interface)
TT – BrakeRedWarningTelltale
Range: OFF, Txt, Img

### TFDCX32348-61869: InternalSignal - VacuumWarningSystem (System Interface)

## TFDCX32348-1012: Performance Requirements (Heading)

### TFDCX32348-2450: Display Symbol (Heading)

#### TFDCX32348-3041: Display Symbol1: (Heading)

##### TFDCX32348-5402: Display Symbol: Display Color: Red D... (Information)
1. Display Symbol:
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2. Display Color: Red
3. Destination: FMVSS Applicable

#### TFDCX32348-3043: Display Symbol2: (Heading)

##### TFDCX32348-5404: Display Symbol: Display Color: Red D... (Information)
1. Display Symbol:
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2. Display Color: Red
3. Destination: Other than FMVSS Applicable

### TFDCX32348-2453: Bulb Check (Heading)

#### TFDCX32348-3046: None (System Requirement)
- ASIL Rating: QM

### TFDCX32348-2459: Decision Processing (Heading)

#### TFDCX32348-3048: Brake Reservoir Level Warning (Heading)

##### TFDCX32348-5406: B_BRLV Decision Table (Heading)

###### TFDCX32348-5408: No. Input B_BRLV Decision Result Inte... (System Requirement)
| No. | Input |  |  | B_BRLV Decision Result |
| --- | --- | --- | --- | --- |
| No. | InternalSignal - IgnMode | CAN Signal Communication Status – B_BRLV | CAN Signal - B_BRLV Value | B_BRLV Decision Result |
| 1 | OFF | x | x | OFF |
| 2 | ON | Communication starting Never Received: 1 Communication Failure: 0 | x | OFF |
| 3 | ON | Communication establishment Never Received: 0 Communication Failure: 0 | 0b | OFF |
| 4 | ON | Communication establishment Never Received: 0 Communication Failure: 0 | 1b | ON |
| 5 | ON | Communication abnormality Never Received: x Communication Failure: 1 | x | No Change |
Note:
Never Received and Communication Failurelisted in CAN General SRD.
Please check the CAN General SRD for details.
- Verification Criteria: Verify by executing test cases
- Verification Method: System Qualification Test, Unit Test
- Verification Owner: FV, SW
- System Requirement State: Approved
- Secondary Disciplines: FV, SW
- Primary Discipline: SW
- ASIL Rating: QM

##### TFDCX32348-5410: B_BRLV2 Decision Table (Heading)

###### TFDCX32348-5412: No. Input B_BRLV2 Decision Result Int... (System Requirement)
| No. | Input |  |  | B_BRLV2 Decision Result |
| --- | --- | --- | --- | --- |
| No. | InternalSignal - IgnMode | CAN Signal Communication Status – B_BRLV2 | CAN Signal - B_BRLV2 Value | B_BRLV2 Decision Result |
| 1 | OFF | x | x | OFF |
| 2 | ON | Communication starting Never Received: 1 Communication Failure: 0 | x | OFF |
| 3 | ON | Communication establishment Never Received: 0 Communication Failure: 0 | 0b | OFF |
| 4 | ON | Communication establishment Never Received: 0 Communication Failure: 0 | 1b | ON |
| 5 | ON | Communication abnormality Never Received: x Communication Failure: 1 | x | No Change |
Note:
Never Received and Communication Failurelisted in CAN General SRD.
Please check the CAN General SRD for details.
- Verification Criteria: Verify by executing test cases
- Verification Method: System Qualification Test, Unit Test
- Verification Owner: FV, SW
- System Requirement State: Approved
- Secondary Disciplines: FV, SW
- Primary Discipline: SW
- ASIL Rating: QM

##### TFDCX32348-5414: Reservoir Level Warning Decision Table (Heading)

###### TFDCX32348-5416: No. Input Output B_BRLV Decision Resu... (System Requirement)
| No. | Input |  | Output |
| --- | --- | --- | --- |
| No. | B_BRLV Decision Result | B_BRLV2 Decision Result | B_BRLV Reservoir Level Warning |
| 1 | OFF | OFF | OFF |
| 2 | Other than above (One or more of the above two parameters are ON) |  | ON |
- Verification Criteria: Verify by executing test cases
- Verification Method: System Qualification Test, Unit Test
- Verification Owner: FV, SW
- System Requirement State: Approved
- Secondary Disciplines: FV, SW
- Primary Discipline: SW
- ASIL Rating: QM

#### TFDCX32348-5424: Brake System Warning (Heading)

##### TFDCX32348-6932: B_BRKW Decision Table (Heading)

###### TFDCX32348-6934: No. Input B_BRKW Decision Result Inte... (System Requirement)
| No. | Input |  |  | B_BRKW Decision Result |
| --- | --- | --- | --- | --- |
| No. | InternalSignal - IgnMode | CAN Signal Communication Status – B_BRKW | CAN Signal - B_BRKW Value | B_BRKW Decision Result |
| 1 | OFF | x | x | OFF |
| 2 | ON | Communication starting Never Received: 1 Communication Failure: 0 | x | OFF |
| 3 | ON | Communication establishment Never Received: 0 Communication Failure: 0 | 00b | OFF |
| 4 | ON | Communication establishment Never Received: 0 Communication Failure: 0 | 11b | ON |
| 5 | ON | Communication establishment Never Received: 0 Communication Failure: 0 | Other than above | OFF |
| 6 | ON | Communication abnormality Never Received: x Communication Failure: 1 | x | ON |
- Verification Criteria: Verify by executing test cases
- Verification Method: Software Qualification Test, System Qualification Test, Unit Test
- Verification Owner: FV, SW
- System Requirement State: Approved
- Secondary Disciplines: FV, SW
- Primary Discipline: SW
- ASIL Rating: ASIL B

##### TFDCX32348-6936: B_BRKW2 Decision Table (Heading)

###### TFDCX32348-6938: No. Input B_BRKW2 Decision Result Int... (System Requirement)
| No. | Input |  |  | B_BRKW2 Decision Result |
| --- | --- | --- | --- | --- |
| No. | InternalSignal - IgnMode | CAN Signal Communication Status – B_BRKW2 | CAN Signal - B_BRKW2 Value | B_BRKW2 Decision Result |
| 1 | OFF | x | x | OFF |
| 2 | ON | Communication starting Never Received: 1 Communication Failure: 0 | x | OFF |
| 3 | ON | Communication establishment Never Received: 0 Communication Failure: 0 | 00b | OFF |
| 4 | ON | Communication establishment Never Received: 0 Communication Failure: 0 | 11b | ON |
| 5 | ON | Communication establishment Never Received: 0 Communication Failure: 0 | Other than above | OFF |
| 6 | ON | Communication abnormality Never Received: x Communication Failure: 1 | x | ON |
- Verification Criteria: Verify by executing test cases
- Verification Method: Software Qualification Test, System Qualification Test, Unit Test
- Verification Owner: FV, SW
- System Requirement State: Approved
- Secondary Disciplines: FV, SW
- Primary Discipline: SW
- ASIL Rating: ASIL B

##### TFDCX32348-5426: Brake System Warning Decision (Heading)

###### TFDCX32348-5428: No. Input Output (System Requirement)
| No. | Input |  | Output |
| --- | --- | --- | --- |
| No. | B_BRKW Decision Result | B_BRKW2 Decision Result | Brake System Warning Result |
| 1 | OFF | OFF | OFF |
| 2 | OFF | ON | ON |
| 3 | ON | x | ON |
- Verification Criteria: Verify by executing test cases
- Verification Method: System Qualification Test, Unit Test
- Verification Owner: FV, SW
- System Requirement State: Approved
- Secondary Disciplines: FV, SW
- Primary Discipline: SW
- ASIL Rating: ASIL B

#### TFDCX32348-3054: Brake Vacuum Warning System at low level (Heading)

##### TFDCX32348-54494: # (System Requirement)
| # | Input |  |  |  |  |  | Output |
| --- | --- | --- | --- | --- | --- | --- | --- |
| # | InternalSignal - IgnMode | InternalSignal – VacuumSWTestMode | InternalSignal - ReadytoTravelFlag | CAN communication States - BVWRSW*1) | CAN Signal - BVWRSW | CAN Signal - BVWRSW_V | InternalSignal - VacuumWarningSystem |
| 1 | (Initialization at CPU reset or wakeup) |  |  |  |  |  | OFF |
| 2 | OFF | x | x | x | x | x | OFF |
| 3 | ON | ON | x | Communication starting Never Received: 1 Communication Failure: 0 | x | x | OFF |
| 4 | ON | ON | x | Communication establishment Never Received: 0 Communication Failure: 0 | 0b | x | OFF |
| 5 | ON | ON | x | Communication establishment Never Received: 0 Communication Failure: 0 | 1b | 0b | OFF |
| 6 | ON | ON | x | Communication establishment Never Received: 0 Communication Failure: 0 | 1b | 1b | ON |
| 7 | ON | ON | x | Communication abnormality Never Received: x Communication Failure: 1 | x | x | OFF |
| 8 | ON | OFF | OFF | x | x | x | OFF |
| 9 | ON | OFF | ON or FAILED* *2) | Communication starting Never Received: 1 Communication Failure: 0 | x | x | OFF |
| 10 | ON | OFF | ON or FAILED* *2) | Communication establishment Never Received: 0 Communication Failure: 0 | 0b | x | OFF |
| 11 | ON | OFF | ON or FAILED* *2) | Communication establishment Never Received: 0 Communication Failure: 0 | 1b* | 0b | OFF |
| 12 | ON | OFF | ON or FAILED* *2) | Communication establishment Never Received: 0 Communication Failure: 0 | 1b* | 1b* | READY*3) |
| 13 | ON | OFF | ON or FAILED* *2) | Communication abnormality Never Received: x Communication Failure: 1 | x | x | OFF |
| # | Input | Output |
| --- | --- | --- |
| # | InternalSignal - VacuumWarningSystem(Before) | InternalSignal - VacuumWarningSystem |
| 1 | READY continues 7100ms | ON |
Note:
*1) CAN communication States - BVWRSW_V is not described because it is the same Message Label as the BVWRSW.
*2) Refar to TFDCX32348-3061: Internal Signal ReadytoTravelFlag val...
*3) READY(#12) changes to ON when all three conditions marked with * ( ReadytoTravelFlag : ON or FAILED, BVWRSW : 1b, BVWRSW_V : 1b) continue for 7100 ms.
- Verification Criteria: Verify by executing test cases
- Verification Method: Software Qualification Test, System Qualification Test, Unit Test
- Verification Owner: FV, SW
- System Requirement State: Approved
- Secondary Disciplines: FV, SW
- Primary Discipline: SW
- ASIL Rating: QM

#### TFDCX32348-3056: BrakeWarning Telltale Decision (Heading)

##### TFDCX32348-5436: No. (System Requirement)
| No. | Input |  |  | Output |
| --- | --- | --- | --- | --- |
| No. | B_BRLV Reservoir Level Warning | Brake System Warning Result | InternalSignal - VacuumWarningSystem | InternalSignal - BrakeRedWarningTelltale_jdg |
| 1 | OFF | OFF | OFF or READY | OFF |
| 2 | OFF | OFF | ON | ON |
| 3 | OFF | ON | x | ON |
| 4 | ON | x | x | ON |
- Verification Criteria: Verify by executing test cases
- Verification Method: System Qualification Test, Unit Test
- Verification Owner: FV, SW
- System Requirement State: Approved
- Secondary Disciplines: FV, SW
- Primary Discipline: SW
- ASIL Rating: ASIL B

#### TFDCX32348-106555: Destination check (Heading)
- System Requirement State: Draft
- Primary Discipline: TBD
- ASIL Rating: TBD

##### TFDCX32348-106556: No. (System Requirement)
| No. | Input |  | Output |
| --- | --- | --- | --- |
| No. | InternalSignal - DESTID0026 | InternalSignal - TT_DESTVali | LocalParameter - Brake_Red_Destination |
| 1 | 0 | x | UNR |
| 2 | 1 | x | FMVSS |
| 3 | Other than above | 0 | FMVSS |
| 4 | Other than above | 1 | UNR |
- Verification Criteria: Verify by executing test cases
- Verification Method: System Qualification Test, Unit Test
- Verification Owner: FV, SW
- System Requirement State: Approved
- Primary Discipline: SW
- ASIL Rating: QM

#### TFDCX32348-54171: Telltale Control Using DESTVali (Heading)

##### TFDCX32348-54172: # (System Requirement)
| # | Input |  |  | Output |
| --- | --- | --- | --- | --- |
| # | InternalSignal - BrakeRedWarningTelltale_jdg | InternalSignal - Electrical_brake_pad_wear_indicator_Telltale_jdg | LocalParameter - Brake_Red_Destination InternalSignal - TT_DESTVali | TT – BrakeRedWarningTelltale |
| 1 | ON | x | FMVSS | Txt |
| 2 | ON | x | UNR | Img |
| 3 | OFF | ON | FMVSS | Txt |
| 4 | OFF | ON | UNR | Img |
| 5 | OFF | OFF | x | OFF |
- Verification Criteria: Verify by executing test cases
- Verification Method: Software Qualification Test, System Qualification Test, Unit Test
- Verification Owner: FV, SW
- System Requirement State: Approved
- Secondary Disciplines: FV, SW
- Primary Discipline: SW
- ASIL Rating: ASIL B

#### TFDCX32348-3059: Fail Operation (Heading)

##### TFDCX32348-3061: Internal Signal ReadytoTravelFlag val... (System Requirement)
Internal Signal ReadytoTravelFlag value of FAILED.
| N o. | Input Name | Judgment Condition | Operation after Judgment | Recover Condition | Remark |
| --- | --- | --- | --- | --- | --- |
| 1 | ReadytoTravelFlag | Value of ReadytoTravelFlag is FAILE. | The meter shall perform processing considering ReadytoTravelFlag = ON. | Value of ReadytoTravelFlag is OFF or ON. | The value of ReadytoTravelFlag becomes FAILED when the meter cannot receive ENGINE RPM data (NE1). |
- Verification Criteria: Verify by executing test cases
- Verification Method: System Qualification Test, Unit Test
- Verification Owner: FV, SW
- System Requirement State: Approved
- Secondary Disciplines: FV, SW
- Primary Discipline: SW
- ASIL Rating: QM

# Json2ReqIF Transformation

# Specification: TT_AUTO LSD indicator
- JDA Snapshot Date: 2025-10-29 07:14:49

## TFDCX32348-34626: TT_AUTO LSD indicator (Heading)

## TFDCX32348-34627: History (Heading)

### TFDCX32348-34628: Version (Information)
| Version | date | Name | Description of change | Baseline |
| --- | --- | --- | --- | --- |
| 0.1 | 2024/Jul/19 | Syuta Matsuoka | Newly Created [SYS-Task] TFDCX32348-28120: [SYS][12.3FDC][APP][Telltale] AUTO LSD indicator | BL_20240730_01 |
| 0.2 | 2025/Mar/21 | Syuta Matsuoka | Swap Blinking and ON [SYS-Task] TFDCX32348-76544: [SYS][12.3FDC][APP][DEFECT][Telltale] AUTO LSD indicator (Changed by TFDCX32348-76529) | BL_20250328_01 |

## TFDCX32348-34629: Reference Document (Heading)

### TFDCX32348-34630: MET-D_TATLSD-CSTD-0-00-B-C0 (Information)

### TFDCX32348-34631: MET-D_TATLSD-CSTD-0-00-B-C0_en (Information)

### TFDCX32348-34632: DMS_MET-D_TATLSD-CSTD-0-00-B-C0 (Information)

## TFDCX32348-34633: Overview (Heading)

### TFDCX32348-34634: This SRD defines the requirements for telltale of AutoLSD control. (Information)

## TFDCX32348-34635: Input Requirements (Heading)

### TFDCX32348-34640: InternalSignal – IgnMode (System Interface)

### TFDCX32348-34641: CANSignal - B_ALSD(Message Label: VSC1S95) (System Interface)

## TFDCX32348-34712: Output Requirements (Heading)

### TFDCX32348-34713: TT - AUTO_LSD_indicator_Telltale (System Interface)
TT - AUTO_LSD_indicator_Telltale
Range: OFF, ON, Blinking

## TFDCX32348-34715: Performance Requirements (Heading)

### TFDCX32348-34716: Display Symbol (Heading)

#### TFDCX32348-34717: Display Symbol (Information)
Display Symbol:
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Display Color: Amber

### TFDCX32348-35050: Bulb Check (Heading)

#### TFDCX32348-35051: None (System Requirement)
- ASIL Rating: QM

### TFDCX32348-34718: Table Auto LSD indicator (Heading)

#### TFDCX32348-34719: #Input (System Requirement)
| # | Input |  |  |  | Output |
| --- | --- | --- | --- | --- | --- |
| # | InternalSignal - IgnMode | CANSignal -B_ALSD Never Received Status | CANSignal - B_ALSD Fail Status | CANSignal - B_ALSD | TT - AUTO_LSD_indicator_Telltale |
| 1 | (Initialization at CPU reset or wakeup) |  |  |  | OFF |
| 2 | OFF | X | X | X | OFF |
| 3 | ON | X | 1(Fail) | X | no change |
| 4 | ON | 0(Normal) | 0(Normal) | 10b | Blinking Cycle: 500ms Refer to TFDCX32348-35477 ON |
| 5 | ON | 0(Normal) | 0(Normal) | 11b | ON Blinking Cycle: 500ms |
| 6 | ON | other than above |  |  | OFF |
- Verification Criteria: Verify by executing test cases
- Verification Method: Software Qualification Test, System Qualification Test, Unit Test
- Verification Owner: FV, SW
- System Requirement State: Approved
- Primary Discipline: SW
- ASIL Rating: QM

### TFDCX32348-35476: Blinking control (Heading)

#### TFDCX32348-35477: Note: Tun off the Telltale immediately when the telltale off or blinking end conditions are met. (System Requirement)
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Note:
Tun off the Telltale immediately when the telltale off or blinking end conditions are met.
- Verification Criteria: Verify by executing test cases
- Verification Method: Software Qualification Test, System Qualification Test, Unit Test
- Verification Owner: FV, SW
- System Requirement State: Approved
- Primary Discipline: SW
- ASIL Rating: QM

# Json2ReqIF Transformation

# Specification: TT_Factory mode (ADAS DoMekong)
- JDA Snapshot Date: 2025-10-29 07:16:39

## TFDCX32348-46537: TT_Factory mode (ADAS DoMekong) (Heading)

## TFDCX32348-46542: History (Heading)

### TFDCX32348-46548: Version (Information)
| Version | Date | Name | Description of change | Baseline |
| --- | --- | --- | --- | --- |
| 0.1 | 11/Oct/2024 | Takuya Tamura | Newly Create [SYS-Task] TFDCX32348-34192: [SYS][12.3FDC][APP][Telltale] Factory mode (ADAS DoMekong) | BL_20241029_01 |

## TFDCX32348-46543: Reference Document (Heading)

### TFDCX32348-46739: MET-S_FACTMD-CSTD-A0-01-A-C0.xlsm (Information)
MET-S_FACTMD-CSTD-A0-01-A-C0.xlsm
(DMS(In))MET-M_FACTMD-CSTD-A0-01-A-C0.xlsx

## TFDCX32348-46544: Overview (Heading)

### TFDCX32348-46549: This SRD defines (Information)
This SRD defines Telltale of Factory mode (ADAS DoMekong).

## TFDCX32348-46545: Input Requirements (Heading)

### TFDCX32348-46740: InternalSignal – IgnMode (System Interface)

### TFDCX32348-46743: CAN Signal – PLANTREQ(Message Label: ADU1S07) (System Interface)

## TFDCX32348-46546: Output Requirements (Heading)

### TFDCX32348-46744 (System Interface)
HMI - Factory_mode_ADAS_DoMekong_Telltale
Range: {OFF, AMBER_Blinking}

## TFDCX32348-46547: Performance Requirements (Heading)

### TFDCX32348-46566: Display Symbol (Heading)

#### TFDCX32348-46745: Factory mode Symbol (Information)
1. Display Symbol
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2. Display Color : AMBER

### TFDCX32348-46567: Bulb Check (Heading)

#### TFDCX32348-46575: None (System Requirement)
- ASIL Rating: QM

### TFDCX32348-46570: Telltale Control (Heading)

#### TFDCX32348-49304: Logic Table (Heading)

##### TFDCX32348-46748: # (System Requirement)
| # | Input |  |  | Output |
| --- | --- | --- | --- | --- |
| # | InternalSignal - IgnMode | CAN communication States - PLANTREQ | CAN Signal - PLANTREQ | HMI - Factory_mode_ADAS_DoMekong_Telltale |
| 1 | (Initialization at CPU reset or wakeup) |  |  | OFF |
| 2 | OFF | x | x | OFF |
| 3 | ON | Communication starting Never Received: 1 Communication Failure: 0 | x | OFF |
| 4 | ON | Communication establishment Never Received: 0 Communication Failure: 0 | 01b | AMBER_Blinking |
| 5 | ON | Communication establishment Never Received: 0 Communication Failure: 0 | other than above | OFF |
| 6 | ON | Communication abnormality Never Received: x Communication Failure: 1 | x | no change |
- Verification Criteria: Verify by executing test cases
- Verification Method: System Qualification Test, Unit Test
- Verification Owner: FV, SW
- System Requirement State: Approved
- Primary Discipline: SW
- ASIL Rating: QM

#### TFDCX32348-46749: Blinking Control (Heading)

##### TFDCX32348-46752: Blinking Control (System Requirement)
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- Verification Criteria: Verify by executing test cases
- Verification Method: System Qualification Test, Unit Test
- Verification Owner: FV, SW
- System Requirement State: Approved
- Primary Discipline: SW
- ASIL Rating: QM

# Json2ReqIF Transformation

# Specification: GAU_Volt gauge
- JDA Snapshot Date: 2025-09-04 02:42:55

## TFDCX32348-78944: GAU_Volt gauge (Heading)

## TFDCX32348-78948: History (Heading)

### TFDCX32348-78949: Table (Information)
| Version | Date | Name | Description of change | Baseline |
| --- | --- | --- | --- | --- |
| 0.1 | Apr/3/2025 | Hiromune Wachi | Newly create for 12.3inch FDC. [SYS-Story] : TFDCX32348-65536: [SYS][12.3FDC][R4][APP][Gauges] Voltmeter | BL_20250411_01 |

## TFDCX32348-78950: Overview (Heading)

### TFDCX32348-78951: This SRD defines the requirements for IG voltage gauge. (Information)

## TFDCX32348-78953: Reference Document (Heading)

### TFDCX32348-78954: External Sources (Heading)

#### TFDCX32348-78955: MET-M_VOLT-CSTD-A0-00-A-C1 (Information)

## TFDCX32348-78957: Input Requirements (Heading)

### TFDCX32348-78961: HW - IGN_AD (System Interface)
- System Requirement State: Approved

### TFDCX32348-78962: InternalSignal - IgnMode (System Interface)
- System Requirement State: Approved

### TFDCX32348-78969: MCUCONST - MCUID0822 (System Interface)
- System Requirement State: Approved

### TFDCX32348-78970: MCUCONST - MCUID0823 (System Interface)
- System Requirement State: Approved

### TFDCX32348-78971: MCUCONST - MCUID0824 (System Interface)
- System Requirement State: Approved

## TFDCX32348-78958: Output Requirements (Heading)

### TFDCX32348-78992: HMI - HMI_VOLT_GAUGE (System Interface)
HMI - HMI_VOLT_GAUGE
Range : 0[0.0%], 1[0.1%], ..., 1000[100.0%]
- System Requirement State: Approved

### TFDCX32348-78995: InternalSignal - VoltGauge_Prsnt (System Interface)
InternalSignal - VoltGauge_Prsnt
Range : 0[NOT_PRSNT], 1[PRSNT]
- System Requirement State: Approved

## TFDCX32348-78959: Performance Requirements (Heading)

### TFDCX32348-78999: General (Heading)

#### TFDCX32348-79002: Processing block structure (Heading)

##### TFDCX32348-79003: Figure (System Requirement)
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- Verification Criteria: Verify by design review
- Verification Method: Code/Design Review
- Verification Owner: SW
- System Requirement State: Approved
- Primary Discipline: SW
- ASIL Rating: QM

##### TFDCX32348-79004: Table (System Requirement)
| # | Signal name | Range |
| --- | --- | --- |
| ①-1 | ReadingBufStatusFlag | -1[No data], 0[Not full], 1[Full] |
| ①-2 | IGN_AD_In | Range is same as IGN_AD Note : Refer to HSIS. |
| ②-1 | SamplingUpdateFlag | 0[No update], 1[Updated] |
| ②-2 | IGN_AD_Smp | Range is same as IGN_AD Note : Refer to HSIS. |
| ③ | Average_IGN_AD | Range is same as IGN_AD Note : Refer to HSIS. |
| ④ | Final_IGN_AD | Range is same as IGN_AD Note : Refer to HSIS. |
- Verification Criteria: Verify by design review
- Verification Method: Code/Design Review
- Verification Owner: SW
- System Requirement State: Approved
- Primary Discipline: SW
- ASIL Rating: QM

#### TFDCX32348-79016: Parameters (Heading)

##### TFDCX32348-79017: Table - Parameters (System Requirement)
| # | Parameter name | Value |
| --- | --- | --- |
| 1 | 【V_TM】 | MCUID0822 Note : If MCUID0822 cannot read or is greater than 10 , replace it with 0. |
| 2 | 【N_AVE】 | MCUID0823 Note : If MCUID0823 cannot read or is greater than 10, replace it with 0. |
| 3 | 【HYSVAL_AD】 | 79 Note : The above AD value corresponds to a voltage value of [0.5V]. |
| 4 | 【9VDeg_AD】 | 1427 Note : The above AD value corresponds to a voltage value of [9.0V]. |
| 5 | 【12VDeg_AD】 | 1871 Note : The above AD value corresponds to a voltage value of [11.8V]. |
| 6 | 【14VDeg_AD】 | 2458 Note : The above AD value corresponds to a voltage value of [15.5V]. |
| 7 | 【16VDeg_AD】 | 2537 Note : The above AD value corresponds to a voltage value of [16V], and this parameter is not used. |
| 8 | 【19VDeg_AD】 | 3013 Note : The above AD value corresponds to a voltage value of [19V]. |
- Verification Criteria: Verify by design review
- Verification Method: Code/Design Review
- Verification Owner: SW
- System Requirement State: Approved
- Primary Discipline: SW
- ASIL Rating: QM

### TFDCX32348-79000: Process (Heading)

#### TFDCX32348-79008: [A] Initialization (Heading)

##### TFDCX32348-79009: Table - Initialization (System Requirement)
| # | Name | Initilize @ Battery Connect | Initialize @ Module Wake-Up | Initialize @ IgnMode change from ON to OFF | Init Value | Remark |
| --- | --- | --- | --- | --- | --- | --- |
| 1 | HMI - HMI_VOLT_GAUGE | 〇 | 〇 | 〇 | 0[0.0%] | Output signal of this module |
| 2 | InternalSignal - VoltGauge_Prsnt | 〇 | 〇 | X | [*1] | Output signal of this module |
| 3 | ReadingBufIndex (Range : 0, 1, ..., 3) | 〇 | 〇 | 〇 | 0 | Variable of [C] block |
| 4 | ReadingBuf[4] (Range is same as IGN_AD Note : Refer to HSIS.) | 〇 | 〇 | 〇 | Clear all data (Set 0 to all data) | Variable of [C] block |
| 5 | ReadingBufStatusFlag | 〇 | 〇 | 〇 | -1[No data] | Output of [C] block |
| 6 | IGN_AD_In | 〇 | 〇 | 〇 | 0 | Output of [C] block |
| 7 | SamplingTimingCnt (Range : 0, 1, ..., 9) | 〇 | 〇 | 〇 | 0 | Variable of [D] block |
| 8 | SamplingUpdateFlag | 〇 | 〇 | 〇 | 0[No update] | Output of [D] block |
| 9 | IGN_AD_Smp | 〇 | 〇 | 〇 | 0 | Output of [D] block |
| 10 | BufferIndex (Range : 0, 1, ..., 9) | 〇 | 〇 | 〇 | 0 | Variable of [E] block |
| 11 | BufferStatusFlag (Range : -1[No data], 0[Not full], 1[Full]) | 〇 | 〇 | 〇 | -1[No data] | Variable of [E] block |
| 12 | SampleBuffer[10] (Range is same as IGN_AD Note : Refer to HSIS.) | 〇 | 〇 | 〇 | Clear all data (Set 0 to all data) | Variable of [E] block |
| 13 | Average_IGN_AD | 〇 | 〇 | 〇 | 0 | Output of [E] block |
| 14 | Final_IGN_AD | 〇 | 〇 | 〇 | 0 | Output of [F] block |
| 15 | Final_IGN_AD_pre (Range is same as IGN_AD Note : Refer to HSIS.) | 〇 | 〇 | 〇 | 0 | Variable of [G] block |
[*1] : Follow the table below.
| # | Input | Output |
| --- | --- | --- |
| # | MCUID0824 | InternalSignal - VoltGauge_Prsnt |
| 1 | 1[voltage gauge present] | 1[PRSNT] |
| 2 | Other than above | 0[NOT_PRSNT] |
- Verification Criteria: Verify by executing test cases
- Verification Method: System Qualification Test, Unit Test
- Verification Owner: FV, SW
- System Requirement State: Approved
- Primary Discipline: SW
- ASIL Rating: QM

#### TFDCX32348-79010: [B] Function presence/absence judgment (Heading)

##### TFDCX32348-79011: Table - VoltGauge_Prsnt (System Requirement)
| # | Input |  | Output |
| --- | --- | --- | --- |
| # | IgnMode | MCUID0824 | InternalSignal - VoltGauge_Prsnt |
| 1 | OFF → ON | 1[voltage gauge present] | 1[PRSNT] |
| 2 | OFF → ON | Other than above | 0[NOT_PRSNT] |
| 3 | Other than above |  | No change |
- Verification Criteria: Verify by executing test cases
- Verification Method: System Qualification Test, Unit Test
- Verification Owner: FV, SW
- System Requirement State: Approved
- Primary Discipline: SW
- ASIL Rating: QM

#### TFDCX32348-79014: Main operation (Heading)

##### TFDCX32348-79012 (System Requirement)
Each block of the main operation shall be executed when all of the following conditions are met.
- VoltGauge_Prsnt == 1[PRSNT]
- IgnMode == ON
- 【V_TM】 != 0[0msec]
- 【N_AVE】 != 0[0times]
If any of the above conditions are not met, set the HMI_VOLT_GAUGE as follows:
- HMI_VOLT_GAUGE = 0[0.0%]
- Verification Criteria: Verify by executing test cases
- Verification Method: System Qualification Test, Unit Test
- Verification Owner: FV, SW
- System Requirement State: Approved
- Primary Discipline: SW
- ASIL Rating: QM

##### TFDCX32348-79019: [C] IGN_AD reading process (Heading)

###### TFDCX32348-79021: Table - IGN_AD reading process (System Requirement)
| # | Input |  | Output |  |  |
| --- | --- | --- | --- | --- | --- |
| # | ReadingBufIndex | ReadingBufStatusFlag | ReadingBuf[ReadingBufIndex] | ReadingBufIndex [*1] | ReadingBufStatusFlag |
| 1 | 3 | X | Value of IGN_AD | 0 | 1[Full] |
| 2 | Other than 3 | 1[Full] | Value of IGN_AD | Increment by 1 | No change |
| 3 | Other than 3 | Other than 1[Full] | Value of IGN_AD | Increment by 1 | 0[Not full] |
[*1] : Update ReadingBufIndex after updating ReadingBuf.
- Verification Criteria: Verify by executing test cases
- Verification Method: System Qualification Test, Unit Test
- Verification Owner: FV, SW
- System Requirement State: Approved
- Primary Discipline: SW
- ASIL Rating: QM

###### TFDCX32348-79022: Calculation of IGN_AD_In (System Requirement)
Cluster shall calculate IGN_AD_In for each of the following conditions.
Case of “ReadingBufStatusFlag != 1[Full]“:
IGN_AD_In = 0
Case of “ReadingBufStatusFlag == 1[Full]“:
IGN_AD_In = Round{(Sum of ReadingBuf[0] to ReadingBuf[3]) / 4. 0}
- Verification Criteria: Verify by executing test cases
- Verification Method: System Qualification Test, Unit Test
- Verification Owner: FV, SW
- System Requirement State: Approved
- Primary Discipline: SW
- ASIL Rating: QM

##### TFDCX32348-79023: [D] Sampling process (Heading)

###### TFDCX32348-79024: Table - Sampling process (System Requirement)
| # | Input |  | Output |  |  |
| --- | --- | --- | --- | --- | --- |
| # | SamplingTimingCnt | ReadingBufStatusFlag | IGN_AD_Smp | SamplingUpdateFlag | SamplingTimingCnt |
| 1 | 0 | 1[Full] | IGN_AD_In | 1[Updated] | [*1] |
| 2 | 0 | Other than 1[Full] | 0 | 0[No update] | 0 |
| 3 | Other than 0 | X | No change | 0[No update] | [*1] |
[*1] : Set according to the table below.
| # | Input | Output |
| --- | --- | --- |
| # | SamplingTimingCnt | SamplingTimingCnt |
| 1 | SamplingTimingCnt <（【V_TM】 - 1) | Increment by 1 |
| 2 | (【V_TM】 - 1) ≦ SamplingTimingCnt | 0 |
- Verification Criteria: Verify by executing test cases
- Verification Method: System Qualification Test, Unit Test
- Verification Owner: FV, SW
- System Requirement State: Approved
- Primary Discipline: SW
- ASIL Rating: QM

##### TFDCX32348-79025: [E] Averaging process (Heading)

###### TFDCX32348-79026: Table - Averaging process (System Requirement)
| # | Input |  |  | Output |  |  |
| --- | --- | --- | --- | --- | --- | --- |
| # | SamplingUpdateFlag | BufferIndex | BufferStatusFlag | SampleBuffer[] | BufferIndex [*1] | BufferStatusFlag |
| 1 | 1[Updated] | BufferIndex >=(【N_AVE】 - 1) | X | Store IGN_AD_Smp value in SampleBuffer[【N_AVE】 - 1] | 0 | 1[Full] |
| 2 | 1[Updated] | BufferIndex < (【N_AVE】 - 1) | 1[Full] | Store IGN_AD_Smp value in SampleBuffer[BufferIndex] | Increment by 1 | No change |
| 3 | 1[Updated] | BufferIndex < (【N_AVE】 - 1) | Other than 1[Full] | Store IGN_AD_Smp value in SampleBuffer[BufferIndex] | Increment by 1 | 0[Not full] |
| 4 | Other than above |  |  | No change | No change | No change |
[*1] : Update BufferIndex after updating SampleBuffer.
- Verification Criteria: Verify by executing test cases
- Verification Method: System Qualification Test, Unit Test
- Verification Owner: FV, SW
- System Requirement State: Approved
- Primary Discipline: SW
- ASIL Rating: QM

###### TFDCX32348-79027: Calculation of average data (System Requirement)
Cluster shall calculate the averaged data according to the following calculation:
Case of “BufferStatusFlag == -1[No data]“
Average_IGN_AD = 0
Case of “BufferStatusFlag == 0[Not full]“
Average_IGN_AD = Round{(“Sum of SampleBuffer[0] to SampleBuffer[BufferIndex - 1]” / BufferIndex), 0}
Case of “BufferStatusFlag == 1[Full]“
Average_IGN_AD = Round{(“Sum of SampleBuffer[0] to SampleBuffer[【N_AVE】 - 1]” / 【N_AVE】), 0}
- Verification Criteria: Verify by executing test cases
- Verification Method: System Qualification Test, Unit Test
- Verification Owner: FV, SW
- System Requirement State: Approved
- Primary Discipline: SW
- ASIL Rating: QM

##### TFDCX32348-79028: [F] Hysteresis process (Heading)

###### TFDCX32348-79029: Table - Hysteresis process (System Requirement)
| # | Input |  | Output |
| --- | --- | --- | --- |
| # | Final_IGN_AD(previous value) | Average_IGN_AD vs Final_IGN_AD(previous value) | Final_IGN_AD |
| 1 | Final_IGN_AD ≧【HYSVAL_AD】 | (Final_IGN_AD +【HYSVAL_AD】) ≦ Average_IGN_AD | Average_IGN_AD |
| 2 | Final_IGN_AD ≧【HYSVAL_AD】 | Average_IGN_AD ≦ (Final_IGN_AD -【HYSVAL_AD】) | Average_IGN_AD |
| 3 | Final_IGN_AD <【HYSVAL_AD】 | (Final_IGN_AD +【HYSVAL_AD】) ≦ Average_IGN_AD | Average_IGN_AD |
| 4 | Other than above |  | No change |
- Verification Criteria: Verify by executing test cases
- Verification Method: System Qualification Test, Unit Test
- Verification Owner: FV, SW
- System Requirement State: Approved
- Primary Discipline: SW
- ASIL Rating: QM

##### TFDCX32348-79030: [G] Bar display value calculation process (Heading)

###### TFDCX32348-79031: Table - Bar display value calculation process (System Requirement)
| # | Input | Output |  |
| --- | --- | --- | --- |
| # | Final_IGN_AD vs Final_IGN_AD_pre | HMI - HMI_VOLT_GAUGE | Final_IGN_AD_pre |
| 1 | Final_IGN_AD != Final_IGN_AD_pre | [*1] | Final_IGN_AD |
| 2 | Other than above | No change | No change |
[*1] : Calculate HMI_VOLT_GAUGE according to the table below.
| # | Input |  | Output | Remarks |
| --- | --- | --- | --- | --- |
| # | Final_IGN_AD |  | HMI - HMI_VOLT_GAUGE | Remarks |
| # | Decimal value in 12bit A/D | Voltage at connector pin [a] | HMI - HMI_VOLT_GAUGE | Remarks |
| 1 | Final_IGN_AD ≦【9VDeg_AD】 | [a] ≦ 9.0V | 0[0.0%] |  |
| 2 | 【9VDeg_AD】< Final_IGN_AD < 【12VDeg_AD】 | 9.0V < [a] < 11.8V | Round(400[40.0%] x (Final_IGN_AD -【9VDeg_AD】) / (【12VDeg_AD】-【9VDeg_AD】), 0) | Calculate by linear interpolation |
| 3 | 【12VDeg_AD】≦ Final_IGN_AD ≦ 【14VDeg_AD】 | 11.8.V ≦ [a] ≦15.5V | 400[40.0%] |  |
| 4 | 【14VDeg_AD】< Final_IGN_AD < 【19VDeg_AD】 | 15.5V < [a] < 19.0V | 400[40.0%] + Round(600[60.0%] x (Final_IGN_AD -【14VDeg_AD】) / (【19VDeg_AD】-【14VDeg_AD】), 0) | Calculate by linear interpolation [*1] |
| 5 | 【19VDeg_AD】≦ Final_IGN_AD | 19.0V ≦ [a] | 1000[100.0%] |  |
[*1] : According to Toyota's required specifications, the output at 【16VDeg_AD】 is the same as the linearly interpolated value, so no judgment is made using 【16VDeg_AD】.
- Verification Criteria: Verify by executing test cases
- Verification Method: System Qualification Test, Unit Test
- Verification Owner: FV, SW
- System Requirement State: Approved
- Primary Discipline: SW
- ASIL Rating: QM

###### TFDCX32348-79087: Reference: Excerpt from Toyota's requirements (Information)
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Note :
The backlight will turn off when IGN_AD is around 16V or higher.
Therefore, gauges that are higher than around 16V will not be displayed on the meter.

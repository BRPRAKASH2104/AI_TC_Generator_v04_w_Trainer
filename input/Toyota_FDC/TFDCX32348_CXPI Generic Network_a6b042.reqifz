# Json2ReqIF Transformation

# Specification: CXPI Generic Network
- JDA Snapshot Date: 2025-09-04 02:36:18

## TFDCX32348-9401: CXPI Generic Network (Heading)
CXPI (Clock eXtension Peripheral Interface) Generic Network

## TFDCX32348-9403: History (Heading)

### TFDCX32348-15377: History (Information)
| Version | Date | Name | Description of change | SRD Baseline |
| --- | --- | --- | --- | --- |
| 1.0 | 20/Jun/2024 | ttakaba | TFDCX32348-23804: [SYS][12.3FDC][APP][CXPI] General Specification First release for 12.3 FDC. CXPI slave. A document of the change points from 38xD is attached to the Jira story. | BL_20240617_01 |
| 1.1 | 11/Mar/2025 | ttakaba | TFDCX32348-34151 [SYS][12.3FDC][APP][CXPI] Zone CXPI2 communication specification Supported METEER (Meter Error) output. | BL_20250311_01 |
| 1.2 | 31/Jul/2025 | ttakaba | TFDCX32348-100884 [SYS][12.3FDC][IMP][APP][Common] VoltageOperatingMode update for HSIS C-Sample CXPI communication abnormal voltage flags have been changed from LVSD2/HVSD2 to LVSD4/HVSD4. Updated startup time requirements. | BL_20250731_01 |

## TFDCX32348-9404: Overview (Heading)

### TFDCX32348-15379: SRD Overview (Heading)

#### TFDCX32348-19673: Overview (Information)
This SRD specifies the utilization of the CXPI communication function and defines the interface between CXPI communication driver and the application software.
CXPI communication protocol shall be implemented based on the CXPI protocol specification.

### TFDCX32348-15380: Overview of the CXPI Communication (Heading)

#### TFDCX32348-19675: CXPI overview (Information)
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In the CXPI communication, each ECU (node) shares one communication line (CXPI bus) like LIN communication.
And the data format getting on the bus is also the serial communication format that starts from start bit and ends with stop bit.
However, the communication signal on the bus is transmitted as a PWM signal unlike a normal serial signal.
One cycle of the PWM signal corresponds to one bit of the serial data, and the logical value 0 and 1 are represented by the PWM duty ratio.
There is one master node on the CXPI bus, and the master node always outputs the clock to the CXPI bus with the duty ratio equivalent to the logical “1”.
And each node connected to the CXPI bus communicates in synchronization with the clock.
The CXPI bus is pulled-up to +B voltage, and each node drives the bus line with open drain output.
Therefore, each node can output a logical “0” signal by extending the low width of the PWM signal. Here, logical “0” is dominant and logical “1” is recessive.
In this way, CXPI communication is performed by converting serial format frames into PWM signals.

### TFDCX32348-15382: Overview of the CXPI Message Frame Format (Heading)

#### TFDCX32348-19677: Message frame (Information)
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The above figure is the normal frame format used in the CXPI communication. When logical “1” state continues 20 bits on the bus, it is considered as bus idle, and then each note can start frame transmission.
The PID corresponds to the message ID of CAN communication.
Similar to CAN communication, there is an arbitration function that detects simultaneous transmission.
When each node transmits a PID, the output bit and actual bit on the bus are always compared, and if a mismatch is detected, the arbitration lost is determined and the subsequent output is stopped.
Finally, only one node that wins the arbitration can continue frame transmission.

### TFDCX32348-15384: Overview of the Communication Method (Heading)

#### TFDCX32348-19679: Communication method (Information)
Two communication methods are defined in the CXPI protocol specification, and either method can be adopted as the system implementation.
1. Polling method
Like LIN communication, the master controls all frame transmission timing. The PID can be transmitted only by the master, and slaves can send response data to the PID transmitted by the master.
2. Event trigger method
The master sends PIDs for periodic timing. And the slave sends a PID for an event timing. In response to the PID, the ECU designated as the transmitter sends the data frame.
In this product, event trigger method is adopted, and the cluster is the slave.
The cluster does not transmit a PID to request data from slave node, and each node transmits PID and following data autonomously.

## TFDCX32348-9410: Related Documents (Heading)

### TFDCX32348-19681: JASO CXPI standard specifications (Information)
| # | Document Name | Document ID | Document Link | Remarks |
| --- | --- | --- | --- | --- |
| [1] | CXPI 1部: 規格概要とユースケース定義 CXPI Part 1: General Information and Use Cases Definition | JASO D015-1 | Attached |  |
| [2] | CXPI 3部: プロトコル仕様 CXPI Part 3: Protocol Specification | JASO D015-3 | attached |  |
| [3] | CXPI 5部: プロトコルコンフォーマンステスト仕様 CXPI Part 5: Protocol Conformance Test Specification | JASO D015-5 | attached |  |

### TFDCX32348-19683: Customer specifications (Information)
| # | Document Name | Document ID | Document Link | Remarks |
| --- | --- | --- | --- | --- |
| [4] | CXPI 仕様書体系 CXPI Specification Overfiew | gncxpispf-a00-01-a | Attahced |  |
| [5] | CXPI ECU標準ハードウェア仕様書 CXPI ECU Standard Hardware Specification | gncxpiecuhard-a00-01-a | Attahced |  |
| [6] | CXPIネットワーク記述仕様書 Rule of CXPI Network Specification | gncxpinetfmt-a00-01-a | Attahced |  |
| [7] | CXPI ECU通信機能仕様書 CXPI ECU Communication Functional Specifications | gncxpiecufunc-a00-01-a | Attahced |  |
| [8] | メータCXPIシステム標準通信仕様書 Meter CXPI System Standard Communication Specifications | gncxpivehcs-ZON2-1006-a | Attahced |  |
| [9] | CXPI ECU試験仕様書 CXPI ECU Test Specification | gncxpiecutest-a00-01-a | Attahced |  |

## TFDCX32348-9406: Input Requirements (Heading)

### TFDCX32348-15386: Internal Signal - CAN-NM_Mode (System Interface)
- Verification Criteria: Verify by code review
- Verification Method: Code/Design Review
- Verification Owner: SW
- System Requirement State: Approved
- Primary Discipline: SW
- ASIL Rating: QM

### TFDCX32348-15388: Internal Signal - IgnMode (System Interface)
- Verification Criteria: Verify by code review
- Verification Method: Code/Design Review
- Verification Owner: SW
- System Requirement State: Approved
- Primary Discipline: SW
- ASIL Rating: QM

### TFDCX32348-15067: Internal Signal - BAStatus (System Interface)
- Verification Criteria: Verify by code review
- Verification Method: Code/Design Review
- Verification Owner: SW
- System Requirement State: Approved
- Primary Discipline: SW
- ASIL Rating: QM

### TFDCX32348-15070: Internal Signal - ACCStatus (System Interface)
- Verification Criteria: Verify by code review
- Verification Method: Code/Design Review
- Verification Owner: SW
- System Requirement State: Approved
- Primary Discipline: SW
- ASIL Rating: QM

### TFDCX32348-15072: H/W - CXPI Bus Signal (System Interface)
H/W - CXPI Bus Signal
(Used to detect CXPI wakeup pulse)
- Verification Criteria: Verify by code review
- Verification Method: Code/Design Review
- Verification Owner: SW
- System Requirement State: Approved
- Primary Discipline: SW
- ASIL Rating: QM

### TFDCX32348-15074: CXPI RX Message Frames (System Interface)
CXPI RX Message Frames specified in the CXPI summary
- Verification Criteria: Verify by code review
- Verification Method: Code/Design Review
- Verification Owner: SW
- System Requirement State: Approved
- Primary Discipline: SW
- ASIL Rating: QM

### TFDCX32348-15076: Internal Signal - LVSD2 LVSD4 (System Interface)
- Verification Criteria: Verify by code review
- Verification Method: Code/Design Review
- Verification Owner: SW
- System Requirement State: Approved
- Primary Discipline: SW
- ASIL Rating: QM

### TFDCX32348-15078: Internal Signal - HVSD2 HVSD4 (System Interface)
- Verification Criteria: Verify by code review
- Verification Method: Code/Design Review
- Verification Owner: SW
- System Requirement State: Approved
- Primary Discipline: SW
- ASIL Rating: QM

### TFDCX32348-15080: Internal Signal - LVSD3 (System Interface)
- Verification Criteria: Verify by code review
- Verification Method: Code/Design Review
- Verification Owner: SW
- System Requirement State: Approved
- Primary Discipline: SW
- ASIL Rating: QM

### TFDCX32348-15082: Internal Signal - HVSD3 (System Interface)
- Verification Criteria: Verify by code review
- Verification Method: Code/Design Review
- Verification Owner: SW
- System Requirement State: Approved
- Primary Discipline: SW
- ASIL Rating: QM

### TFDCX32348-27636: HMI - HMI_InterruptType (System Interface)
- Verification Criteria: Verify by code review
- Verification Method: Code/Design Review
- Verification Owner: SW
- System Requirement State: Approved
- Primary Discipline: SW
- ASIL Rating: QM

## TFDCX32348-9408: Output Requirements (Heading)

### TFDCX32348-27612: Internal Signal - CXPI_ComState (System Interface)
InternalSignal - CXPI_ComState
Range : SLEEP, INIT, ACTIVE, SEND_LOCK, BUS_OFF, DEINIT
This parameter indicates the CXPI driver level communication status.
- Verification Criteria: Verify by code review
- Verification Method: Code/Design Review
- Verification Owner: SW
- System Requirement State: Approved
- Primary Discipline: SW
- ASIL Rating: QM

### TFDCX32348-15084: CXPI TX Message Frames (System Interface)
CXPI TX Message Frames specified in the CXPI summary
(Message Transmission)
- Verification Criteria: Verify by code review
- Verification Method: Code/Design Review
- Verification Owner: SW
- System Requirement State: Approved
- Primary Discipline: SW
- ASIL Rating: QM

### TFDCX32348-15086: Internal Signal - CXPI_B (System Interface)
Internal Signal - CXPI_B
Range : 0 (INACTIVE), 1 (ACTIVE)
This parameter indicates the status of CXPI_B communication condition.
- Verification Criteria: Verify by code review
- Verification Method: Code/Design Review
- Verification Owner: SW
- System Requirement State: Approved
- Primary Discipline: SW
- ASIL Rating: QM

### TFDCX32348-15088: Internal Signal - CXPI_BA (Dropped) (System Interface)
Internal Signal - CXPI_BA (Dropped)
Range : 0 (INACTIVE), 1 (ACTIVE)
This parameter indicates the status of CXPI_BA communication condition.
- Verification Criteria: Verify by code review
- Verification Method: Code/Design Review
- Verification Owner: SW
- System Requirement State: Rejected
- Primary Discipline: SW
- ASIL Rating: QM

### TFDCX32348-15090: Internal Signal - CXPI_IGR (System Interface)
Internal Signal - CXPI_IGR
Range : 0 (INACTIVE), 1 (ACTIVE)
This parameter indicates the status of CXPI_IGR communication condition.
- Verification Criteria: Verify by code review
- Verification Method: Code/Design Review
- Verification Owner: SW
- System Requirement State: Approved
- Primary Discipline: SW
- ASIL Rating: QM

### TFDCX32348-15091: CXPI Frame Never Received Status (System Interface)
CXPI Frame Never Received Status - *** (Defined in the CXPI summary <CXID7>)
Range : 0 (Received), 1 (Never Received)
Never Received and Communication Failure status processing are processed per message frame.
- Verification Criteria: Verify by code review
- Verification Method: Code/Design Review
- Verification Owner: SW
- System Requirement State: Approved
- Primary Discipline: SW
- ASIL Rating: QM

### TFDCX32348-15093: CXPI Frame Communication Failure Status (System Interface)
CXPI Frame Communication Failure Status - *** (Defined in the CXPI summary <CXID9>)
Range : 0 (Normal), 1 (Failed)
Never Received and Communication Failure status processing are processed per message frame.
- Verification Criteria: Verify by code review
- Verification Method: Code/Design Review
- Verification Owner: SW
- System Requirement State: Approved
- Primary Discipline: SW
- ASIL Rating: QM

### TFDCX32348-15094: CXPI Frame Diag Status (System Interface)
CXPI Frame Diag Status - *** (Defined in the CXPI summary <CXID11>)
Range : 0 (Normal), 1 (Failed)
Used for logging a DTC.
- Verification Criteria: Verify by code review
- Verification Method: Code/Design Review
- Verification Owner: SW
- System Requirement State: Approved
- Primary Discipline: SW
- ASIL Rating: QM

### TFDCX32348-15096: CXPI Signal (System Interface)
CXPI Signal - *** (Defined in the CXPI summary <CXID16>)
Range : Depends on signal.
If CXPI signal is defined in the Input Requirements of the application, consider that the signal value and communication status (never received, communication failure) are also defined as input.
Note that communication status will be processed per message. Hence reference the status of the message that signal belongs to.
- Verification Criteria: Verify by code review
- Verification Method: Code/Design Review
- Verification Owner: SW
- System Requirement State: Approved
- Primary Discipline: SW
- ASIL Rating: QM

### TFDCX32348-15098: Internal Signal - CXPIHWErrorStaus (System Interface)
Internal Signal - CXPIHWErrorStaus
Range : 0 (Normal), 1 (Error)
This parameter indicates the status of the CXPI module hardware error.
- Verification Criteria: Verify by code review
- Verification Method: Code/Design Review
- Verification Owner: SW
- System Requirement State: Approved
- Primary Discipline: SW
- ASIL Rating: QM

### TFDCX32348-15100 (System Interface)
Internal Signal - CXPIBusOffStatus (Dropped)
Range : 0 (Normal), 1 (Bus off)
This parameter indicates the status of the CXPI bus off.
- Verification Criteria: Verify by code review
- Verification Method: Code/Design Review
- Verification Owner: SW
- System Requirement State: Rejected
- Primary Discipline: SW
- ASIL Rating: QM

### TFDCX32348-15102 (System Interface)
Internal Signal - CXPITxLockStatus (Dropped)
Range : 0 (Normal), 1 (TxLock)
This parameter indicates the status of the transmission lock.
- Verification Criteria: Verify by code review
- Verification Method: Code/Design Review
- Verification Owner: SW
- System Requirement State: Rejected
- Primary Discipline: SW
- ASIL Rating: QM

### TFDCX32348-15104 (System Interface)
CXPI Signal - METEER (Message Label: CXMET1S01)
Range : 0 (Normal), 1 (Error)
- Verification Criteria: Verify by code review
- Verification Method: Code/Design Review
- Verification Owner: SW
- System Requirement State: Approved
- Primary Discipline: SW
- ASIL Rating: QM

## TFDCX32348-9412: Performance Requirements (Heading)

### TFDCX32348-15109: CXPI Summary (Heading)

#### TFDCX32348-19685: Note (Information)
This SRD defines the general processing of the CXPI communication.
In this SRD, <CXID##> indicates the link to a configuration item in the CXPI summary.
CXPI summary is stored in https://visteon.atlassian.net/browse/TFDCX32348-7505.

### TFDCX32348-15111: Processing Cycle (Heading)

#### TFDCX32348-19686: CXPI Processing Cycle = 10 msec (System Requirement)
- Verification Criteria: Verify by code review
- Verification Method: Code/Design Review
- Verification Owner: SW
- System Requirement State: Approved
- Primary Discipline: SW
- ASIL Rating: QM

### TFDCX32348-15113: CXPI Protocol Implementation (Heading)

#### TFDCX32348-19688: CXPI protocol (System Requirement)
[[8]Node_List]
CXPI communication protocol shall be implemented based on the CXPI protocol specification.
Standard communication logic and parameter values which does not mentioned in this SRD, need to be implemented according to the protocol specification. Refer to [2]JASO D015-3 (TFDCX32348-19681 )
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- Verification Criteria: Verify by code review
- Verification Method: Code/Design Review
- Verification Owner: SW
- System Requirement State: Approved
- Primary Discipline: SW
- ASIL Rating: QM

### TFDCX32348-15115: CXPI Configuration Parameters (Heading)

#### TFDCX32348-19690: Table - CXPI Configuration parameters (System Requirement)
[[5]CXHW002-2] [[8]Node_List,Schdule] [[7]CXMF006-1,CXMF018-5]
| # | Item | Configuration Value | Remarks |
| --- | --- | --- | --- |
| 1 | Baud Rate | 19.2K bps |  |
| 2 | 1 Bit Time (Tbit) | 52.08usec (1000000usec/19.2K bps) |  |
| 3 | Master/Slave | Slave |  |
| 4 | Message Frame Format | Normal Format (DLC = 0 to 12) | No burst frame (long frame) support required. Do not receive the message frame if DLC value is 1111b. |
| 5 | Method | Event Trigger Method | Master transmits PIDs for periodic transmission and slave responces the data frame for the PIDs. Slave transmits PID and the data frame for an event transmission. (*1) |
| 6 | Data Assignment | Big Endian |  |
| 7 | Unused bit in TX message | Fill with ‘0”. |  |
| 8 | Transmission retry count when arbitration lost is detected. | unlimited | Retry will be stooped by detecting send lock. (*2) |
| 9 | Transmission retry count when transmission error is detected. | 2 times (total 3 times including first transmission) |  |
(*1) Refer to TFDCX32348-27277
(*2) Refer to #4 of TFDCX32348-20294
- Verification Criteria: Verify by communication test
- Verification Method: Code/Design Review, Software Qualification Test
- Verification Owner: SW
- System Requirement State: Approved
- Primary Discipline: SW
- ASIL Rating: QM

#### TFDCX32348-27617: Table - CXPI Control Constants (System Requirement)
[gncxpiecufunc-a00-01-a:Table6-1, Table5-3]
| # | Parameter | value |  |  | Remarks | Reference |
| --- | --- | --- | --- | --- | --- | --- |
| # | Parameter | min | typical | max | Remarks | Reference |
| 1 | Tsend_lock | 700 msec | 800 msec | 900 msec | Send lock detection time. | gncxpiecufunc-a00-01-a:Table6-1 |
| 2 | Tbusoff_restart_s | 500 msec | - | - | Slave bus-off recovery time. | gncxpiecufunc-a00-01-a:Table6-1 |
| 3 | Tsleep | - | 40 msec | - | Slave sleep delay after receiving a sleep frame. | gncxpiecufunc-a00-01-a:Table6-1 |
| 4 | Twakeup_s | - | - | 50 msec | Slave startup time. No apply. (LogicQA#229) | gncxpiecufunc-a00-01-a:Table6-1 |
| 5 | Ttx_wakeup | 0.25 msec | - | 2.5 msec | Wakeup pulse dominant width. | gncxpiecufunc-a00-01-a:Table6-1 |
| 6 | Twakeup_recovery_s | 60 msec | 150 msec | 250 msec | Wakeup pulse retry time. | gncxpiecufunc-a00-01-a:Table6-1 |
| 7 | Ttx_wakeup_space | 5 msec | - | 10 msec | Wakeup pulse recessive width. | gncxpiecufunc-a00-01-a:Table6-1 |
| 8 | Trx_wakeup_slave | 5 usec | - | - | Slave wakeup pulse detection period. | gncxpiecufunc-a00-01-a:Table6-1 |
| 9 | Trx_wakeup_timeout | 15 msec | - | 60 msec | Wakeup pulse timeout time. | gncxpiecufunc-a00-01-a:Table6-1 |
| 10 | Trx_wakeup_filter_s | 0.5 usec | - | 5 usec | Slave wakeup pulse filtering time | gncxpiecufunc-a00-01-a:Table6-1 |
| 11 | Tslv_init | - | - | 100 msec | CXPI initialization completion time | gncxpiecufunc-a00-01-a:Table5-3 |
| 12 | Tslv_st | - | - | 120 msec | PID reception startup time | gncxpiecufunc-a00-01-a:Table5-3 |
- Verification Criteria: Verify by communication test
- Verification Method: Code/Design Review, Software Qualification Test
- Verification Owner: SW
- System Requirement State: Approved
- Primary Discipline: SW
- ASIL Rating: QM

### TFDCX32348-27276: CXPI Communication State Control (Heading)

#### TFDCX32348-27295: Diagram - CXPI Communication State Transition (System Requirement)
[gncxpiecufunc-a00-01-a:Fig5-2]
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Parameter / Key words used in above picture (for text search)
- CXPI_ComState, CXPI_ComRequest. PID_Tx, LVSD4, HVSD4, Sleep frame, Physical bus error, Tbusoff_restart_s, Tsleep
As for the CXPI initialization/de-initialization processing, refer to CXPI controller datasheets.
(1) Configure the CXPI modue to wakeup pulse detection mode.
(2) Initialize the CXPI controller.
(3) Output CXPI wakeup pulse. Refer to TFDCX32348-27390
(4) (7) (10) Disable PID tansmission for event condition.
(5) When any PID is received, PID transmission for event condition is enabled. Refer to (C) of TFDCX32348-27277
(6) When “Send lock” error is determined, re-initialize the CXPI dirver module. Refer to #4 of TFDCX32348-20294
(8) When “Bus off” error is determined, re-initialize the CXPI driver module. Refer to #2 of TFDCX32348-20294
(9) Wait Tbusoff_restart_s (Refer to TFDCX32348-15115 ) before returning to normal operation.
(11) Wait Tsleep (Refer to TFDCX32348-15115 ) for the clock to stop, then start the shutdown procedure.
(12) De-initialize the CXPI driver module. (Transion to wakeup pulse detection mode.)
(*1) If CXPI register check is failed, return to SLEEP state and do not start the communication. Refer to #1 of TFDCX32348-20294
(*2) Refer toTFDCX32348-27273 for clock input status determination.
(*3) If CXPI activation condition is due to CXPI wakeup pulse input, skip CXPI wakeup pulse output.
If CXPI activation trigger condition is external (CXPI wakeup pulse reception), skip CXPI clock status checking and directly transition to box (4) processing. (Impediment TFDCX32348-36643)
(*4) Refer to TFDCX32348-20298 for physical bus error. This path also includes the case that CXPI clock is stopped without receiving a sleep frame,
(*5) Refer to TFDCX32348-27396 for sleep frame.
- Verification Criteria: Verify by executing test cases
- Verification Method: Code/Design Review, System Qualification Test
- Verification Owner: FV
- System Requirement State: Approved
- Primary Discipline: SW
- ASIL Rating: QM

#### TFDCX32348-27457: CXPI Wakeup Pulse Detection (Slave) (System Requirement)
[[7]CXNM006]
- Slave shall detect wakeup pulse when two consecutive dominant (low) level separated by recessive (high) level on the CXPI bus.
- Wakeup pulse shall not be detected when each dominant (low) level width is lass than Trx_wakeup_filter_s.
- Wakeup pulse shall be detected when each dominant (low) level width is greater than Trx_wakeup_slave.
i.e.) The width between Trx_wakeup_filter_s and Trx_wakeup_slave, wakeup may or may not be detected.
- If the period of the two consecutive dominant (low) is less than Trx_wakeup_timeout(min), wakeup shall be detected.
- If the period of the two consecutive dominant (low) is greater than Trx_wakeup_timeout(max), wakeup shall not be detected.
i.e.) The period between Trx_wakeup_timeout(min) and Trx_wakeup_timeout(max), wakeup may or may not be detected.
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Trx_wakeup_filter_s, Trx_wakeup_slave, Trx_wakeup_timeout : Refer to TFDCX32348-27617
- Verification Criteria: Verify by injecting wakeup pulse
- Verification Method: Code/Design Review, System Qualification Test
- Verification Owner: FV
- System Requirement State: Approved
- Primary Discipline: SW
- ASIL Rating: QM

#### TFDCX32348-20288: CXPI Startup Requirements (System Requirement)
[gncxpivehcs-ZON2-1006-a:CXMN019, LogicQA#229]
Cluster (slave node) shall transition to standby mode within Twakeup_s after receiving a wakeup pulse.
Cluster (slave node) shall transition to standby mode within Tslv_init and shall be able to receive a PID until Tslv_st after receiving a wakeup pulse.
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Twakeup_s Tslv_init, Tslv_st : Refer to TFDCX32348-27617
(*1) Tslv_init is a reference value. If we conform the PID reception possible timing (Tslv_st), it is acceptable even if Tslv_init is not conformed.
- Verification Criteria: Verify by communication test
- Verification Method: Code/Design Review, Software Qualification Test
- Verification Owner: SW
- System Requirement State: Approved
- Primary Discipline: SW
- ASIL Rating: QM

#### TFDCX32348-27273 (System Requirement)
How to determine if CXPI clock input is active or inactive.
[gncxpiecufunc-a00-01-a:5.4.7]
If a falling edge has been detected on the CXPI bus within past 5 ms, it is determiened that CXPI clock input is active.
If no falling edge has been detected on the CXPI bus within past 5 ms, it is determined that CXPI clock input is inactive.
- Verification Criteria: Verify by communication test
- Verification Method: Code/Design Review, Software Qualification Test
- Verification Owner: SW
- System Requirement State: Approved
- Primary Discipline: SW
- ASIL Rating: QM

#### TFDCX32348-27390: Flowchart - CXPI Wakeup Pulse Output (System Requirement)
[gncxpiecufunc-a00-01-a:CXNM005]
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Key words for text search.
- Ttx_wakeup, Ttx_wakeup_space, Twakeup_recovery_s
(1) Output wakeup pulse to CXPI bus.
(2) Check CXPI clock is started. Refer to TFDCX32348-27273 for clock status determination. However, care must be taken to ensure that the wakeup pulse output itself is not detected as the presence of a clock input.
(3) Wait up to Twakeup_recovery_s to receive clock input.
(4) Output wakeup pulse to CXPI bus as 2nd try.
Ttx_wakeup, Ttx_wakeup_space, Twakeup_recovery_s : Refer to TFDCX32348-27617
- Verification Criteria: Verify by executing test cases
- Verification Method: Code/Design Review, System Qualification Test
- Verification Owner: FV
- System Requirement State: Approved
- Primary Discipline: SW
- ASIL Rating: QM

#### TFDCX32348-27396: Table - Sleep frame format (System Requirement)
[gncxpiecufunc-a00-01-a:CXNM008-1, 4.6]
| # | PID | Information Byte | Data1 | Data2 | Data3 | Data4 | Data5 | Data6 | Data7 | Data8 | CRC |
| --- | --- | --- | --- | --- | --- | --- | --- | --- | --- | --- | --- |
| 1 | 0x1F | Table-2 | 0x00 | 0xFF | 0xFF | 0xFF | 0xFF | 0xFF | 0xFF | 0xFF | Same as standard message. (*1) |
(*1) Refer to section 5.4.3.1.1.7 in [2]JASO D015-3 (TFDCX32348-19681 )
Table-2 Information byte
| # | DLC (bit7-bit4) | Wakeup.ind (bit3) | Sleep.ind (bit2) | CT (bit1-bit0) |
| --- | --- | --- | --- | --- |
| 1 | 1000b | Same as standard message. | 1b | 11b |
For slave node: Only Data1 = 0x00 shall be checked for sleep frame. (Accept any value for Data2 to Data8).
Also DLC check is not required.
- Verification Criteria: Verify by executing test cases
- Verification Method: Code/Design Review, System Qualification Test
- Verification Owner: FV
- System Requirement State: Approved
- Primary Discipline: SW
- ASIL Rating: QM

### TFDCX32348-15123: CXPI Error Handling (Heading)

#### TFDCX32348-20292: CXPI Protocol Defined Error Check (System Requirement)
[JASO-D015-3 5.1.7]
The CXPI driver shall perform the following error detections defined in the protocol standard.
| # | Item | Error Detection | Reference | Applicability |  | Operation when the error is detected | Retry Processing |
| --- | --- | --- | --- | --- | --- | --- | --- |
| # | Item | Error Detection | Reference | Tx Frame | Rx Frame | Operation when the error is detected | Retry Processing |
| 1 | Arbitration Lost(This is not an error) | Bit error is detected for PID | 5.4.8.2 of [2] JASO D015-3 | Yes (For PID) | No | Stop the transmission, and switch to receiver. | After detected IFS, retry the frame transmission (*1) |
| 2 | Bit Error | Received bit does not match transmitted bit. | 5.4.9.1 of [2] JASO D015-3 | Yes (Except for PID) | No | Stop the transmission, and reflect to bus off determination and METERR output. | After detected IFS, retry the frame transmission (*2) |
| 3 | CRC Error | Calculated CRC does not match received CRC. | 5.4.9.2 of [2] JASO D015-3 | No | Yes | Discard the received frame, and reflect to METERR output. | After detected IFS, start new frame reception. |
| 4 | Parity Error | Number of "1" does not odd value. | 5.4.9.3 of [2] JASO D015-3 | No | Yes (For PID) | Discard the received frame. | After detected IFS, start new frame reception. |
| 5 | Physical Bus Error | Physical Bus Error Judgement (*3) | 5.4.9.4 of [2] JASO D015-3 | - | - | Transition to sleep state (*4). Used for METERR output. | N/A |
| 6 | Data Length Error | Detected logical "0" (start bit) within 10bit length after CRC. or Received data length does not match the DLC value in the information byte. | 5.4.9.5 of [2] JASO D015-3 | Yes | - | Stop the transmission, and reflect to bus off determination and METERR output. | After detected IFS, retry the frame transmission (*2) |
| 7 | Data Length Error | Detected logical "0" (start bit) within 10bit length after CRC. or Received data length does not match the DLC value in the information byte. | 5.4.9.5 of [2] JASO D015-3 | - | Yes | Discard the received frame, and reflect to METERR output. | After detected IFS, start new frame reception. |
| 8 | Counter Error | CT does not change sequentially. | 5.4.9.6 of [2] JASO D015-3 | No | No | N/A (CT checking is not applied for this product) | N/A |
| 9 | Overrun Error | Data buffer was overwritten by a new data before reading the data. | 5.4.9.7 of [2] JASO D015-3 | No | Yes | Stop the reception, and discard the receiving frame | After detected IFS, start new frame reception. |
| 10 | Framing Error | No stop bit detected (Logical "0" is detected at stop bit position) | 5.4.9.8 of [2] JASO D015-3 | Yes | - | Stop the transmission, and reflect to bus off determination and METERR output. | After detected IFS, retry the frame transmission (*2) |
| 11 | Framing Error | No stop bit detected (Logical "0" is detected at stop bit position) | 5.4.9.8 of [2] JASO D015-3 | - | Yes | Stop the reception, and discard the receiving frame, and reflect to METERR output. | After detected IFS, start new frame reception. |
Note 1: IFS (Inter Frame Space). Refer to 5.4.3.3.1 of [2] JASO D015-3.
Note 2: Refer to #2 of TFDCX32348-20294 and 5.4.11 of [2] JASO D015-3 for bus off determination.
Note 3: Refer to TFDCX32348-20299 for METERR output.
(*1) Refer to #8 of TFDCX32348-19690
(*2) Refer to #9 of TFDCX32348-19690
(*3) Refer to TFDCX32348-20298
(*4) Refer to (*4) path in TFDCX32348-27295
- Verification Criteria: Verify by injecting fault by CXPI test tool
  Verify by code/design review for items that cannot be tested
- Verification Method: Code/Design Review, System Qualification Test
- Verification Owner: FV, SW
- System Requirement State: Approved
- Primary Discipline: SW
- ASIL Rating: QM

#### TFDCX32348-20298: CXPI Physical Bus Error Judgement (System Requirement)
[JASO D015-3 5.4.12]
Judge physical bus error according to below condition.
| # | Item | Error Condition | Recovery Condition | Reference |
| --- | --- | --- | --- | --- |
| 1 | Physical bus error | No frame received for 7 seconds during CXPI communication is active. | Any frame received normally. | 5.4.9.4 of [2] JASO D015-3 |
Note 1:
Start with normal status, and reset error status when power domain CXPI_B (Refer to TFDCX32348-20302 ) status becomes INACTIVE.
Maintain 7 seconds timer counting even if CXPI communication is re-initialized by some error (bus off, send lock).
Note 2:
This error will force the CXPI communication status to go into sleep mode. Refer to (*4) path of TFDCX32348-27295 .
Also this error status is referred in CXPI Error Bit processing. Refer to TFDCX32348
- Verification Criteria: Verify by executing test cases
- Verification Method: Code/Design Review, System Qualification Test
- Verification Owner: FV
- System Requirement State: Approved
- Primary Discipline: SW
- ASIL Rating: QM

#### TFDCX32348-20294: Table - CXPI Error Handling (System Requirement)
[gncxpiecufunc-a00-01-a:CXFS001,CXFS003,CXFS004,CXFS006,CXFS007]
| # | Failure detection item | Check condition (Timing) | Target object | Failure judge method | Operation when the failure is detected | Recovery judge method | Operation when the failure is recovered | Status output interface (I/F Name) | Customer spec reference |
| --- | --- | --- | --- | --- | --- | --- | --- | --- | --- |
| 1 | CXPI register check | At CXPI initialization | CXPI system registers | Verify by R/W test | CXPI communication shall not be activated and set the application interface parameter to specific value. (*2) | N/A | N/A | CXPIHWErrorStaus Set to TRUE when the failure is detected. Clear to FALSE when the check is passed normally. | Section 4.5 of customer spec [7]. |
| 2 | Bus off | During CXPI bus is active | CXPI bus | Based on the frame transmission error (Refer to CXPI protocol specification) | Disable PID and frame data transmission and clear queued TX message then re-initialize the CXPI controller. | N/A (Force recovery) | Wait Tbusoff_restart_s after re-initialization, then return to normal operation. (*3)(*4) | CXPI_ComState = BUS_OFF (*4) | Section 5.4.11 of JASO spec [2] Section 4.4 of customer spec [7]. |
| 3 | Wrong DLC | When a message is received | Any RX message | Compare received CXPI message DLC with the DLC specified in CXPI summary. | If received message DLC is bigger than expected DLC, discard extra data and consider as normal reception. If received message DLC is smaller than specified DLC, then discard the message. | - | - | N/A | Section 4.6 of customer spec [7] |
| 4 | Send lock for TX message | When CXPI message is transmitted. | All TX messages | When the message cannot be transmitted normally within Tsend_lock. (*1) | Disable and clear CXPI queued TX message then re-initialize the CXPI controller. | N/A (Force recovery) | Return to normal operation after the re-initialization. (*4) | CXPI_ComState = SEND_LOCK (*4) | Section 4.2 of customer spec [7] |
| 5 | Missing judgment for control | Every CXPI task execution | CXPI RX messages that communication is enabled | (*5) | (*5) | When CXPI message is received normally. | Immediately recover the failure. | Refer to <CXID9> in the CXPI summary. | Section 4.3 of customer spec [7] |
| 6 | Missing judgment for DTC logging | Every CXPI task execution | CXPI RX messages that communication is enabled | (*5) | (*5) | When CXPI message is received normally. | Immediately recover the failure. | Refer to <CXID11> in the CXPI summary. | Section 4.3 of customer spec [7] |
(*1) If the message transmission is cancelled due to the limit of error retries before the send lock is determined, the send lock shall not be detected. Tsend_lock : Refer to TFDCX32348-27617
(*2) Refer to "Set value when CXPI register check is failed" column in the signal processing table. Refer to TFDCX32348-20317
(*3) Tbusoff_restart_s : Refer to TFDCX32348-27617
(*4) Refer to communication state transition (TFDCX32348-27295 )
(*5) Refer to receive signal application interface (TFDCX32348-20317 )
- Verification Criteria: Verify by injecting fault by CXPI test tool
  Verify by code/design review for items that cannot be tested
- Verification Method: Code/Design Review, System Qualification Test
- Verification Owner: FV, SW
- System Requirement State: Approved
- Primary Discipline: SW
- ASIL Rating: QM

### TFDCX32348-15125: CXPI Error Status Handling (Heading)
CXPI Communication Error Status Judgement

#### TFDCX32348-20299: Table - CXPI Error Status (System Requirement)
[JASO D015-3 5.4.12]
| # | Internal Parameter | Set 1 (Error) Condition | Clear 0 (normal) Condition | Comment |
| --- | --- | --- | --- | --- |
| 1 | CXPI_Error_Status (*1) | When the following error is detected. - Bit Error - CRC Error - Physical Bus Error - Data Length Error - Framing Error (*2) | When CXPI frame CXMET1S01 is sent normally. |  |
(*1) CXPI_Error_Status shall be initialized with 0 when CXPI power domain CXPI_B (TFDCX32348-20302 ) status is changed from INACTIVE to ACTIVE.
(*2) Refer to TFDCX32348-20292
- Verification Criteria: Verify by design/code review
- Verification Method: Code/Design Review
- Verification Owner: SW
- System Requirement State: Approved
- Primary Discipline: SW
- ASIL Rating: QM

#### TFDCX32348-20301: METEER (Meter Error) output (System Requirement)
[JASO D015-3 5.4.12]
Error bit signal is not available in the CXPI signal table.
We are requesting to add METERR output for CXPI function evaluation but ignore below table for now.
METEER signal has been added to CXMET1S01 frame.
| # | Input | Output | Remarks |
| --- | --- | --- | --- |
| # | Internal Parameter - CXPI_Error_Status | CXPI Signal - METERR METEER | Remarks |
| 1 | 0 (Normal) | 0 | No output signal available. CXMET1S01 |
| 2 | 1 (Error) | 1 | No output signal available. CXMET1S01 |
CXPI_Error_Status : Refer to TFDCX32348-20299
- Verification Criteria: Verify by design/code review.
- Verification Method: Code/Design Review
- Verification Owner: SW
- System Requirement State: Approved
- Primary Discipline: SW
- ASIL Rating: QM

### TFDCX32348-15126: CXPI Communication Power Domain (Heading)

#### TFDCX32348-19717: Explanation of the Power Domain (Information)
CXPI message frames are grouped based on the communication active condition. Power domain is the grouping name of the communication active condition.
The name is referred in the CXPI summary. If the power domain status is ACTIVE, CXPI TX/RX shall be executed for the messages which belongs to the power domain.

#### TFDCX32348-27302: CXPI Communication Request Status Determination (Network Management) (System Requirement)
[gncxpivehcs-ZON2-1006-a:NetworkManagement]
[MET-M_SWLIGHT-CSTD-A0-00-A-C0:5]
| # | Input |  |  |  |  | Output |
| --- | --- | --- | --- | --- | --- | --- |
| # | Internal Signal - IgnMode | Internal Signal - AccStatus | Internal Signal - BAStatus | Internal Signal - CAN-NM_Mode | HMI - HMI_InterruptType | Internal Parameter - CXPI_ComRequest |
| 1 | ON | X | X | X | X | TRUE |
| 2 | X | ON | X | X | X | TRUE |
| 3 | X | X | ON | X | X | TRUE |
| 4 | X | X | X | Other than "Bus Sleep Mode" (*1) | X | TRUE |
| 5 | X | X | X | X | Other than (BLANK or OFF) | TRUE |
| 6 | Other than above (All power status is OFF and (CAN-NM = "Bus Sleep") and interrupt content is not displayed on TFT) |  |  |  |  | FALSE |
(*1) “Network Mode” or Prepare Bus Sleep Mode”
- Verification Criteria: Verify by executing test cases
- Verification Method: Code/Design Review, System Qualification Test
- Verification Owner: FV
- System Requirement State: Approved
- Primary Discipline: SW
- ASIL Rating: QM

#### TFDCX32348-20302: Power domain - CXPI_B (System Requirement)
[[8]NetworkManagement]
| # | Input |  |  | Output |  | Remarks |
| --- | --- | --- | --- | --- | --- | --- |
| # | Internal Parameter - CXPI_B current status (*1) | Internal Parameter - CXPI_ComState | Internal Parameter - CXPI_ComRequest | Internal Parameter - CXPI_B | Internal Parameter - CXPI_WakeupCause | Remarks |
| 1 | (Initialization at CPU reset or wakeup) |  |  | INACTIVE | EXTERNAL |  |
| 2 | INACTIVE | INIT or ACTIVE or SEND_LOCK or BUS_OFF | X | ACTIVE | EXTERNAL | CXPI activated by CXPI bus status. |
| 3 | INACTIVE | DEINIT or SLEEP | TRUE | ACTIVE | INTERNAL | CXPI will be activated by cluster cause. |
| 4 | INACTIVE | DEINIT or SLEEP | FALSE | INACTIVE | No change | Maintain inactive. |
| 5 | ACTIVE | INIT or ACTIVE or SEND_LOCK or BUS_OFF | X | ACTIVE | No change | Maintain active. |
| 6 | ACTIVE | DEINIT or SLEEP | TRUE | ACTIVE | No change | Maintain active by cluster cause. |
| 7 | ACTIVE | DEINIT or SLEEP | FALSE | INACTIVE | No change |  |
(*1) "current status" means the status before processing this table.
Note: This table need to process normally regardless LVSD4 and HVSD4 status.
CXPI_ComState : Refer to TFDCX32348-27295
CXPI_ComRequest : Refer to TFDCX32348-27302
- Verification Criteria: Verify by executing test cases
- Verification Method: Code/Design Review, System Qualification Test
- Verification Owner: FV
- System Requirement State: Approved
- Primary Discipline: SW
- ASIL Rating: QM

#### TFDCX32348-20305: Power domain - CXPI_BA (Dropped) (System Requirement)
Power domain - CXPI_BA (Dropped)
Currently no BA transmission condition is existing.
[[8]Transmit]
| # | InternalSignal – BAStatus | InternalSignal - ACCState | InternalSignal - IgnMode | Internal Parameter – CXPI_BA |
| --- | --- | --- | --- | --- |
| 1 | ON | X | X | ACTIVE |
| 2 | X | ON | X | ACTIVE |
| 3 | X | X | ON | ACTIVE |
| 4 | OFF | OFF | OFF | INACTIVE |
Note: CXPI bus is activated based on CXPI_B status. Theoretically, if CXPI_BA is ACTIVE, CXPI_B is also ACTIVE.
Note: This table need to process normally regardless LVSD4 and HVSD4 status.
- Verification Criteria: Verify by executing test cases
- Verification Method: TBD
- Verification Owner: FV
- System Requirement State: Rejected
- Primary Discipline: SW
- ASIL Rating: QM

#### TFDCX32348-20307: Power domain - CXPI_IGR (System Requirement)
[[8]Transmit]
| # | Input | Output |
| --- | --- | --- |
| # | Internal Signal - IgnMode | Internal Parameter - CXPI_IGR |
| 1 | ON | ACTIVE |
| 2 | OFF | INACTIVE |
Note: If IgnMode = ON, CXPI_Com_Request is set to TRUE. Theoretically, if CXPI_IGR is ACTIVE, CXPI_B is also ACTIVE.
Note: This table need to process normally regardless LVSD4 and HVSD4 status.
- Verification Criteria: Verify by executing test cases
- Verification Method: TBD
- Verification Owner: FV
- System Requirement State: Approved
- Primary Discipline: SW
- ASIL Rating: QM

### TFDCX32348-27271: CXPI PID Transmission Scheduling (Heading)

#### TFDCX32348-27277: CXPI Frame Transmission Rules (System Requirement)
[gncxpiecufunc-a00-01-a:CXMF013,CXMF014,CXMF015] [STD_QA#2324]
(A) The master node transmits PIDs for periodic transmission timing and the designated transmitter for the PID shall send the corresponding data frame.
(B) When an event transmission condition is satisfied, the CXPI slave node shall transmit the PID and the associated data frame for the event.
(C) The CXPI slave node shall not transmit an event timing PID until it has received any PID (referred to as “the first received PID” in (D) & (E)).
(D) Regarding (C), the first received PID includes PIDs that are not target for cluster Tx or Rx.
(E) Regarding (C), if the first received PID is targeted for cluster Tx or Rx, the cluster shall process the data frame accordingly.
(F) The master node always transmits all periodic timing PIDs regardless of the current communication condition (power domain status). If communication condition for a received PID is not active, respond with a data frame containing initial values specified in the CXPI summary sheet.
(G) The slave node shall not transmit an event timing PID if communication condition (power domain) for the PID is not active.
(H) If a data frame is received for a PID whose communication condition (power domain) is inactive, the received data frame shall be discarded.
- Verification Criteria: Verify by executing test cases
- Verification Method: Code/Design Review, System Qualification Test
- Verification Owner: SW
- System Requirement State: Approved
- Primary Discipline: SW
- ASIL Rating: QM

#### TFDCX32348-27278: CXPI Sample Behavior (Information)
Assumption for the example
| PID | Tx Type | Frame Data Transmitter | Frame Data Receiver |  |  |
| --- | --- | --- | --- | --- | --- |
| PID | Tx Type | Frame Data Transmitter | Cluster | Master | Node1 |
| PID1 | Event periodic | Cluster | - | Receive | Receive |
| PID2 | periodic | Master Node | Receive | - | No receive |
| PID3 | Event periodic | Node1 | Receive | Receive | - |
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
#### TFDCX32348-27293: CXPI Master PID Scheduling <for reference> (Information)
<Information>
[gncxpivehcs-ZON2-1006-a:schedule]
| Master Scheduling (1000ms cycle) |  |  |  |
| --- | --- | --- | --- |
| # | Schedule Frame Name | PID | Time Offset[ms] |
| 1 | CXZON1S01 | 0xF2 | 0 |
| 2 | CXCMB1S01 | 0x64 | 50 |
| 3 | CXCMB1S02 | 0xF4 | 100 |
| 4 | CXSTF1S01 | 0x70 | 150 |
| 5 | CXSWS1S01 | 0x68 | 200 |
| 6 | CXCMB1S01 | 0x64 | 250 |
| 7 | CXSWS1S02 | 0xF8 | 300 |
| 8 | CXZON1S03 | 0xEC | 350 |
| 9 | CXMET1S01 | 0x7C | 400 |
| 10 | CXZON1S02 | 0x62 | 450 |
| 11 | CXCMB1S01 | 0x64 | 500 |
| 12 | CXBDB1S41 | 0x7A | 550 |
| 13 | CXBDB1S42 | 0xE6 | 600 |
| 14 | CXBDB1S43 | 0x76 | 650 |
| 15 | CXDMS1S01 | 0x58 | 700 |
| 16 | CXCMB1S01 | 0x64 | 750 |
| 17 | CXOHC1S02 | 0xFE | 800 |
| 18 | CXMET1S02 | 0x4C | 850 |
| 19 | CXZON1S04 | 0xF1 | 900 |

#### TFDCX32348-27373: CXPI Event Transmission Condition (System Requirement)
[gncxpiecufunc-a00-01-a:3.4.2.4]
Event transmission shall be processed during associated power domain status (<CXID28> of the CXPI summary sheet) is active.
Event condition is specified in <CXID30> of the CXPI summary sheet.
According to <CXID30> configuration, when specified condition is satisfied, send PID and the associated data frame if event transmission is enabled (refer to (C) of TFDCX32348-27277 ).
| # | Event Symbol <CXID30> | Event Condition | Remarks |
| --- | --- | --- | --- |
| 1 | W | When the signal value is written. |  |
| 2 | C | When the signal value is changed. |  |
| 3 | R | When the flag changed from 0 to 1. | Applicable for 1 bit length signal. |
| 4 | F | When the flag changed from 1 to 0. | Applicable for 1 bit length signal. |
| 5 | - | No event condition. |  |
- Verification Criteria: Verify by executing test cases
- Verification Method: Code/Design Review, System Qualification Test
- Verification Owner: FV
- System Requirement State: Approved
- Primary Discipline: SW
- ASIL Rating: QM

### TFDCX32348-15130: CXPI Data Frame Transmission Processing (Heading)

#### TFDCX32348-27589: CXPI Data Frame Transmission High Level Flow (System Requirement)
[STD_QA#2324]
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Refer to (F) of TFDCX32348-27277
- Verification Criteria: Verify by executing test cases
- Verification Method: Code/Design Review, System Qualification Test
- Verification Owner: FV
- System Requirement State: Approved
- Primary Discipline: SW
- ASIL Rating: QM

#### TFDCX32348-20312: CXPI Transmit Data Frame Format (System Requirement)
[[7]CXNM013-2] [[8]System_Spec] [[2]5.4.3.1.1.5-(c)]
| Data Name | PID | Information Byte |  |  |  | DATA1 | DATA2 | … | DATA12 | CRC |
| --- | --- | --- | --- | --- | --- | --- | --- | --- | --- | --- |
| Contained Data | ID Parity Bit | DLC (bit7-bit4) | Wakeup.ind (bit3) | Sleep.ind (bit2) | CT (bit1-bit0) | Message data. Variable data length in range 0 to 12. |  |  |  | CRC data |
| Data Handling | Master transmit PID for a periodic timing. Slave transmit PID for an event timing. | Set DLC specified in the CXPI summary sheet <CXID26>. | See Table-2 | See Table-3 | See Table-4 | Data length : Refer to DLC definition in the CXPI summary <CXID26> Signal layout : Refer to Data Position in the CXPI summary <CXID37> |  |  |  | (*1) |
(*1) Refer to section 5.4.3.1.1.7 in [2]JASO D015-3 (TFDCX32348-19681 )
Table-2 (Wakeup.ind)
| # | Input | Output |
| --- | --- | --- |
| # | Internal Parameter - CXPI_WakeupCause | Wakeup.ind |
| 1 | INTERNAL | 1 |
| 2 | EXTERNAL | 0 |
CXPI_WakeupCause : Refer to TFDCX32348-20302
Table-3 (Sleep.ind)
| # | Input |  | Output | Remarks |
| --- | --- | --- | --- | --- |
| # | PID transmitter | Internal Parameter - CXPI_ComRequest | Sleep.ind | Remarks |
| 1 | Master for a periodic timing. | FALSE | 1 | Sleep OK. |
| 2 | Master for a periodic timing. | TRUE | 0 | Awake request. |
| 3 | Slave for an event timing. | X | 0 | Awake request. |
CXPI_ComRequest : Refer to TFDCX32348-27302
Table-4 (CT)
| # | Input | Output | Remarks |
| --- | --- | --- | --- |
| # | CT configuration CXPI summary <CXID32> | CT | Remarks |
| 1 | 0 | 11b | Fixed to 11b. |
| 2 | 1 | 00b → 01b → 10b → 11b → 00b → ... Increment every message transmission | CT value shall be managed for individual message. CT value shall be initialized with 00b when its power domain status <CXID28> is changed from INACTIVE to ACTIVE. |
- Verification Criteria: Verify by executing test cases
- Verification Method: Code/Design Review, System Qualification Test
- Verification Owner: FV
- System Requirement State: Approved
- Primary Discipline: SW
- ASIL Rating: QM

### TFDCX32348-15132: CXPI Message Reception Processing (Heading)
CXPI Message Reception Handling

#### TFDCX32348-20315: CXPI Receive Message Frame Format (System Requirement)
[[7]CXMF008]
| Data Name | PID | Information Byte |  |  |  | DATA1 | DATA2 | … | DATA12 | CRC |
| --- | --- | --- | --- | --- | --- | --- | --- | --- | --- | --- |
| Contained Data | ID Parity Bit | DLC (bit7-bit4) | Wakeup.ind (bit3) | Sleep.ind (bit2) | CT (bit1-bit0) | Message data. Variable data length in range 0 to 12. |  |  |  | CRC data |
| Data Handling | Refer to PID in the CXPI summary <CXID3> | Used for checking the data length. (*1) | Ignore this bit status. | Ignore this bit status. | Ignore this value (CT validation is not required.) | Used to extract the signal values. Signal layout : Refer to Data Position in the CXPI summary <CXID18> |  |  |  | Used to check validity of the frame. |
(*1) Refer to #3 of TFDCX32348-20294
(*2) Refer to section 5.4.3.1.1.7 in [2]JASO D015-3 (TFDCX32348-19681 ) for CRC. Refer to #3 of TFDCX32348-20292 for CRC validation.
- Verification Criteria: Verify by design/code review
- Verification Method: Code/Design Review
- Verification Owner: SW
- System Requirement State: Approved
- Primary Discipline: SW
- ASIL Rating: QM

#### TFDCX32348-20317: CXPI Receive Signal Application Interface (System Requirement)
[[CXFS006,CXFS007]
| # | I/F Parameter | Scope | Value Range | Initialization at CPU reset or wakeup | Initialization at the communication condition (power domain) is changed from INACTIVE to ACTIVE. | De-initialization at the communication condition (power domain) is changed from ACTIVE to INACTIVE. | Received Signal Processing | Set value when CXPI register check is failed. (*2) |
| --- | --- | --- | --- | --- | --- | --- | --- | --- |
| 1 | CXPI Signal Value | For each individual CXPI signal defined in the CXPI summary. | Depends on the signal. | Initialize with the value specified in <CXID20> | Initialize with the value specified in <CXID20> | Initialize with the value specified in <CXID20> | Refer to signal processing flowchart. (*3) | If failsafe value is defined in CXPI summary <CXID21>, set the specified value, otherwise set initial value. |
| 2 | Frame Never Received Status <CXID7> (*1) | For each individual CXPI frame defined in the CXPI summary. | 0 (Received) 1 (Never Received) | 1 (Never Received) | 1 (Never Received) | 1 (Never Received) | Refer to signal processing flowchart. (*3) | 1 (Never Received) |
| 3 | Frame Communication Failure Status for Control <CXID9> (*1) | For each individual CXPI frame defined in the CXPI summary. | 0 (Normal) 1 (Failed) | 0 (Normal) | 0 (Normal) | 0 (Normal) | Refer to signal processing flowchart. (*3) | 1 (Failed) |
| 4 | Frame Missing Status IF for Diag <CXID11> | For each individual CXPI frame defined in the CXPI summary. | 0 (Normal) 1 (Failed) | 0 (Normal) | 0 (Normal) | 0 (Normal) | Refer to signal processing flowchart. (*3) | 0 (Normal) |
| 5 | Signal Reception Callback (optional) | If application need to process something at every signal reception, CXPI high level driver shall support application callback. | - | - | - | - | When signal is received normally, call the callback function defined in the application. | - |
(*1) Process the status of Never Received and Communication Failure for each CXPI message.
When application refers these status for a CXPI signal, provide the status from the message frame to which the signal belongs.
(*2) Refer to #1 of TFDCX32348-20294
(*3) Refer to TFDCX32348-20321
- Verification Criteria: Verify by executing test cases
- Verification Method: Code/Design Review, System Qualification Test
- Verification Owner: FV
- System Requirement State: Approved
- Primary Discipline: SW
- ASIL Rating: QM

#### TFDCX32348-20319: CXPI Diag Mask Condition Processing (For DTC logging) (System Requirement)
[MET-M_METGW-CSTD-3-07-B-C0.7]
| # | Timer Name | Type | Set Condition (*1) | Count Condition | Timer initial Value |
| --- | --- | --- | --- | --- | --- |
| 1 | CXPI Diag Mask Timer | Count down | CPU reset or CPU wakeup or CXPI_B = INACTIVE or LVSD3 = NOT_OK or HVSD3 = NOT_OK or CXPI_ComState = "Other than ACTIVE" | Set Condition is not satisfied. (until 0) | 3 sec |
(*1) Re-start timer if set condition is satisfied while the timer is counting.
CXPI_B : Refer to TFDCX32348-20302
CXPI_ComState : Refer to TFDCX32348-27295
- Verification Criteria: Verify by executing test cases
- Verification Method: Code/Design Review, System Qualification Test
- Verification Owner: FV
- System Requirement State: Approved
- Primary Discipline: SW
- ASIL Rating: QM

#### TFDCX32348-20321: CXPI Received Signal Processing Flow (System Requirement)
[gncxpiecufunc-a00-01-a:4.3,CXFS006,CXFS007]
Execute below flowchart periodically for individual CXPI message defined in the CXPI summary while their communication condition (power domain) is ACTIVE.
Received signal processing and CXPI communication status (CXPI_ComState) are independent. Even if CXPI communication status (CXPI_ComState) becomes other than ACTIVE due to some errors, continue this received signal processing as long as the power domain status is ACTIVE.
Note : Master transmits the periodic timing PIDs regardless their communication conditions. Discard received data frame and skip below processing if associated power domain <CXID6> status is INACTIVE.
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- Never Received and Communication Failure status are processed for each CXPI message frame.
- In below explanation, <CXID##> indicates the configuration item in the CXPI summary. Refer to the setting value for the processing CXPI message.
- Communication Failure status is the missing status for control, and Communication Diag status is the missing status for DTC logging. Timeout decision time is different.
Box (1) : If the CXPI message has received from last execution, then this condition is "Yes", else this condition is "No".
Box (2) : Set the Frame Never Received Status to 0 (Received) for the processing message. Actual interface parameter name is defined in <CXID7>.
Box (3) : Set the Frame Communication Failure Status to 0 (Normal) for the processing message. Actual interface parameter name is defined in <CXID9>.
Box (4) (10) : If "Missing Time (Control)" <CXID8> has specific time value, this condition is "Yes". If <CXID8> is "NA", this condition is "No".
Box (5) : Re-start the missing timer (Control) with specified time value <CXID8>.
Box (6) : Set the Frame Diag Status to 0 (Normal) for the processing message. Actual interface parameter name is defined in <CXID11>.
Box (7) (16) : If "Missing Time (Diag)" <CXID10> has specific time value, this condition is "Yes". If <CXID10> is "NA", this condition is "No".
Box (8) : Re-start the missing timer (Diag) with specified time value <CXID10>.
Box (9) : Extract signal values from the message frame data and save them into the signal buffer. The accumulated data will be delivered to application.
Box (11) : Count down the missing timer (Control) until 0.
Box (12) : If the missing timer (control) is running, this condition is "Yes". If the timer has expired, this condition is "No".
Box (13) : Set the Frame Communication Failure status to 1 (Failed) for the processing message. Actual interface parameter name is defined in <CXID9>.
Box (14) : If "Failsafe Value" <CXID21> has specific value, this condition is "Yes". If <CXID21> is "NA", this condition is "No". In this case the signal buffer maintains last received value.
Box (15) : Replace the signal buffer value with the specified failsafe value <CXID21>.
Box (17) : Count down the missing timer (Diag) until 0.
Box (18) : If the missing timer (Diag) is running, this condition is "Yes". If the timer has expired, this condition is "No".
Box (19) : Set the Frame Diag Status to 1 (Failed) for the processing message. Actual interface parameter name is defined in <CXID11>.
Box (20) : Check the diag mask timer () and transitions to (21) if diag mask timer is running.
Box (21) : Re-start missing timer for diag (for DTC logging).
- Verification Criteria: Verify by executing test cases
- Verification Method: Code/Design Review, System Qualification Test
- Verification Owner: FV
- System Requirement State: Approved
- Primary Discipline: SW
- ASIL Rating: QM

# Json2ReqIF Transformation

# Specification: DIAG_Factory Test Mode
- JDA Snapshot Date: 2025-09-04 02:40:08

## TFDCX32348-7548: Factory Test Mode (Heading)

## TFDCX32348-7551: History (Heading)

### TFDCX32348-10919: Factory Test Mode History (Information)
| Version | Date | Name | Description of change | Baseline |
| --- | --- | --- | --- | --- |
| 1.0 | - | - | New create (Copied from the 38xD project) | - |
| 1.1 | 2025/01/27 | Kazuya Niiho | Update Meter Plant Inspection Mode(Phase 6) TFDCX32348-34211: [SYS][12.3FDC][APP][Diagnostic] Meter Plant Inspection Mode (Phase 6) | BL_20250128_01 |
| 1.2 | 2025/02/25 | Kazuya Niiho | Added requirements for releasing Plant Mode via routine control. TFDCX32348-62042: [SYS][12.3FDC][APP][Diagnostic] Standard Specification for Meter Phase 6 Diag System for Routine Identifier for CV8 | BL_20250303_01 |
| 1.3 | 2025/03/18 | Kazuya Niiho | Replaced NVM signal(NVM_MS_UnitPattern ) with Internal Signal(UnitPattern). TFDCX32348-65564: [SYS][12.3FDC][APP] Update Meter Settings | BL_20250318_01 |
| 1.4 | 2025/06/11 | Kazuya Niiho | Update the requirement of Inspection dedicated screen mode (TFDCX32348-12255, 12257) TFDCX32348-85758: [SYS][12.3FDC][R5.2][D3723][APP][Diagnostic] Standard Specification for Meter Phase 6 Diag System for SID and Session for CV11 | BL_20250618_01 |

## TFDCX32348-7553: Reference Document (Heading)

### TFDCX32348-10921: # Reference document (Information)
| # | Reference document No. | ISL Reference |
| --- | --- | --- |
| 1 | MET-M_TESTMODE-CSTD-A0-03-A-C0 - MET-M_TESTMODE-CSTD-A0-03-A-C0.docx |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 |
| 2 | plantmode-rd001-003-a |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 |

## TFDCX32348-7555: Overview (Heading)

### TFDCX32348-10923: This SRD defines Factory Test Mode. (Information)

## TFDCX32348-7556: Input Requirements (Heading)

### TFDCX32348-10925: InternalSignal: - IgnMode (System Interface)

### TFDCX32348-10927: Internal Signal - TargetSW (System Interface)

### TFDCX32348-10929: Internal Signal - HMI_InterruptType (System Interface)

### TFDCX32348-10934: InternalSignal - Display_Distance_Unit (System Interface)

### TFDCX32348-74383: Internal Signal - UnitPattern (System Interface)
- System Requirement State: Draft
- Primary Discipline: TBD
- ASIL Rating: TBD

## TFDCX32348-7558: Output Requirements (Heading)

### TFDCX32348-10935: Internal Signal - VacuumSWTestMode (System Interface)
Meaning : This parameter indicates the VacuumSW Test Mode status.
Range : 0 (OFF), 1 (ON)
Initial Value : 0 (OFF)
Note: This parameter is stored into backup RAM.

### TFDCX32348-10937: Internal Signal - FactoryMode (System Interface)
Internal Signal - FactoryMode
Description : Output to Screen Navigation for determining Win B mode

### TFDCX32348-10939: HMI - HMI_IN_TestMode_NumItems Descri... (System Interface)
HMI - HMI_IN_TestMode_NumItems
Description : This parameter provides the number of items to be displayed on Test Mode screen
Range : 0 ~ 2

### TFDCX32348-10941: HMI - HMI_IN_TestMode_Item1 Descripti... (System Interface)
HMI - HMI_IN_TestMode_Item1
Description : This parameter provides the first item to be displayed on Test Mode screen
Range : NONE, AC100V, UNIT

### TFDCX32348-10942: HMI - HMI_IN_TestMode_Item2 Descripti... (System Interface)
HMI - HMI_IN_TestMode_Item2
Description : This parameter provides the second item to be displayed on Test Mode screen
Range : NONE, UNIT

### TFDCX32348-10946: HMI - HMI_IN_TestMode_Focus Descripti... (System Interface)
HMI - HMI_IN_TestMode_Focus
Description : This provides the item number on which cursor focus is located currently
Range : 1 ~ 2

### TFDCX32348-65338: Internal Signal - AC100VTestMode (System Interface)
Meaning : This parameter indicates the AC100V Test Mode status.
Range : 0 (OFF), 1 (ON)
Initial Value : 0 (OFF)
Note: This parameter is stored into backup RAM.

### TFDCX32348-65339: Internal Signal - UnitTestMode (System Interface)
Meaning : This parameter indicates the Unit(km/mile) Test Mode status.
Range : 0 (OFF), 1 (ON)
Initial Value : 0 (OFF)
Note: This parameter is stored into backup RAM.

## TFDCX32348-7560: Function Entry (Heading)

### TFDCX32348-10950: Function Entry - fn_TestMode_KeyUp() ... (System Requirement)
Function Entry - fn_TestMode_KeyUp()
Description: This function performs the handling of UP key press
- Verification Criteria: Verify by executing test cases
- Verification Method: Software Qualification Test, System Qualification Test, Unit Test
- Verification Owner: FV, SW
- System Requirement State: Approved
- Primary Discipline: SW
- ASIL Rating: QM

### TFDCX32348-10952: Function Entry - fn_TestMode_KeyDown(... (System Requirement)
Function Entry - fn_TestMode_KeyDown()
Description: This function performs the handling of DOWN key press
- Verification Criteria: Verify by executing test cases
- Verification Method: Software Qualification Test, System Qualification Test, Unit Test
- Verification Owner: FV, SW
- System Requirement State: Approved
- Primary Discipline: SW
- ASIL Rating: QM

### TFDCX32348-10528: Function Entry - fn_TestMode_KeyEnter... (System Requirement)
Function Entry - fn_TestMode_KeyEnter()
Description: This function performs the handling of ENTER key press
- Verification Criteria: Verify by executing test cases
- Verification Method: Software Qualification Test, System Qualification Test, Unit Test
- Verification Owner: FV, SW
- System Requirement State: Approved
- Primary Discipline: SW
- ASIL Rating: QM

## TFDCX32348-7562: Function Call (Heading)

### TFDCX32348-65432 (System Interface)
Function Call - fn_ACInvOutletOnOff_changerequest()
Description: This function sends request to external ECU to change the setting

### TFDCX32348-65433: Function Call - fn_Unit_changerequest(ItemID) (System Interface)

## TFDCX32348-7564: Diagnostics SID (Heading)

### TFDCX32348-10535: SID 0x2E (System Requirement)
SID 0x2E
DataID MSB: $AA, DataID LSB: $00
- Verification Criteria: Verify by executing test cases
- Verification Method: Software Qualification Test, System Qualification Test, Unit Test
- Verification Owner: FV, SW
- System Requirement State: Approved
- Primary Discipline: SW
- ASIL Rating: QM

### TFDCX32348-10537: SID 0x2F (System Requirement)
SID 0x2F
DataID MSB: $2A, DataID LSB: $22, shortTerm Adjustment: $03
- Verification Criteria: Verify by executing test cases
- Verification Method: Software Qualification Test, System Qualification Test, Unit Test
- Verification Owner: FV, SW
- System Requirement State: Approved
- Primary Discipline: SW
- ASIL Rating: QM

### TFDCX32348-70539: SID 0x31 (System Requirement)
SID 0x31
routineID MSB: $DA, routineID LSB: $00, routineInfo: $02
- Verification Criteria: Verify by executing test cases
- Verification Method: Software Qualification Test, System Qualification Test, Unit Test
- Verification Owner: FV, SW
- System Requirement State: Approved
- Primary Discipline: SW
- ASIL Rating: QM

## TFDCX32348-7566: Performance Requirements (Heading)

### TFDCX32348-10539: Diagnostics infomation (Heading)

#### TFDCX32348-12250: SID 0x2E (Heading)

##### TFDCX32348-17446: DataIdentifier AA00 (Heading)

###### TFDCX32348-21082: Request (System Requirement)
| Byte | #1 | #2 | #3 | #4 | #5 | #6 | #7 |
| --- | --- | --- | --- | --- | --- | --- | --- |
| value (contents) | $2E (SID) | $AA (DataID MSB) | $00 (DataID LSB) | $** (Support Info.) | $** (Request Item) | $** (Support Info.) | $** (Request Item) |
- Verification Criteria: Verify by executing test cases
- Verification Method: Software Qualification Test, System Qualification Test, Unit Test
- Verification Owner: FV, SW
- System Requirement State: Approved
- Primary Discipline: SW
- ASIL Rating: QM

###### TFDCX32348-21084: Request Details (Byte #4 - #7) (System Requirement)
| sebit | #7 | #6 | #5 | #4 | #3 | #2 | #1 | #0 |
| --- | --- | --- | --- | --- | --- | --- | --- | --- |
| Request details Byte #4 | (Deleted) | (Deleted) | AC100V ON/OFF support information | km/mile switching ON/OFF Support information | - | - | - | - |
| Request details Byte #5 | (Deleted) | (Deleted) | AC100V ON/OFF | km/mile switching ON/OFF | - | - | - | - |
| Request details Byte #6 | Vacuum SW in plant mode ON/OFF support information | - | - | - | - | - | - | - |
| Request details Byte #7 | Vacuum SW in plant mode ON/OFF | - | - | - | - | - | - | - |
- Verification Criteria: Verify by executing test cases
- Verification Method: Software Qualification Test, System Qualification Test, Unit Test
- Verification Owner: FV, SW
- System Requirement State: Approved
- Primary Discipline: SW
- ASIL Rating: QM

###### TFDCX32348-21676: Positive response (System Requirement)
| Byte | #1 | #2 | #3 |
| --- | --- | --- | --- |
| Value (contents) | $6E (SID) | $AA (DataID MSB) | $00 (DataID LSB) |
- Verification Criteria: Verify by executing test cases
- Verification Method: Software Qualification Test, System Qualification Test, Unit Test
- Verification Owner: FV, SW
- System Requirement State: Approved
- Primary Discipline: SW
- ASIL Rating: QM

###### TFDCX32348-21678: Negtive response (System Requirement)
| Byte | #1 | #2 | #3 |
| --- | --- | --- | --- |
| Value (contents) | $7F (SID) | $2E (SID) | NRC |
Note: About NRC, details refer to TFDCX32348-17067: Negative Response:
- Verification Criteria: Verify by executing test cases
- Verification Method: Software Qualification Test, System Qualification Test, Unit Test
- Verification Owner: FV, SW
- System Requirement State: Approved
- Primary Discipline: SW
- ASIL Rating: QM

###### TFDCX32348-21090: Factory Test Mode OFF Request (System Requirement)
| Byte | #1 | #2 | #3 | #4 | #5 | #6 | #7 |
| --- | --- | --- | --- | --- | --- | --- | --- |
| Value (contents) | $2E (SID) | $AA (DataID MSB) | $00 (DataID LSB) | $00 | $00 | $00 | $00 |
- Verification Criteria: Verify by executing test cases
- Verification Method: Software Qualification Test, System Qualification Test, Unit Test
- Verification Owner: FV, SW
- System Requirement State: Approved
- Primary Discipline: SW
- ASIL Rating: QM

#### TFDCX32348-12252: SID 0x2F (Heading)

##### TFDCX32348-17449: Data Identifier 2A22 (Heading)

###### TFDCX32348-21092: Request (System Requirement)
| Byte | #1 | #2 | #3 | #4 | #5 | #6 |
| --- | --- | --- | --- | --- | --- | --- |
| Value (contents) | $2F (SID) | $2A (DataID MSB) | $22 (DataID LSB) | $03 (shortTermAdjustment) | SW input 2 support infomation (Control State) | SW input 2 (Control State) |
Note: If all bit2=1 of received Byte5, Byte6, then STRG-Back=ON.
* ControlEnableMask has been deleted as it is clearly stated as unnecessary by standard control specification QA(No.3091).
- Verification Criteria: Verify by executing test cases
- Verification Method: Software Qualification Test, System Qualification Test, Unit Test
- Verification Owner: FV, SW
- System Requirement State: Approved
- Primary Discipline: SW
- ASIL Rating: QM

###### TFDCX32348-21094: Request Details (Byte #5 - #6) (System Requirement)
| bit | #7 | #6 | #5 | #4 | #3 | #2 | #1 | #0 |
| --- | --- | --- | --- | --- | --- | --- | --- | --- |
| Request details Byte #5 | - | - | - | - | - | STRG-Back Support information | - | - |
| Request details Byte #6 | - | - | - | - | - | STRG-Back | - | - |
* ControlEnableMask has been deleted as it is clearly stated as unnecessary by standard control specification QA(No.3091).
- Verification Criteria: Verify by executing test cases
- Verification Method: Software Qualification Test, System Qualification Test, Unit Test
- Verification Owner: FV, SW
- System Requirement State: Approved
- Primary Discipline: SW
- ASIL Rating: QM

###### TFDCX32348-21680: Positive response (System Requirement)
| Byte | #1 | #2 | #3 | #4 | #5 | #6 |
| --- | --- | --- | --- | --- | --- | --- |
| Value (contents) | $6F (SID) | $2A (DataID MSB) | $22 (DataID LSB) | $03 (shortTermAdjustment) | SW input 2 support infomation | SW input 2 |
- Verification Criteria: Verify by executing test cases
- Verification Method: Software Qualification Test, System Qualification Test, Unit Test
- Verification Owner: FV, SW
- System Requirement State: Approved
- Primary Discipline: SW
- ASIL Rating: QM

###### TFDCX32348-21682: Negative response (System Requirement)
| Byte | #1 | #2 | #3 |
| --- | --- | --- | --- |
| Value (contents) | $7F (SID) | $2F (SID) | NRC |
Note: About NRC, details refer to TFDCX32348-17085: Negative Response.
- Verification Criteria: Verify by executing test cases
- Verification Method: Software Qualification Test, System Qualification Test, Unit Test
- Verification Owner: FV, SW
- System Requirement State: Approved
- Primary Discipline: SW
- ASIL Rating: QM

###### TFDCX32348-21100: Stop Request (System Requirement)
| Byte | #1 | #2 | #3 | #4 |
| --- | --- | --- | --- | --- |
| Value (contents) | $2F (SID) | $2A (DataID MSB) | $22 (DataID LSB) | $00 (returnControl To ECU) |
Note: If recieved this command, STRG-Back=OFF
* ControlEnableMask has been deleted as it is clearly stated as unnecessary by standard control specification QA(No.3091).
- Verification Criteria: Verify by executing test cases
- Verification Method: Software Qualification Test, System Qualification Test, Unit Test
- Verification Owner: FV, SW
- System Requirement State: Approved
- Primary Discipline: SW
- ASIL Rating: QM

###### TFDCX32348-21684: Positive response (for Stop request) (System Requirement)
| Byte | #1 | #2 | #3 | #4 |
| --- | --- | --- | --- | --- |
| Value | $6F (SID) | $2A (DataID MSB) | $22 (DataID LSB) | $00 (return Control To ECU) |
* ControlEnableMask has been deleted as it is clearly stated as unnecessary by standard control specification QA(No.3091).
- Verification Criteria: Verify by executing test cases
- Verification Method: Software Qualification Test, System Qualification Test, Unit Test
- Verification Owner: FV, SW
- System Requirement State: Approved
- Primary Discipline: SW
- ASIL Rating: QM

###### TFDCX32348-21686: Negative response (for Stop request) (System Requirement)
| Byte | #1 | #2 | #3 |
| --- | --- | --- | --- |
| Value (contents) | $7F (SID) | $2F (SID) | NRC |
Note: About NRC, details refer to TFDCX32348-17085: Negative Response.
- Verification Criteria: Verify by executing test cases
- Verification Method: Software Qualification Test, System Qualification Test, Unit Test
- Verification Owner: FV, SW
- System Requirement State: Approved
- Primary Discipline: SW
- ASIL Rating: QM

#### TFDCX32348-70540: SID 0x31 (Heading)

##### TFDCX32348-70541: routineIdentifier DA00 (Heading)

###### TFDCX32348-70543: Request and Response (Information)
The request and response format is described in the SRD of Data Identifiers (TFDCX32348-7294).
Refer to TFDCX32348-70531: Request and Response Format.

### TFDCX32348-10542: Factory Test Mode (Heading)

#### TFDCX32348-12255: FactoryTestModeStatus and each TestMode (System Requirement)
| No. | Input |  |  |  |  |  | Output |  |  |  |
| --- | --- | --- | --- | --- | --- | --- | --- | --- | --- | --- |
| No. | Execution Timing | SID 2E DID:AA00 Byte5 - Bit5 (AC100V ON/OFF) (*1) | SID 2E DID:AA00 Byte5 - Bit4 (km/mile switching ON/OFF) (*1) | SID 2E DID:AA00 Byte7 - Bit7 (Vacuum SW in plant mode ON/OFF) | SID 2E DID:AA00 Other Bits from Byte 4 to 7 | SID 31 RID:DA00 | Internal Parameter - FactoryTestModeStatus | Internal Signal - AC100VTestMode | Internal Signal - UnitTestMode | InternalSignal - VacuumSWTestMode |
| 1 | IG ON | 1 | 1 | 1 | * | - | ON | 1(ON) | 1(ON) | 1(ON) |
| 2 | IG ON | 1 | 1 | 0 | * | - | ON | 1(ON) | 1(ON) | 0(OFF) |
| 3 | IG ON | 1 | 0 | 1 | * | - | ON | 1(ON) | 0(OFF) | 1(ON) |
| 4 | IG ON | 1 | 0 | 0 | * | - | ON | 1(ON) | 0(OFF) | 0(OFF) |
| 5 | IG ON | 0 | 1 | 1 | * | - | ON | 0(OFF) | 1(ON) | 1(ON) |
| 6 | IG ON | 0 | 1 | 0 | * | - | ON | 0(OFF) | 1(ON) | 0(OFF) |
| 7 | IG ON | 0 | 0 | 1 | * | - | ON | 0(OFF) | 0(OFF) | 1(ON) |
| 8 | IG ON | 0 | 0 | 0 | All 0 | - | OFF | 0(OFF) | 0(OFF) | 0(OFF) |
| 9 | IG ON | Other than above |  |  |  | - | No change |  |  |  |
| 10 | IG ON | - | - | - | - | Received | OFF | 0(OFF) | 0(OFF) | 0(OFF) |
| 11 | IG OFF | - | - | - | - | - | No change |  |  |  |
| 12 | ECU Reset or +B OFF/ON | - | - | - | - | - | OFF | 0(OFF) | 0(OFF) | 0(OFF) |
(*1) There are applicable conditions for these items. Refer to TFDCX32348-21670: DID AA00 Processing.
If applicable conditions are not valid and SID 2E tries to enable that particular bit , then NRC31(RequestOutOfRange) shall be Responded.
- Verification Criteria: Verify by executing test cases
- Verification Method: Software Qualification Test, System Qualification Test, Unit Test
- Verification Owner: FV, SW
- System Requirement State: Approved
- Primary Discipline: SW
- ASIL Rating: QM

### TFDCX32348-10544: Inspection dedicated screen mode (Heading)

#### TFDCX32348-12257: # (System Requirement)
| # | Input |  |  |  | Output |
| --- | --- | --- | --- | --- | --- |
| # | InternalSignal - IgnMode | Internal Parameter - FactoryTestModeStatus | Internal Signal - TargetSW | Internal Signal - FactoryMode(current) | Internal Signal - FactoryMode |
| 1 | OFF | X | X | X | OFF |
| 2 | OFF to ON | OFF | X | X | OFF |
| 3 | OFF to ON | ON | X | X | ON |
| 4 | ON | OFF | X | X | OFF |
| 5 | ON | ON | others value -> 6(TG_BACK) continue 1sec | OFF | ON |
| 6 | ON | ON | others value -> 6(TG_BACK) continue 1sec | ON | OFF |
| 7 | ON | ON | Other than above | X | No Change |
- Verification Criteria: Verify by executing test cases
- Verification Method: Software Qualification Test, System Qualification Test, Unit Test
- Verification Owner: FV, SW
- System Requirement State: Approved
- Primary Discipline: SW
- ASIL Rating: QM

### TFDCX32348-10546: Soft SW Control (Heading)

#### TFDCX32348-12259: Soft SW list (Heading)

##### TFDCX32348-17453: Soft SW (Information)
| Soft SW | Switching Type | Applicability |
| --- | --- | --- |
| AC100V ON/OFF | AⅠ | Support |
| km/mile switching | AⅠ | Support |
| Rear sunshade Open/Close | AⅠ | Not Support |

#### TFDCX32348-12263: Menu Item Determination (Heading)

##### TFDCX32348-17457: Menu Item Determination (System Requirement)
Menu Item Determination
| # | Input |  | Output |  |  |
| --- | --- | --- | --- | --- | --- |
| # | Internal Signal - AC100VTestMode | Internal Signal - UnitTestMode | HMI_IN_TestMode_Item1 | HMI_IN_TestMode_Item2 | HMI_IN_TestMode_NumItems |
| 1 | 0(OFF) | 0(OFF) | NONE | NONE | 0 |
| 2 | 0(OFF) | 1(ON) | UNIT | NONE | 1 |
| 3 | 1(ON) | 0(OFF) | AC100V | NONE | 1 |
| 4 | 1(ON) | 1(ON) | AC100V | UNIT | 2 |
- Verification Criteria: Verify by executing test cases
- Verification Method: Software Qualification Test, System Qualification Test, Unit Test
- Verification Owner: FV, SW
- System Requirement State: Approved
- Primary Discipline: SW
- ASIL Rating: QM

#### TFDCX32348-12264: Initialization of Focus Parameter (Heading)

##### TFDCX32348-17459: Focus Parameter Initialization # Inpu... (System Requirement)
Focus Parameter Initialization
| # | Input | Output |
| --- | --- | --- |
| # | Internal Signal - HMI_InterruptType | HMI_IN_TestMode_Focus |
| 1 | (Initialization at CPU reset or wakeup) | 1 |
| 2 | != FACTORY | 1 |
| 3 | FACTORY | No Change |
- Verification Criteria: Verify by executing test cases
- Verification Method: Software Qualification Test, System Qualification Test, Unit Test
- Verification Owner: FV, SW
- System Requirement State: Approved
- Primary Discipline: SW
- ASIL Rating: QM

#### TFDCX32348-12266: Up Key Control (Heading)

##### TFDCX32348-17461: Up Key Control # Input Output Functio... (System Requirement)
Up Key Control
| # | Input |  |  | Output |
| --- | --- | --- | --- | --- |
| # | Function Entry | HMI_IN_TestModeNumItems | HMI_IN_TestMode_Focus (Current) | HMI_IN_TestMode_Focus |
| 1 | fn_TestMode_KeyUp() | 1 | x | 1 |
| 2 | fn_TestMode_KeyUp() | 2 | 1 | 2 |
| 3 | fn_TestMode_KeyUp() | 2 | 2 | 1 |
| 4 | fn_TestMode_KeyUp() | Other than above |  | 1 |
#1 ~ #4 - Execute in sync with the function call.
- Verification Criteria: Verify by executing test cases
- Verification Method: Software Qualification Test, System Qualification Test, Unit Test
- Verification Owner: FV, SW
- System Requirement State: Approved
- Primary Discipline: SW
- ASIL Rating: QM

#### TFDCX32348-12375: Down Key Control (Heading)

##### TFDCX32348-17463: Down Key Control # Input Output Funct... (System Requirement)
Down Key Control
| # | Input |  |  | Output |
| --- | --- | --- | --- | --- |
| # | Function Entry | HMI_IN_TestModeNumItems | HMI_IN_TestMode_Focus (Current) | HMI_IN_TestMode_Focus |
| 1 | fn_TestMode_KeyDown() | 1 | x | 1 |
| 2 | fn_TestMode_KeyDown() | 2 | 1 | 2 |
| 3 | fn_TestMode_KeyDown() | 2 | 2 | 1 |
| 4 | fn_TestMode_KeyDown() | Other than above |  | 1 |
#1 ~ #4 - Execute in sync with the function call.
- Verification Criteria: Verify by executing test cases
- Verification Method: Software Qualification Test, System Qualification Test, Unit Test
- Verification Owner: FV, SW
- System Requirement State: Approved
- Primary Discipline: SW
- ASIL Rating: QM

#### TFDCX32348-12378: Enter Key Control (Heading)

##### TFDCX32348-17464: # (System Requirement)
| # | Input |  |  |  | Output |
| --- | --- | --- | --- | --- | --- |
| # | Function Entry | HMI_IN_TestMode_Focus | HMI_IN_TestMode_Item1 | HMI_IN_TestMode_Item2 | Function Call |
| 1 | fn_TestMode_KeyEnter() | 1 | NONE | - | - |
| 2 | fn_TestMode_KeyEnter() | 1 | AC100V | - | fn_ACInvOutletOnOff_changerequest() |
| 3 | fn_TestMode_KeyEnter() | 1 | UNIT | - | Refer to TFDCX32348-17467: Output - fn_Unit_changerequest() |
| 4 | fn_TestMode_KeyEnter() | 2 | X | UNIT | Refer to TFDCX32348-17467: Output - fn_Unit_changerequest() |
#1 ~ #4 - Execute in sync with the function call.
- Verification Criteria: Verify by executing test cases
- Verification Method: Software Qualification Test, System Qualification Test, Unit Test
- Verification Owner: FV, SW
- System Requirement State: Approved
- Primary Discipline: SW
- ASIL Rating: QM

#### TFDCX32348-12380: Unit Factory inspection (Heading)

##### TFDCX32348-17467: Output - fn_Unit_changerequest() (System Requirement)
| Input |  | Output |
| --- | --- | --- |
| Internal Signal - UnitPattern | InternalSignal - Display_Distance_Unit | Function Call |
| 0x00(Pattern_A) | 1:km | fn_Unit_changerequest(miles(MPG USA)) |
| 0x00(Pattern_A) | 2:mile | fn_Unit_changerequest(km(L/100km)) |
| 0x01(Pattern_B) | 1:km | fn_Unit_changerequest(miles(MPG)) |
| 0x01(Pattern_B) | 2:mile | fn_Unit_changerequest(km(L/100km)) |
| 0x03(Pattern_D) | 1:km | fn_Unit_changerequest(miles(MPG USA,miles/kWh)) |
| 0x03(Pattern_D) | 2:mile | fn_Unit_changerequest(km(L/100km, kWh/100km)) |
| 0x04(Pattern_E) | 1:km | fn_Unit_changerequest(miles(MPG, miles/kWh)) |
| 0x04(Pattern_E) | 2:mile | fn_Unit_changerequest(km(L/100km, kWh/100km)) |
| 0x07(Pattern_H) | 1:km | fn_Unit_changerequest(miles(miles/kWh))) |
| 0x07(Pattern_H) | 2:mile | fn_Unit_changerequest(km(kWh/100km)) |
| 0x08(Pattern_I) | 1:km | fn_Unit_changerequest(miles(MPGe)) |
| 0x08(Pattern_I) | 2:mile | fn_Unit_changerequest(km(kg/100km)) |
| 0x09(Pattern_J) | 1:km | fn_Unit_changerequest(miles(kg/100km)) |
| 0x09(Pattern_J) | 2:mile | fn_Unit_changerequest(km(kg/100km)) |
| Other than above | - | (Do nothing) |
- Verification Criteria: Verify by executing test cases
- Verification Method: Software Qualification Test, System Qualification Test, Unit Test
- Verification Owner: FV, SW
- System Requirement State: Approved
- Primary Discipline: SW
- ASIL Rating: QM

### TFDCX32348-10550: Factory Test Mode Behaviour on IGN and Battery Cycle (Heading)

#### TFDCX32348-12385 (System Requirement)
Factory mode shall be kept over IGN cycle.
Supplement
If IG ON is detected, the following process will be performed
- If the factory mode is OFF before IG-ON, the Meter will start with the factory mode OFF.
- If the factory mode is ON before IG-ON, the Meter will start with the factory mode ON.
- Verification Criteria: Verify by executing test cases
- Verification Method: Software Qualification Test, System Qualification Test, Unit Test
- Verification Owner: FV, SW
- System Requirement State: Approved
- Primary Discipline: SW
- ASIL Rating: QM

#### TFDCX32348-12388: Factory mode shall be released over battery cycle. (System Requirement)
(All the associated parameter shall be reset to 0)
- Verification Criteria: Verify by executing test cases
- Verification Method: Software Qualification Test, System Qualification Test, Unit Test
- Verification Owner: FV, SW
- System Requirement State: Approved
- Primary Discipline: SW
- ASIL Rating: QM

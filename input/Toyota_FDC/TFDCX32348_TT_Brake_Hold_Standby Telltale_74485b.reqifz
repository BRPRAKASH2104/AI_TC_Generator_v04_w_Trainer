# Json2ReqIF Transformation

# Specification: TT_Brake_Hold_Standby Telltale
- JDA Snapshot Date: 2025-10-29 07:15:31

## TFDCX32348-1030: TT_Brake HOLD Standby Telltale (Heading)

## TFDCX32348-1033: History (Heading)

### TFDCX32348-1699: Version Date Name Description of chan... (Information)
| Version | Date | Name | Description of change | Baseline |
| --- | --- | --- | --- | --- |
| 0.1 | Jun/19/2024 | Kazuya Nagata | Newly create (Based on 38XD) TFDCX32348-29328 [SYS][12.3FDC][APP][Telltale] Brake Hold Standby (after 21 PF) Change point: Nothing | BL_20240627_01 |

## TFDCX32348-1035: Reference Document (Heading)

### TFDCX32348-1702: MET-C_BRKHLD-CSTD-1-03-A-C0.xlsm (Information)

### TFDCX32348-1704: DMS_MET-C_BRKHLD-CSTD-1-03-A-C0.xlsx (Information)

## TFDCX32348-1037: Overview (Heading)

### TFDCX32348-1706: This SRD defines Telltale of Brake HO... (Information)
This SRD defines Telltale of Brake HOLD Standby.

## TFDCX32348-1039: Input Requirements (Heading)

### TFDCX32348-1708: InternalSignal: - IgnMode (System Interface)

### TFDCX32348-1710: CANSignal – B_DAINDC (Message Label: ... (System Interface)
CANSignal – B_DAINDC (Message Label: VSC1S95)

## TFDCX32348-1041: Output Requirements (Heading)

### TFDCX32348-1714: TT – Brake_Hold_Standby_Telltale Me... (System Interface)
TT – Brake_Hold_Standby_Telltale
Meaning: This parameter indicates the display state of Brake Hold Standby Telltale.
Range: OFF, ON
Initial Value: OFF

## TFDCX32348-1042: Performance Requirements (Heading)

### TFDCX32348-1716: Display Symbol (Heading)

#### TFDCX32348-3076: Display Symbol: Display Color: Pure ... (Information)
1. Display Symbol:
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2. Display Color: Pure Green
3. Destination: All [ North America (CONV)_USA, North America (HEV)_USA, North America (CONV)_CANADA, Middle East (CONV), General (CONV), Australia (HEV), Middle East (HEV), General (HEV) ]

### TFDCX32348-1718: Bulb Check (Heading)

#### TFDCX32348-3078: None (System Requirement)
- ASIL Rating: QM

### TFDCX32348-1720: Initial Process (Heading)

#### TFDCX32348-3081: When the ON of the internal signal Ig... (System Requirement)
When the ON of the internal signal IgnMode is detected, the telltale is turn off until a lighting signal is received.
- Verification Criteria: Verify by executing test cases
- Verification Method: System Qualification Test, Unit Test
- Verification Owner: FV, SW
- System Requirement State: Approved
- Primary Discipline: SW
- ASIL Rating: QM

### TFDCX32348-1723: Telltale Control (Heading)

#### TFDCX32348-3083: CAN Signal B_DAINDC Determination (Heading)

##### TFDCX32348-5447: No. Input Output System Status Intern... (System Requirement)
| No. | Input |  |  | Output |
| --- | --- | --- | --- | --- |
| No. | InternalSignal - IgnMode | CAN Signal Communication Status – B_DAINDC | Receive CAN Signal B_DAINDC | TT – Brake_Hold_Standby_Telltale |
| 1 | OFF | - | - | OFF |
| 2 | ON | Communication starting Never Received: 1 Communication Failure: 0 | x | OFF |
| 3 | ON | Communication establishment Never Received: 0 Communication Failure: 0 | 000b | OFF |
| 4 | ON | Communication establishment Never Received: 0 Communication Failure: 0 | 010b | ON |
| 5 | ON | Communication establishment Never Received: 0 Communication Failure: 0 | Other than above | OFF |
| 6 | ON | Communication abnormality Never Received: x Communication Failure: 1 | x | OFF |
Note:
Never Received and Communication Failure listed in CAN General SRD.
Please check the CAN General SRD for details.
- Verification Criteria: Verify by executing test cases
- Verification Method: System Qualification Test, Unit Test
- Verification Owner: FV, SW
- System Requirement State: Approved
- Primary Discipline: SW
- ASIL Rating: QM

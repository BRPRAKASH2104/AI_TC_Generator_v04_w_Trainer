# Json2ReqIF Transformation

# Specification: GAU_Boost pressure
- JDA Snapshot Date: 2025-09-04 02:41:07

## TFDCX32348-78543: GAU_Boost pressure (Heading)

## TFDCX32348-78544: History (Heading)

### TFDCX32348-78545: Table (Information)
| Version | Date | Name | Description of change | Baseline |
| --- | --- | --- | --- | --- |
| 0.1 | Mar/31/2025 | Hiromune Wachi | Newly create for 12.3inch FDC. [SYS-Story] : TFDCX32348-65538: [SYS][12.3FDC][R4][APP][Gauges] Boost gauge | BL_20250404_01 |
| 0.2 | Jul/3/2025 | Hiromune Wachi | ・Fixed a typo and changed the calculation of SurgeTankGaugePressure. ・Deleted “[B] Function presence/absence judgment” process block. [SYS-Story] : TFDCX32348-96197: [SYS][12.3FDC][R4][IMP][APP][Gauges] Boost gauge (changed by TFDCX32348-96194 and TFDCX32348-90688) | BL_20250710_01 |

## TFDCX32348-78546: Overview (Heading)

### TFDCX32348-78547: This SRD defines the requirements for Boost pressure. (Information)

## TFDCX32348-78548: Reference Document (Heading)

### TFDCX32348-78549: External Sources (Heading)

#### TFDCX32348-78550: MET-P_BSTPR-CSTD-1-00-A-C1 (Information)

## TFDCX32348-78551: Input Requirements (Heading)

### TFDCX32348-78555: InternalSignal - IgnMode (System Interface)
- System Requirement State: Approved

### TFDCX32348-78556: CANSignal - B_PINM (System Interface)
- System Requirement State: Approved

### TFDCX32348-78569: MCUCONST - MCUID1113 (System Interface)
- System Requirement State: Approved

### TFDCX32348-78570: MCUCONST - MCUID1114 (System Interface)
- System Requirement State: Approved

### TFDCX32348-78571: MCUCONST - MCUID1115 (System Interface)
- System Requirement State: Approved

### TFDCX32348-78572: MCUCONST - MCUID1116 (System Interface)
- System Requirement State: Approved

### TFDCX32348-78573: MCUCONST - MCUID1118 (System Interface)
- System Requirement State: Approved

### TFDCX32348-78574: MCUCONST - MCUID1121 (System Interface)
- System Requirement State: Approved

## TFDCX32348-78552: Output Requirements (Heading)

### TFDCX32348-78580: HMI - HMI_BOOST_PRESSURE_GAUGE (System Interface)
HMI - HMI_BOOST_PRESSURE_GAUGE
Range : 0[0.0%], 1[0.1%], ..., 1000[100.0%]
- System Requirement State: Approved

### TFDCX32348-78579: HMI - HMI_BSTPR_LOGO_MARK (System Interface)
HMI - HMI_BSTPR_LOGO_MARK
Range : 0[No display iForce logo mark], 1[Display iForce logo mark]
- System Requirement State: Approved

### TFDCX32348-78578 (System Interface)
InternalSignal - BoostPressureGauge_Prsnt
Range : 0[NOT_PRSNT], 1[PRSNT]
- System Requirement State: Approved

## TFDCX32348-78553: Performance Requirements (Heading)

### TFDCX32348-78581: General (Heading)

#### TFDCX32348-78583: Processing block structure (Heading)

##### TFDCX32348-78585: Figure (System Requirement)
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- Verification Criteria: Verify by design review
- Verification Method: Code/Design Review
- Verification Owner: SW
- System Requirement State: Approved
- Primary Discipline: SW
- ASIL Rating: QM

##### TFDCX32348-78586: Table (System Requirement)
| # | Signal name | Range |
| --- | --- | --- |
| ①-1 | SamplingUpdateFlag | 0[No update], 1[Updated] |
| ①-2 | B_PINM_In | -1[No data], 0h[-100.00000kPa], 1h[-99.84375‬kPa], ..., 280h[0.00000kPa], 281h[0.15625kPa], …, 780h[200.00000kPa] |
| ② | Average_B_PINM | -1[No data], 0h[-100.00000kPa], 1h[-99.84375‬kPa], ..., 280h[0.00000kPa], 281h[0.15625kPa], …, 780h[200.00000kPa] |
| ③ | Final_B_PINM | -1[No data], 0h[-100.00000kPa], 1h[-99.84375‬kPa], ..., 280h[0.00000kPa], 281h[0.15625kPa], …, 780h[200.00000kPa] |
- Verification Criteria: Verify by design review
- Verification Method: Code/Design Review
- Verification Owner: SW
- System Requirement State: Approved
- Primary Discipline: SW
- ASIL Rating: QM

#### TFDCX32348-78584: Parameters (Heading)

##### TFDCX32348-78590: Table - Parameters (System Requirement)
| # | Parameter name | Value |
| --- | --- | --- |
| 1 | 【Maximum value per unit】 | MCUID1113 x 10000 Note : Set the resolution to 0.001kPa (1Pa). |
| 2 | 【Minimum value per unit】 | MCUID1114 x 10000 Note : Set the resolution to 0.001kPa (1Pa). |
| 3 | 【S_TM】 | MCUID1115 Note : If MCUID1115 is greater than 10, replace it with 10. |
| 4 | 【N_AVE】 | MCUID1116 Note : If MCUID1116 is greater than 10, replace it with 10. |
- Verification Criteria: Verify by design review
- Verification Method: Code/Design Review
- Verification Owner: SW
- System Requirement State: Approved
- Primary Discipline: SW
- ASIL Rating: QM

### TFDCX32348-78582: Process (Heading)

#### TFDCX32348-78592: [A] Initialization (Heading)

##### TFDCX32348-78593: Table - Initialization (System Requirement)
| # | Name | Initilize @ Battery Connect | Initialize @ Module Wake-Up | IgnMode change from ON to OFF | Init Value | Remark |
| --- | --- | --- | --- | --- | --- | --- |
| 1 | HMI - HMI_BOOST_PRESSURE_GAUGE | 〇 | 〇 | 〇 | 0[0.0%] | Output signal of this module |
| 2 | HMI - HMI_BSTPR_LOGO_MARK | 〇 | 〇 | X | [*1] | Output signal of this module |
| 3 | InternalSignal - BoostPressureGauge_Prsnt | 〇 | 〇 | X | [*2] | Output signal of this module |
| 4 | SamplingTimingCnt (Range : 0, 1, ..., 9) | 〇 | 〇 | 〇 | 0 | Variable of [C] block |
| 5 | SamplingUpdateFlag | 〇 | 〇 | 〇 | 0[No update] | Output of [C] block |
| 6 | B_PINM_In | 〇 | 〇 | 〇 | -1[No data] | Output of [C] block |
| 7 | BufferIndex (Range : 0, 1, ..., 9) | 〇 | 〇 | 〇 | 0 | Variable of [D] block |
| 8 | BufferStatusFlag (Range : -1[No data], 0[Not full], 1[Full]) | 〇 | 〇 | 〇 | -1[No data] | Variable of [D] block |
| 9 | SampleBuffer[10] (Range of each data : -1[No data], 0h[-100.00000kPa], 1h[-99.84375‬kPa], ..., 280h[0.00000kPa], 281h[0.15625kPa], …, 780h[200.00000kPa]) | 〇 | 〇 | 〇 | Clear all data (Set -1[No data] to all data) | Variable of [D] block |
| 10 | Average_B_PINM | 〇 | 〇 | 〇 | -1[No data] | Output of [D] block |
| 11 | DivNum (Range : 1, 2, ..., 10) | 〇 | 〇 | 〇 | 1 | Variable of [E] block |
| 12 | Final_B_PINM | 〇 | 〇 | 〇 | -1[No data] | Output of [E] block |
| 13 | SurgeTankGaugePressure (Range : -100000[-100.000kPa], -99999[-99.999kPa], ..., 200000[200.000kPa]) | 〇 | 〇 | 〇 | -100000[-100.000kPa] | Variable of [F] block |
[*1] : Follow the table below.
| # | Input | Output |
| --- | --- | --- |
| # | MCUID1121 | HMI - HMI_BSTPR_LOGO_MARK |
| 1 | 1[boost gauge logo present] | 1[Display iForce logo mark] |
| 2 | 3[boost gauge/MG gauge logo present] | 1[Display iForce logo mark] |
| 3 | Other than above | 0[No display iForce logo mark] |
[*2] : Follow the table below.
| # | Input | Output |
| --- | --- | --- |
| # | MCUID1118 | InternalSignal - BoostPressureGauge_Prsnt |
| 1 | 1[boost pressure function present] | 1[PRSNT] |
| 2 | Other than above | 0[NOT_PRSNT] |
- Verification Criteria: Verify by executing test cases
- Verification Method: System Qualification Test, Unit Test
- Verification Owner: FV, SW
- System Requirement State: Approved
- Primary Discipline: SW
- ASIL Rating: QM

#### TFDCX32348-78598: [B] Function presence/absence judgment (Heading)
- System Requirement State: Rejected

##### TFDCX32348-78599: Table - BoostPressureGauge_Prsnt (System Requirement)
Table - BoostPressureGauge_Prsnt
| # | Input |  | Output |
| --- | --- | --- | --- |
| # | IgnMode | MCUID1118 | InternalSignal - BoostPressureGauge_Prsnt |
| 1 | OFF → ON | 1[boost pressure function present] | 1[PRSNT] |
| 2 | OFF → ON | Other than above | 0[NOT_PRSNT] |
| 3 | Other than above |  | No change |
- System Requirement State: Rejected

##### TFDCX32348-78600: Table - HMI_BSTPR_LOGO_MARK (System Requirement)
Table - HMI_BSTPR_LOGO_MARK
| # | Input |  | Output |
| --- | --- | --- | --- |
| # | IgnMode | MCUID1121 | HMI - HMI_BSTPR_LOGO_MARK |
| 1 | OFF → ON | 1[boost gauge logo present] | 1[Display iForce logo mark] |
| 2 | OFF → ON | 3[boost gauge/MG gauge logo present] | 1[Display iForce logo mark] |
| 3 | OFF → ON | Other than above | 0[No display iForce logo mark] |
| 4 | Other than above |  | No change |
- System Requirement State: Rejected

#### TFDCX32348-78601: Main operation (Heading)

##### TFDCX32348-78602 (System Requirement)
Each block of the main operation shall be executed when all of the following conditions are met.
- BoostPressureGauge_Prsnt == 1[PRSNT]
- IgnMode == ON
- 【S_TM】 != 0[0msec]
- 【N_AVE】 != 0[0times]
If any of the above conditions are not met, set the HMI_BOOST_PRESSURE_GAUGE as follows:
- HMI_BOOST_PRESSURE_GAUGE = 0[0.0%]
- Verification Criteria: Verify by executing test cases
- Verification Method: System Qualification Test, Unit Test
- Verification Owner: FV, SW
- System Requirement State: Approved
- Primary Discipline: SW
- ASIL Rating: QM

##### TFDCX32348-78611: [B] Sampling process (Heading)

###### TFDCX32348-78612: Table - Sampling process (System Requirement)
| # | Input |  |  | Output |  |  |
| --- | --- | --- | --- | --- | --- | --- |
| # | SamplingTimingCnt | CAN Signal Communication Status - B_PINM | B_PINM | B_PINM_In | SamplingUpdateFlag | SamplingTimingCnt |
| 1 | 0 | Never received (Never Received: 1 Communication Failure: 0) OR Communication failure (Never Received: x Communication Failure: 1) | X | -1[No data] | 1[Updated] | 0 |
| 2 | 0 | Normal (Never Received: 0 Communication Failure: 0) | B_PINM ≦ 780h | CANSignal - B_PINM | 1[Updated] | [*1] |
| 3 | 0 | Normal (Never Received: 0 Communication Failure: 0) | B_PINM > 780h | No Change | 0[No update] | [*1] |
| 4 | Other than 0 | Never received (Never Received: 1 Communication Failure: 0) OR Communication failure (Never Received: x Communication Failure: 1) | X | -1[No data] | 1[Updated] | 0 |
| 5 | Other than 0 | Normal (Never Received: 0 Communication Failure: 0) | X | No change | 0[No update] | [*1] |
[*1] : Set according to the table below.
| # | Input | Output |
| --- | --- | --- |
| # | SamplingTimingCnt | SamplingTimingCnt |
| 1 | SamplingTimingCnt <（【S_TM】 - 1) | Increment by 1 |
| 2 | (【S_TM】 - 1) ≦ SamplingTimingCnt | 0 |
- Verification Criteria: Verify by executing test cases
- Verification Method: System Qualification Test, Unit Test
- Verification Owner: FV, SW
- System Requirement State: Approved
- Primary Discipline: SW
- ASIL Rating: QM

##### TFDCX32348-78617: [C] Averaging process (Heading)

###### TFDCX32348-78618: Table - Averaging process (System Requirement)
| # | Input |  |  |  | Output |  |  |
| --- | --- | --- | --- | --- | --- | --- | --- |
| # | SamplingUpdateFlag | B_PINM_In | BufferIndex | BufferStatusFlag | SampleBuffer[] | BufferIndex [*1] | BufferStatusFlag |
| 1 | 1[Updated] | -1[No data] | X | X | Clear all data (Set -1[No data] to all data) | 0 | -1[No data] |
| 2 | 1[Updated] | Other than -1[No data] | BufferIndex >=(【N_AVE】 - 1) | X | Store B_PINM_In value in SampleBuffer[【N_AVE】 - 1] | 0 | 1[Full] |
| 3 | 1[Updated] | Other than -1[No data] | BufferIndex < (【N_AVE】 - 1) | 1[Full] | Store B_PINM_In value in SampleBuffer[BufferIndex] | Increment by 1 | No change |
| 4 | 1[Updated] | Other than -1[No data] | BufferIndex < (【N_AVE】 - 1) | Other than 1[Full] | Store B_PINM_In value in SampleBuffer[BufferIndex] | Increment by 1 | 0[Not full] |
| 5 | Other than above |  |  |  | No change | No change | No change |
[*1] : Update BufferIndex after updating SampleBuffer.
- Verification Criteria: Verify by executing test cases
- Verification Method: System Qualification Test, Unit Test
- Verification Owner: FV, SW
- System Requirement State: Approved
- Primary Discipline: SW
- ASIL Rating: QM

###### TFDCX32348-78619: Calculation of average data (System Requirement)
Cluster shall calculate the averaged data according to the following calculation:
Case of “BufferStatusFlag == -1[No data]“
Average_B_PINM = -1[No data]
Case of “BufferStatusFlag == 0[Not full]“
Average_B_PINM = Round{(“Sum of SampleBuffer[0] to SampleBuffer[BufferIndex - 1]” / BufferIndex), 0}
Case of “BufferStatusFlag == 1[Full]“
Average_B_PINM = Round{(“Sum of SampleBuffer[0] to SampleBuffer[【N_AVE】 - 1]” / 【N_AVE】), 0}
- Verification Criteria: Verify by executing test cases
- Verification Method: System Qualification Test, Unit Test
- Verification Owner: FV, SW
- System Requirement State: Approved
- Primary Discipline: SW
- ASIL Rating: QM

##### TFDCX32348-78620: [D] Gradual change processing (Heading)

###### TFDCX32348-78621: Table - Gradual change processing (System Requirement)
| ＃ | Input |  |  | Output |  |
| --- | --- | --- | --- | --- | --- |
| ＃ | SamplingUpdateFlag | Average_B_PINM | DivNum | DivNum | Final_B_PINM [*2] |
| 1 | 1[Updated] | -1[No data] | X | 1 | -1[No data] |
| 2 | 1[Updated] | Other than -1[No data] | X | 【S_TM】 | Final_B_PINM[*1] + Round{((Average_B_PINM-Final_B_PINM[*1]) / DivNum), 0} |
| 3 | Other than 1[Updated] | -1[No data] | X | 1 | -1[No data] |
| 4 | Other than 1[Updated] | Other than -1[No data] | 1 | No change | No change |
| 5 | Other than 1[Updated] | Other than -1[No data] | DivNum > 1 | Decrement by 1 | Final_B_PINM[*1] + Round{((Average_B_PINM-Final_B_PINM[*1]) / DivNum), 0} |
[*1] : The previous value of Final_B_PINM.
[*2] : This column is performed after updating DivNum.
- Verification Criteria: Verify by executing test cases
- Verification Method: System Qualification Test, Unit Test
- Verification Owner: FV, SW
- System Requirement State: Approved
- Primary Discipline: SW
- ASIL Rating: QM

##### TFDCX32348-78622: [E] Update display data (Heading)

###### TFDCX32348-78623 (System Requirement)
Cluster shall calculate output data for each of the following conditions.
Case of “Final_B_PINM == -1[No data]“:
HMI_BOOST_PRESSURE_GAUGE = 0[0.0%]
Case of “Final_B_PINM != -1[No data]“:
Step1
SurgeTankGaugePressure = -100000 + {(Final_B_PINM Final_B_POM x 15625) + 50} / 100
Note : Set the resolution to 0.001kPa (1Pa)
Step2
Cluster shall calculate HMI_BOOST_PRESSURE_GAUGE according to the table below.
| # | Input | Output | Remarks |
| --- | --- | --- | --- |
| # | SurgeTankGaugePressure [a] | HMI_BOOST_PRESSURE_GAUGE | Remarks |
| 1 | [a] ≦【Minimum value per unit】 | 0[0.0%] | - |
| 2 | 【Minimum value per unit】< [a] < 【Maximum value per unit】 | {10000[100.00%] x ([a] -【Minimum value per unit】) / (【Maximum value per unit】-【Minimum value per unit】) + 5} / 10 Note : The above calculation results in a resolution of "0.1%". | Calculate with interpolation method |
| 3 | 【Maximum value per unit】≦ [a] | 1000[100.0%] | - |
- Verification Criteria: Verify by executing test cases
- Verification Method: System Qualification Test, Unit Test
- Verification Owner: FV, SW
- System Requirement State: Approved
- Primary Discipline: SW
- ASIL Rating: QM

# Json2ReqIF Transformation

# Specification: DIAG_ETM_Buzzer beep
- JDA Snapshot Date: 2025-09-04 02:39:45

## TFDCX32348-10564: DIAG_ETM_Buzzer beep (Heading)
Buzzer beep
- System Requirement State: Draft
- Primary Discipline: TBD
- ASIL Rating: TBD

## TFDCX32348-10566: History (Heading)
- System Requirement State: Draft
- Primary Discipline: TBD
- ASIL Rating: TBD

### TFDCX32348-12472: Version Date Description of change SR... (Information)
| Version | Date | Name | Description of change | SRD Baseline |
| --- | --- | --- | --- | --- |
| 0.1 | 2024/04/09 | Takeshi Yamane | New created TFDCX32348-23231 [SYS][12.3FDC][APP] ETM | BL_20240521_01 |
| 0.2 | 2024/09/26 | Mathieu Lenoble | Update of the button to navigate through the buzzer. TFDCX32348-41765: [SYS][12.3FDC][APP][ETM] Update of the steps to enter in ETM | BL_20241018_01 |
| 0.3 | 2025/04/18 | Mathieu Lenoble | Clarification added regarding the screen rendering when the buzzers are played. This is to align to the implementation hence no story required. TFDCX32348-12484: This function control the Buzzer chec... |  |
| 0.4 | 2025/07/18 | Baviskar Tejaswini | Added Toyota and Lexus Reverse Buzzers in ETM. TFDCX32348-98279: [SYS][12.3FDC][APP][ETM] Add TT Illum Image and Reverse Buzzer in ETM | BL_20250721_01 |
- System Requirement State: Draft
- Primary Discipline: TBD
- ASIL Rating: TBD

## TFDCX32348-10568: Overview (Heading)
- System Requirement State: Draft
- Primary Discipline: TBD
- ASIL Rating: TBD

### TFDCX32348-12474: This SRD defines the requirement for ... (Information)
This SRD defines the requirement for Buzzer beep functionality.
This Function is executed only in ETM mode or when Diag request receive.
- System Requirement State: Draft
- Primary Discipline: TBD
- ASIL Rating: TBD

## TFDCX32348-10570: Input Requirements (Heading)
- System Requirement State: Draft
- Primary Discipline: TBD
- ASIL Rating: TBD

### TFDCX32348-12476: Switch Input (Heading)
- System Requirement State: Draft
- Primary Discipline: TBD
- ASIL Rating: TBD

#### TFDCX32348-17162: H/W DI - ODO_TripKnobInput (System Interface)
- Verification Criteria: Verify by design review
- Verification Method: TBD
- Verification Owner: SW
- System Requirement State: Approved
- Secondary Disciplines: TBD
- ASIL Rating: QM

### TFDCX32348-12480: Internal I/F (Heading)
- System Requirement State: Draft
- Primary Discipline: TBD
- ASIL Rating: TBD

#### TFDCX32348-17167: InternalSignal - IgnMode (System Interface)
- Verification Criteria: Verify by design review
- Verification Method: TBD
- Verification Owner: SW
- System Requirement State: Approved
- Secondary Disciplines: TBD
- ASIL Rating: QM

## TFDCX32348-10572: Output Requirements (Heading)
- System Requirement State: Draft
- Primary Discipline: TBD
- ASIL Rating: TBD

### TFDCX32348-12482: Buzzer (Heading)
- System Requirement State: Draft
- Primary Discipline: TBD
- ASIL Rating: TBD

#### TFDCX32348-17169: InternalSignal - BuzzerTest_Door_Ajar (System Interface)
- Verification Criteria: Verify by design review
- Verification Method: TBD
- Verification Owner: SW
- System Requirement State: Approved
- Secondary Disciplines: TBD
- ASIL Rating: QM

#### TFDCX32348-17171: InternalSignal - BuzzerTest_SBR (System Interface)
- Verification Method: TBD
- Verification Owner: SW
- System Requirement State: Approved
- Secondary Disciplines: TBD
- ASIL Rating: QM

#### TFDCX32348-17173: InternalSignal - BuzzerTest_CLESON (System Interface)
- Verification Method: TBD
- Verification Owner: SW
- System Requirement State: Approved
- Secondary Disciplines: TBD
- ASIL Rating: QM

#### TFDCX32348-98141 (System Interface)
InternalSignal - BuzzerTest_Toyota_Rev_Sound
Discription: Reverse Buzzer sound for Toyota Vehicle
- Verification Method: TBD
- Verification Owner: SW
- System Requirement State: Approved
- Secondary Disciplines: TBD
- ASIL Rating: QM

#### TFDCX32348-98143 (System Interface)
InternalSignal - BuzzerTest_Lexus_Rev_Sound
Discription: Reverse Buzzer sound for Lexus Vehicle
Note: Use “MET-LBZ_REVERSE-INT-24-01-A.wav” file for Buzzer Output.(Refer )
- Verification Method: TBD
- Verification Owner: SW
- System Requirement State: Approved
- Secondary Disciplines: TBD
- ASIL Rating: QM

## TFDCX32348-10574: Performance Requirements (Heading)
- System Requirement State: Draft
- Primary Discipline: TBD
- ASIL Rating: TBD

### TFDCX32348-12484: This function control the Buzzer chec... (System Requirement)
This function control the Buzzer check.
This function change the sound pattern by pressing the ODO button on the test box.
For each buzzer played the screen shall be black and show in the middle of the screen the name of the buzzer that is currently played.
- Verification Criteria: Verify by executing test cases
- Verification Method: Functional Verification / Validation
- Verification Owner: FV
- System Requirement State: Draft
- Secondary Disciplines: FV, SW
- Primary Discipline: SW
- ASIL Rating: QM

### TFDCX32348-12486: Figure - Buzzer Check Process Flow (Heading)
- System Requirement State: Draft
- Primary Discipline: TBD
- ASIL Rating: TBD

#### TFDCX32348-17175: Buzzer Flow (System Requirement)
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- Verification Criteria: Verify by executing test cases
- Verification Method: Functional Verification / Validation
- Verification Owner: FV
- System Requirement State: Approved
- Primary Discipline: SW
- ASIL Rating: QM

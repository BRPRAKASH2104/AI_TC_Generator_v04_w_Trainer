# Json2ReqIF Transformation

# Specification: TT_Factory mode (forward radar)
- JDA Snapshot Date: 2025-10-29 07:16:44

## TFDCX32348-46539: TT_Factory mode (forward radar) (Heading)

## TFDCX32348-46550: History (Heading)

### TFDCX32348-46552: Version (Information)
| Version | Date | Name | Description of change | Baseline |
| --- | --- | --- | --- | --- |
| 0.1 | 11/Oct/2024 | Takuya Tamura | Newly Create [SYS-Task] TFDCX32348-34193: [SYS][12.3FDC][APP][Telltale] Factory mode (forward radar) | BL_20241029_01 |

## TFDCX32348-46554: Reference Document (Heading)

### TFDCX32348-46753: MET-S_FRADAR-CSTD-A0-01-A-C0.xlsm (Information)
MET-S_FRADAR-CSTD-A0-01-A-C0.xlsm
(DMS(In))MET-M_FRADAR-CSTD-A0-01-A-C0.xlsx

## TFDCX32348-46556: Overview (Heading)

### TFDCX32348-46578: This SRD defines (Information)
This SRD defines Telltale of Factory mode (forward radar).

## TFDCX32348-46558: Input Requirements (Heading)

### TFDCX32348-46741: InternalSignal – IgnMode (System Interface)

### TFDCX32348-46754: CAN Signal – FRD_PLRQ(Message Label: ADU1S07) (System Interface)

## TFDCX32348-46561: Output Requirements (Heading)

### TFDCX32348-46755 (System Interface)
HMI - Factory_mode_forward_radar_Telltale
Range: {OFF, AMBER_Blinking}

## TFDCX32348-46562: Performance Requirements (Heading)

### TFDCX32348-46565: Display Symbol (Heading)

#### TFDCX32348-46747: Factory mode Symbol (Information)
1. Display Symbol
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2. Display Color : AMBER

### TFDCX32348-46568: Bulb Check (Heading)

#### TFDCX32348-46573: None (System Requirement)
- ASIL Rating: QM

### TFDCX32348-46571: Telltale Control (Heading)

#### TFDCX32348-49303: Logic Table (Heading)

##### TFDCX32348-46756: # (System Requirement)
| # | Input |  |  | Output |
| --- | --- | --- | --- | --- |
| # | InternalSignal - IgnMode | CAN communication States - FRD_PLRQ | CAN Signal - FRD_PLRQ | HMI - Factory_mode_forward_radar_Telltale |
| 1 | (Initialization at CPU reset or wakeup) |  |  | OFF |
| 2 | OFF | x | x | OFF |
| 3 | ON | Communication starting Never Received: 1 Communication Failure: 0 | x | OFF |
| 4 | ON | Communication establishment Never Received: 0 Communication Failure: 0 | 1b | AMBER_Blinking |
| 5 | ON | Communication establishment Never Received: 0 Communication Failure: 0 | other than above | OFF |
| 6 | ON | Communication abnormality Never Received: x Communication Failure: 1 | x | no change |
Note: It shall be displayed exclusively with TT, which is displayed only while running, and no special requirements regarding layout are made.
- Verification Criteria: Verify by executing test cases
- Verification Method: System Qualification Test, Unit Test
- Verification Owner: FV, SW
- System Requirement State: Approved
- Primary Discipline: SW
- ASIL Rating: QM

#### TFDCX32348-46750: Blinking Control (Heading)

##### TFDCX32348-46757: Blinking Control (System Requirement)
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- Verification Criteria: Verify by executing test cases
- Verification Method: System Qualification Test, Unit Test
- Verification Owner: FV, SW
- System Requirement State: Approved
- Primary Discipline: SW
- ASIL Rating: QM

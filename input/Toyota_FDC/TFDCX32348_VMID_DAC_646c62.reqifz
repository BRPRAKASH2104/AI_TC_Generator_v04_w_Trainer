# Json2ReqIF Transformation

# Specification: VMID_DAC
- JDA Snapshot Date: 2025-09-09 09:13:46

## TFDCX32348-83142: VMID_DAC (Heading)

## TFDCX32348-83143: History (Heading)

### TFDCX32348-83144: Table - Version history (Information)
| Version | Date | Name | Description of change | Baseline |
| --- | --- | --- | --- | --- |
| 0.1 | 6/May/2025 | Kubo, Masaki | Newly create TFDCX32348-81877: [SYS][12.3FDC][R5][APP][VMID] DAC | BL_20250627_01 |

## TFDCX32348-83145: Reference Document (Heading)

### TFDCX32348-83146: MET-C_DAC-CSTD-A0-05-A-C1.xlsm (Information)
MET-C_DAC-CSTD-A0-05-A-C1.xlsm
DMS_MET-C_DAC-CSTD-A0-05-A-C1.xlsx

## TFDCX32348-83147: Overview (Heading)

### TFDCX32348-83148: This SRD defines DAC for VMID. (Information)

## TFDCX32348-83149: Input Requirements (Heading)

### TFDCX32348-83150: InternalSignal – IgnMode (System Interface)
- Verification Criteria: Verify by design review
- Verification Method: Code/Design Review
- Verification Owner: SW
- System Requirement State: Approved
- Primary Discipline: SW
- ASIL Rating: QM

### TFDCX32348-83151: CANSignal - B_DACIND (Message Label: VSC1S95) (System Interface)
- Verification Criteria: Verify by design review
- Verification Method: Code/Design Review
- Verification Owner: SW
- System Requirement State: Approved
- Primary Discipline: SW
- ASIL Rating: QM

### TFDCX32348-83156: MCUCONST - MCUID0025 (System Interface)
- Verification Criteria: Verify by design review
- Verification Method: Code/Design Review
- Verification Owner: SW
- System Requirement State: Approved
- Primary Discipline: SW
- ASIL Rating: QM

### TFDCX32348-103645: warningID - WRN_NORM_DRIMOD_03 (System Interface)
- Verification Criteria: Verify by design review
- Verification Method: Code/Design Review
- Verification Owner: SW
- System Requirement State: Approved
- Primary Discipline: SW
- ASIL Rating: QM

### TFDCX32348-103646: warningID - WRN_NORM_DRIMOD_04 (System Interface)
- Verification Criteria: Verify by design review
- Verification Method: Code/Design Review
- Verification Owner: SW
- System Requirement State: Approved
- Primary Discipline: SW
- ASIL Rating: QM

### TFDCX32348-103647: warningID - WRN_NORM_DRIMOD_05 (System Interface)
- Verification Criteria: Verify by design review
- Verification Method: Code/Design Review
- Verification Owner: SW
- System Requirement State: Approved
- Primary Discipline: SW
- ASIL Rating: QM

### TFDCX32348-103648: warningID - WRN_NORM_THMMOD_03 (System Interface)
- Verification Criteria: Verify by design review
- Verification Method: Code/Design Review
- Verification Owner: SW
- System Requirement State: Approved
- Primary Discipline: SW
- ASIL Rating: QM

### TFDCX32348-103649: warningID - WRN_NORM_THMMOD_04 (System Interface)
- Verification Criteria: Verify by design review
- Verification Method: Code/Design Review
- Verification Owner: SW
- System Requirement State: Approved
- Primary Discipline: SW
- ASIL Rating: QM

## TFDCX32348-83157: Output Requirements (Heading)

### TFDCX32348-83158: HMI - HMI_DAC_DISPLAY (System Interface)
HMI - HMI_DAC_DISPLAY
Meaning: This parameter indicates the DAC display.
Range: 0(OFF), 1(ON)
- Verification Criteria: Verify by design review
- Verification Method: Code/Design Review
- Verification Owner: SW
- System Requirement State: Approved
- Primary Discipline: SW
- ASIL Rating: QM

### TFDCX32348-83162: warningID - WRN_NORM_DAC_V03 (System Interface)
warningID - WRN_NORM_DAC_V03
Range: (OFF, ON)
- Verification Criteria: Verify by design review
- Verification Method: Code/Design Review
- Verification Owner: SW
- System Requirement State: Approved
- Primary Discipline: SW
- ASIL Rating: QM

## TFDCX32348-83166: Performance Requirements (Heading)

### TFDCX32348-83167: Screen Configuration (Heading)

#### TFDCX32348-83168: Information (Information)
DAC operating
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
### TFDCX32348-83169: Display Control (Heading)

#### TFDCX32348-83170: Control of display the DAC condition (Heading)

##### TFDCX32348-83171: Table - Judgment the DAC display (System Requirement)
| # | Input |  |  |  |  | Output |  |
| --- | --- | --- | --- | --- | --- | --- | --- |
| # | MCUCONST - MCUID0025 | Warning ID | InternalSignal-IgnMode | CAN Signal Communication Status – B_DACIND | CAN Signal Value–B_DACIND | HMI - HMI_DAC_DISPLAY | WRN_NORM_DAC_V03 |
| 1 | Other than "2:GR or 3:GRMN" | Other than " "WRN_NORM_DRIMOD_03 = ON1 or ON2" or “WRN_NORM_DRIMOD_04 = ON1 or ON2" or “WRN_NORM_DRIMOD_05 = ON1 or ON2" or "WRN_NORM_THMMOD_03 = ON1 or ON2" or "WRN_NORM_THMMOD_04 = ON1 or ON2" " | OFF | X | X | OFF | OFF |
| 2 | Other than "2:GR or 3:GRMN" | Other than " "WRN_NORM_DRIMOD_03 = ON1 or ON2" or “WRN_NORM_DRIMOD_04 = ON1 or ON2" or “WRN_NORM_DRIMOD_05 = ON1 or ON2" or "WRN_NORM_THMMOD_03 = ON1 or ON2" or "WRN_NORM_THMMOD_04 = ON1 or ON2" " | ON | Communication starting Never Received: 1 Communication Failure: 0 | X | OFF | OFF |
| 3 | Other than "2:GR or 3:GRMN" | Other than " "WRN_NORM_DRIMOD_03 = ON1 or ON2" or “WRN_NORM_DRIMOD_04 = ON1 or ON2" or “WRN_NORM_DRIMOD_05 = ON1 or ON2" or "WRN_NORM_THMMOD_03 = ON1 or ON2" or "WRN_NORM_THMMOD_04 = ON1 or ON2" " | ON | Communication starting Never Received: X Communication Failure: 1 | X | OFF | OFF |
| 4 | Other than "2:GR or 3:GRMN" | Other than " "WRN_NORM_DRIMOD_03 = ON1 or ON2" or “WRN_NORM_DRIMOD_04 = ON1 or ON2" or “WRN_NORM_DRIMOD_05 = ON1 or ON2" or "WRN_NORM_THMMOD_03 = ON1 or ON2" or "WRN_NORM_THMMOD_04 = ON1 or ON2" " | ON | Communication starting Never Received: 0 Communication Failure: 0 | 00b to 11b | ON | ON1 |
| 5 | Other than "2:GR or 3:GRMN" | Other than " "WRN_NORM_DRIMOD_03 = ON1 or ON2" or “WRN_NORM_DRIMOD_04 = ON1 or ON2" or “WRN_NORM_DRIMOD_05 = ON1 or ON2" or "WRN_NORM_THMMOD_03 = ON1 or ON2" or "WRN_NORM_THMMOD_04 = ON1 or ON2" " | ON | Communication starting Never Received: 0 Communication Failure: 0 | 11b | No change | No change |
| 6 | Other than "2:GR or 3:GRMN" | Other than " "WRN_NORM_DRIMOD_03 = ON1 or ON2" or “WRN_NORM_DRIMOD_04 = ON1 or ON2" or “WRN_NORM_DRIMOD_05 = ON1 or ON2" or "WRN_NORM_THMMOD_03 = ON1 or ON2" or "WRN_NORM_THMMOD_04 = ON1 or ON2" " | ON | Communication starting Never Received: 0 Communication Failure: 0 | Other than 00b to 00b | OFF | OFF |
| 7 | Other than "2:GR or 3:GRMN" | Other than " "WRN_NORM_DRIMOD_03 = ON1 or ON2" or “WRN_NORM_DRIMOD_04 = ON1 or ON2" or “WRN_NORM_DRIMOD_05 = ON1 or ON2" or "WRN_NORM_THMMOD_03 = ON1 or ON2" or "WRN_NORM_THMMOD_04 = ON1 or ON2" " | ON | Communication starting Never Received: 0 Communication Failure: 0 | Other than above | OFF | OFF |
| 8 | Other than "2:GR or 3:GRMN" | "WRN_NORM_DRIMOD_03 = ON1 or ON2" or “WRN_NORM_DRIMOD_04 = ON1 or ON2" or “WRN_NORM_DRIMOD_05 = ON1 or ON2" or "WRN_NORM_THMMOD_03 = ON1 or ON2" or “WRN_NORM_THMMOD_04 = ON1 or ON2" | X | X | X | OFF | OFF |
| 9 | Other than above |  |  |  |  | OFF | OFF |
- Verification Criteria: Verify by design review Verify all of conditions in the table (need fault injection)
- Verification Method: Code/Design Review, System Qualification Test, Unit Test
- Verification Owner: FV, SW
- System Requirement State: Approved
- Primary Discipline: SW
- ASIL Rating: QM

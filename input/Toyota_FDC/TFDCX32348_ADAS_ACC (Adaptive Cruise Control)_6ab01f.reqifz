# Json2ReqIF Transformation

# Specification: ADAS_ACC (Adaptive Cruise Control)
- JDA Snapshot Date: 2025-10-24 08:14:42

## TFDCX32348-8484: ADAS_ACC (Adaptive Cruise Control) (Heading)

## TFDCX32348-8485: History (Heading)

### TFDCX32348-10441: History Table (Information)
| Version | Date | Name | Description of change | SRD Baseline |
| --- | --- | --- | --- | --- |
| v0.1 | Jul/19/2024 | Kazuya Nagata | Newly create TFDCX32348-25358: [SYS][12.3FDC][APP][ADAS] ACC | BL_20240725_01 |
| V1.0 | Feb/02/14 | Kazuya Nagata | TFDCX32348-65540 :[SYS][12.3FDC][R4][APP][ADAS] ACC 1. Changed 00b and 11b behavior from OFF to White color display (TFDCX32348-28152, TFDCX32348-18153, TFDCX32348-32225) 2. Added new CAN signal and changed 01b and 10b behavior from OFF to White color display (TFDCX32348-32293) 3, Changed WRN_ADAS_ACC_G20 behavior (The same requirements as for HMI_ACC_PRECEDING_VEHICLE_BLINK are applied.) (TFDCX32348-28190) 4. Changed WRN_ADAS_ACC_G22 behavior (The same requirements as for HMI_ACC_ADJACENT_VEHICLE_BLINK_RIGHT are applied.) (TFDCX32348-28230) 5. Changed WRN_ADAS_ACC_G23 behavior (The same requirements as for HMI_ACC_ADJACENT_VEHICLE_BLINK_LEFT are applied.) (TFDCX32348-32339) 6. Fixed parameter names due to typo (TFDCX32348-33984, TFDCX32348-33992, TFDCX32348-13954, TFDCX32348-13956, TFDCX32348-28230, TFDCX32348-32336, TFDCX32348-32339) | BL_20250228_01 |
| V1.1 | Jul/07/04 | Kazuya Nagata | TFDCX32348-95794: [SYS][12.3FDC][TOYOTA_REVIEW][APP][ADAS] ADAS ACC - Remove NVM_ACCExistFlag in Logic Tables 1. Remove NVM_ACCExistFlag in Logic Tables (TFDCX32348-10512, TFDCX32348-10512, TFDCX32348-32225, TFDCX32348-18155, TFDCX32348-32660, TFDCX32348-18156, TFDCX32348-18121, TFDCX32348-18009, TFDCX32348-18136, TFDCX32348-18138, TFDCX32348-18007, TFDCX32348-18011, TFDCX32348-18015, TFDCX32348-32293, TFDCX32348-20796, TFDCX32348-20798, TFDCX32348-20800, TFDCX32348-20802, TFDCX32348-28205, TFDCX32348-28212, TFDCX32348-28214, TFDCX32348-28217, TFDCX32348-28210, TFDCX32348-32333, TFDCX32348-32334, TFDCX32348-32335, TFDCX32348-32336, TFDCX32348-32337) 2. Typo correction (TFDCX32348-32660, TFDCX32348-20798) | BL_20250711_01 |

## TFDCX32348-8486: Reference Document (Heading)

### TFDCX32348-29124: External Resource (Heading)

#### TFDCX32348-10444: Customer Spec (Information)
MET-S_ACC-CSTD-2-05-A-C0.xlsm
MET-S_ACC-CSTD-2-05-A-C0_Appendix.docx
MET-S_ACC-CSTD-2-05-A-C0_Appendix2.xlsx
MET-M_DEFINE-CSTD-0-13-A-C0.xlsx

### TFDCX32348-29125: Internal Resource (Heading)

#### TFDCX32348-29126: Related SRDs (Information)
| # | Category | Name |
| --- | --- | --- |
| 1 | Application | ADAS_CACC (Cooperative Adaptive Cruise Control) |
| 2 | Application | ADAS_ERM (Eco Run Mode) |
| 3 | Application | ADAS_Set_Speed |
| 4 | Application | ADAS_SET/MAX_Mark |
| 5 | GUI | GUI_Right_Content_ADAS |
| 6 | GUI | GUI_ADAS_Interrupt |
| 7 | GUI | GUI_CCSET |

## TFDCX32348-8488: Overview (Heading)

### TFDCX32348-10446: This SRD defines the requirements fo... (Information)
This SRD defines the requirements for Dynamic Radar Cruise Control Feature in Instrument Cluster.

### TFDCX32348-10448: Dynamic radar cruise control suppleme... (Information)
Dynamic radar cruise control supplements conventional cruise control with a vehicle-to-vehicle distance control. In vehicle-to-vehicle distance control mode, the vehicle automatically accelerates or decelerates in order to maintain a set following distance from vehicles ahead.

## TFDCX32348-8489: Input Requirements (Heading)

### TFDCX32348-32197: Internal Signals (Heading)

#### TFDCX32348-10450: InternalSignal - IgnMode (System Interface)

#### TFDCX32348-10512: NVM - NVM_ACCExistFlag (Dropped) (System Interface)
- Verification Criteria: Verify design review

### TFDCX32348-32198: CAN Signals (Heading)

#### TFDCX32348-10455: CANSignal - ACCSP (System Interface)
CANSignal - ACCSP (Message Label: FCM1S39)

#### TFDCX32348-10457: CANSignal - ACCSPST1 (System Interface)
CANSignal - ACCSPST1 (Message Label: FCM1S39)

#### TFDCX32348-10459: CANSignal - ACCSPEXC (System Interface)
CANSignal - ACCSPEXC (Message Label: FCM1S39)

#### TFDCX32348-10461: CANSignal - ACCSPU (System Interface)
CANSignal - ACCSPU (Message Label: FCM1S39)

#### TFDCX32348-10463: CANSignal - ACCSUST1 (System Interface)
CANSignal - ACCSUST1 (Message Label: FCM1S39)

#### TFDCX32348-10467: CANSignal - ACCPVST3 (System Interface)
CANSignal - ACCPVST3 (Message Label: ADU1S07)

#### TFDCX32348-10477: CANSignal – ACCDST (System Interface)
CANSignal – ACCDST (Message Label: FCM1S39)

#### TFDCX32348-10479: CANSignal - ACCDTST1 (System Interface)
CANSignal - ACCDTST1 (Message Label: FCM1S39)

#### TFDCX32348-10482: CANSignal - ACCDTST2 (System Interface)
CANSignal - ACCDTST2 (Message Label: FCM1S39)

#### TFDCX32348-10484: CANSignal - ACCCNTOB (System Interface)
CANSignal - ACCCNTOB (Message Label: FCM1S40)

#### TFDCX32348-10486: CANSignal - ACCMSG2 (System Interface)
CANSignal - ACCMSG2 (Message Label: FCM1S40)

#### TFDCX32348-10488: CANSignal - ACCMSG4 (System Interface)
CANSignal - ACCMSG4 (Message Label: FCM1S40)

#### TFDCX32348-10491: CANSignal - ACCMSGV (System Interface)
CANSignal - ACCMSGV (Message Label: FCM1S40)

#### TFDCX32348-10493: CANSignal - ACCMSGU (System Interface)
CANSignal - ACCMSGU (Message Label: FCM1S40)

#### TFDCX32348-10495: CANSignal - ACCRSAC (System Interface)
CANSignal - ACCRSAC (Message Label: FCM1S41)

#### TFDCX32348-10498: CANSignal - ACCRSACB (System Interface)
CANSignal - ACCRSACB (Message Label: FCM1S41)

#### TFDCX32348-10500: CANSignal - ACCSSAG (System Interface)
CANSignal - ACCSSAG (Message Label: FCM1S41)

#### TFDCX32348-10501: CANSignal - ACCSSAGB (System Interface)
CANSignal - ACCSSAGB (Message Label: FCM1S41)

#### TFDCX32348-28007: CANSignal - ACCPVTY (System Interface)
CANSignal - ACCPVTY (Message Label: ADU1S07)

#### TFDCX32348-10475: CANSignal - ACCPVDST (System Interface)
CANSignal - ACCPVDST (Message Label: ADU1S07)

#### TFDCX32348-10471: CANSignal - ACCPVST1 (System Interface)
CANSignal - ACCPVST1(Message Label: ADU1S07)

#### TFDCX32348-10473: CANSignal - ACCPVST2 (System Interface)
CANSignal - ACCPVST2 (Message Label: ADU1S07)

#### TFDCX32348-28008: CANSignal - ACCAVTYR (System Interface)
CANSignal - ACCAVTYR (Message Label: ADU1S07)

#### TFDCX32348-28009: CANSignal - ACCAVDTR (System Interface)
CANSignal - ACCAVDTR (Message Label: ADU1S07)

#### TFDCX32348-28010: CANSignal - ACCAVS1R (System Interface)
CANSignal - ACCAVS1R (Message Label: ADU1S07)

#### TFDCX32348-28011: CANSignal - ACCAVS2R (System Interface)
CANSignal - ACCAVS2R (Message Label: ADU1S07)

#### TFDCX32348-28012: CANSignal - ACCAVLPR (System Interface)
CANSignal - ACCAVLPR (Message Label: ADU1S07)

#### TFDCX32348-28013: CANSignal - ACCAVTYL (System Interface)
CANSignal - ACCAVTYL (Message Label: ADU1S07)

#### TFDCX32348-28014: CANSignal - ACCAVDTL (System Interface)
CANSignal - ACCAVDTL (Message Label: ADU1S07)

#### TFDCX32348-28015: CANSignal - ACCAVS1L (System Interface)
CANSignal - ACCAVS1L (Message Label: ADU1S07)

#### TFDCX32348-28016: CANSignal - ACCAVS2L (System Interface)
CANSignal - ACCAVS2L (Message Label: ADU1S07)

#### TFDCX32348-28017: CANSignal - ACCAVLPL (System Interface)
CANSignal - ACCAVLPL (Message Label: ADU1S07)

#### TFDCX32348-68545: CANSignal - ISALIMID (System Interface)
CANSignal - ISALIMID (Message Label: FCM1S39)

#### TFDCX32348-68547: CANSignal - ERMMAXID (System Interface)
CANSignal - ERMMAXID (Message Label: FCM1S39)

## TFDCX32348-8491: Output Requirements (Heading)

### TFDCX32348-10515: HMI Interface (Heading)

#### TFDCX32348-33793: HMI - HM_ACC_PRECEDING_VEHICLE_MOVING_BLINK (System Interface)
Range: OFF, Car_Dis_x, Truck_Dis_x, Bike_Dis_x
x : 0, 1, 2, 3, 4

#### TFDCX32348-13922: HMI - HMI_ACC_DISTANCE_TIME (System Interface)
Description: This parameter indicates vehicle to vehicle distance time,
Range: OFF, Level1_White, Level1_Green, Level1_Red, Level1_Red_Blink, Level2_White, Level2_Green, Level2_Red, Level2_Red_Blink, Level3_White, Level3_Green, Level3_Red, Level3_Red_Blink, Level4_White, Level4_Green, Level4_Red, Level4_Red_Blink

#### TFDCX32348-13911: HMI - HMI_ACC_CONTROL_OBJECT (System Interface)
Description: This parameter indicates control target.
Range: NO_Object, Curve

#### TFDCX32348-13913: HMI – HMI_ACC_MESSAGE2 (System Interface)
Description: This parameter indicates Message 2
Range: OFF, Op_Msg_Waiting, Op_Msg_Acceleration_Supress, Op_Msg_Overtake_Preventation

#### TFDCX32348-13915: HMI - HMI_ACC_MESSAGE1 (System Interface)
Description: This parameter indicates Message 1
Range: Op_Msg1_AbletoResume1, Op_Msg1_OperGuideUp, Op_Msg1_OperGuideDown, Op_Msg1_SetCurrentSpeed, Op_Msg1_AbletoResume2, Op_Msg1_OperationGuide, Op_Msg1_SetSpeed

#### TFDCX32348-13918: HMI - HMI_ACC_DISPLAY_LIMITSPEED (System Interface)
Description: This parameter indicates ACC vehicle limit speed
Range: 0-254, ---

#### TFDCX32348-13920: HMI - HMI_ACC_DISPLAY_LIMITSPEED_UNIT (System Interface)
Description: This parameter indicates ACC vehicle limit speed unit
Range: OFF, km/h, MPH

#### TFDCX32348-29121: HMI - HMI_ACC_FRAME_RSA (System Interface)
Description: This parameter indicates Speed suggestion mark.
Range: OFF, ON

#### TFDCX32348-29123: HMI - HMI_ACC_SPEED_UPDOWN_RSA (System Interface)
Description: This parameter indicates Speed guide mark
Range: OFF, UP, DOWN

#### TFDCX32348-13928: HMI - HMI_ACC_PRECEDING_VEHICLE_ICON (System Interface)
Description: This parameter indicates the preceding vehicle icon
Range: OFF, Car_Dx_yyy, Truck_Dx_yyy, Bike_Dx_yyy, Pedestrian_Dx_zzz
x ; 0, 1, 2, 3, 4
yyy : White, Gray, Red
zzz : Gray, Red

#### TFDCX32348-13930: HMI - HMI_ACC_PRECEDING_VEHICLE_ICON_FWIND (System Interface)
Description: This parameter indicates the preceding vehicle icon for Fwindow
Range: OFF, Car_Dx_yyy, Pedestrian_Dx_zzz
x ; 0, 1, 2, 3, 4
yyy : White, Gray, Red
zzz : Gray, Red

#### TFDCX32348-13932: HMI - HMI_ACC_PRECEDING_VEHICLE_BLINK (System Interface)
Description: This parameter indicates preceding vehicle blink request
Range: OFF, ON

#### TFDCX32348-13936: HMI - HMI_ACC_ADJACENT_VEHICLE_ICON_RIGHT (System Interface)
Description: This parameter indicates adjacent right vehicle icon
Range: OFF, Car_Disx_Posy_zzz, Truck_Disx_Posy_zzz, Bike_Disx_Posy_zzz, Pedestrian_Disx_Posy_zzz
x : 1, 2, 3, 4
y : 1, 2, 3, 4, 5, 6, 7
zzz : White, Gray, Red

#### TFDCX32348-13937: HMI – HMI_ACC_ADJACENT_VEHICLE_ICON_RIGHT_FWIND (System Interface)
Description: This parameter indicates adjacent right vehicle icon for Fwindow
Range:
1. Car_Disx_yyy_zzz
x : 1, 2, 3, 4
yyy : Center, Right, Right_1
zzz : White, Gray, Red
2. Pedestrian_Disx_Right_1_yyy
x : 1, 2, 3, 4
yyy : Gray, Red

#### TFDCX32348-13939: HMI - HMI_ACC_ADJACENT_VEHICLE_BLINK_RIGHT (System Interface)
Description: This parameter indicates adjacent right vehicle blink request
Range: OFF, ON

#### TFDCX32348-13957: HMI - HMI_ACC_ADJACENT_VEHICLE_ICON_LEFT (System Interface)
Description: This parameter indicates adjacent left vehicle icon
Range: OFF, Car_Disx_Posy_zzz, Truck_Disx_Posy_zzz, Bike_Disx_Posy_zzz, Pedestrian_Disx_Posy_zzz
x : 1, 2, 3, 4
y : 1, 2, 3, 4, 5, 6, 7
zzz : White, Gray, Red

#### TFDCX32348-13959: HMI – HMI_ACC_ADJACENT_VEHICLE_ICON_LEFT_FWIND (System Interface)
Description: This parameter indicates adjacent left vehicle icon for Fwindow
Range:
1. Car_Disx_yyy_zzz
x : 1, 2, 3, 4
yyy : Center, Right, Right_1
zzz : White, Gray, Red
2. Pedestrian_Disx_Right_1_yyy
x : 1, 2, 3, 4
yyy : Gray, Red

#### TFDCX32348-13961: HMI - HMI_ACC_ADJACENT_VEHICLE_BLINK_LEFT (System Interface)
Description: This parameter indicates adjacent left vehicle blink request
Range: OFF, ON

### TFDCX32348-10517: Warning ID (Heading)

#### TFDCX32348-28115: ADAS Warning IDs (Heading)

##### TFDCX32348-28018: WarningID – WRN_ADAS_ACC_G7 (System Interface)
Description: This parameter indicates the status of ADAS Warning triggered by ACC Distance Time.
Range: OFF, ON

##### TFDCX32348-28112: WarningID – WRN_ADAS_ACC_G11_01 (System Interface)
Description: This parameter indicates the status of ADAS Warning triggered by ACCMSG2 = 00011b.
Range: OFF, ON

##### TFDCX32348-28113: WarningID – WRN_ADAS_ACC_G11_02 (System Interface)
Description: This parameter indicates the status of ADAS Warning triggered by ACCMSG2 = 00101b.
Range: OFF, ON

##### TFDCX32348-28114: WarningID – WRN_ADAS_ACC_G11_03 (System Interface)
Description: This parameter indicates the status of ADAS Warning triggered by ACCMSG2 = 00110b.
Range: OFF, ON

##### TFDCX32348-28019: WarningID – WRN_ADAS_ACC_G20 (System Interface)
Description: This parameter indicates the status of ADAS Warning triggered by ACC Preceding Vehicle.
Range: OFF, ON

##### TFDCX32348-28116: WarningID – WRN_ADAS_ACC_G22 (System Interface)
Description: This parameter indicates the status of ADAS Warning triggered by ACC Right Adjacent Vehicle.
Range: OFF, ON

##### TFDCX32348-28117: WarningID – WRN_ADAS_ACC_G23 (System Interface)
Description: This parameter indicates the status of ADAS Warning triggered by ACC Left Adjacent Vehicle.
Range: OFF, ON

#### TFDCX32348-28118: Normal Warning IDs (Heading)

##### TFDCX32348-14011: WarningID – WRN_NORM_ACC_VM01_GME12_02 (System Interface)
Range: OFF, ON

##### TFDCX32348-14013: WarningID – WRN_NORM_ACC_VM01_GME12_03 (System Interface)
Range: OFF, ON

##### TFDCX32348-14015: WarningID – WRN_NORM_ACC_VM01_GME12_04 (System Interface)
Range: OFF, ON

##### TFDCX32348-14017: WarningID – WRN_NORM_ACC_VM01_GME12_05 (System Interface)
Range: OFF, ON

##### TFDCX32348-14021: WarningID – WRN_NORM_ACC_VM01_GME12_07 (System Interface)
Range: OFF, ON

##### TFDCX32348-14023: WarningID – WRN_NORM_ACC_VM01_GME12_08 (System Interface)
Range: OFF, ON

##### TFDCX32348-14026: WarningID – WRN_NORM_ACC_VM01_GME12_09 (System Interface)
Range: OFF, ON

### TFDCX32348-10519: Internal Signals (Heading)

#### TFDCX32348-28152: InternalSignal - ACC_Set_Speed (System Interface)
Description: This parameter indicates the value for Set speed.
Range: OFF, --- (Excess), --- (White), --- (Green), 1-254 (Excess), 1-254 (White), 1-254 (Green)

#### TFDCX32348-28154: InternalSignal - ACC_Set_Speed_Unit (System Interface)
Description: This parameter indicates the Icon for speed unit.
Range: OFF, km/h (Excess), km/h (White), km/h (Green), mph (Excess), mph (White), mph (Green)

#### TFDCX32348-28185: InternalSignal - ACC_SET_Indicator (System Interface)
Description: This parameter indicates SET mark
Range: OFF, SET (White), SET (Green)

#### TFDCX32348-33748: InternalSignal - ACC_Preceding_Vehicle_Distance (System Interface)
Range: OFF, Distance 0, Distance 1, Distance 2, Distance 3, Distance 4

#### TFDCX32348-33832: InternalSignal - ACC_Preceding_Vehicle_Presence_Status (System Interface)
Range: OFF, Passenger car, Truck, Motorbike, Pedestrian

## TFDCX32348-8493: Performance Requirements (Heading)

### TFDCX32348-10465: Basic Screen No.2 (Heading)

#### TFDCX32348-10114: Screen Configuration (Heading)

##### TFDCX32348-14028: HMI parameters corresponding to Display Group (Information)
| Sample Graphic configuration(*1) | Group No. | Description | InternalSignal/HMI/W/G IDs |
| --- | --- | --- | --- |
|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 | 1 | Set speed | ACC_Set_Speed |
|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 | 2 | Set speed unit | ACC_Set_Speed_Unit |
|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 | 3 | Preceding vehicle moving | HM_ACC_PRECEDING_VEHICLE_MOVING_BLINK |
|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 | 7 | Vehicle to vehicle distance time | HMI_ACC_DISTANCE_TIME HMI_ACC_DISTANCE_TIME_BLINK WRN_ADAS_ACC_G7 |
|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 | 10 | Control target | HMI_ACC_CONTROL_OBJECT |
|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 | 11 | Message 2 | HMI_ACC_MESSAGE2 WRN_ADAS_ACC_G11_01 WRN_ADAS_ACC_G11_02 WRN_ADAS_ACC_G11_03 |
|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 | 12 | Message 1 | HMI_ACC_MESSAGE1 HMI_ACC_DISPLAY_LIMITSPEED HMI_ACC_DISPLAY_LIMITSPEED_UNIT WRN_NORM_ACC_VM01_GME12_02 WRN_NORM_ACC_VM01_GME12_03 WRN_NORM_ACC_VM01_GME12_04 WRN_NORM_ACC_VM01_GME12_05 WRN_NORM_ACC_VM01_GME12_07 WRN_NORM_ACC_VM01_GME12_08 WRN_NORM_ACC_VM01_GME12_09 |
|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 | 13 | Speed suggestion mark | HMI_ACC_FRAME_RSA |
|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 | 14 | Speed guide mark | HMI_ACC_SPEED_UPDOWN_RSA |
|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 | 19 | SET mark | ACC_SET_Indicator |
|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 | 21 | Preceding vehicle | ACC_Preceding_Vehicle_Presence_Status ACC_Preceding_Vehicle_Distance HMI_ACC_PRECEDING_VEHICLE_ICON HMI_ACC_PRECEDING_VEHICLE_ICON_FWIND HMI_ACC_PRECEDING_VEHICLE_BLINK WRN_ADAS_ACC_G20 |
|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 | 22 | Adjacent vehicle (right) | HMI_ACC_ADJACENT_VEHICLE_ICON_RIGHT HMI_ACC_ADJACENT_VEHICLE_ICON_RIGHT_FWIND HMI_ACC_ADJACENT_VEHICLE_BLINK_RIGHT WRN_ADAS_ACC_G22 |
|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 | 23 | Adjacent vehicle (left) | HMI_ACC_ADJACENT_VEHICLE_ICON_LEFT HMI_ACC_ADJACENT_VEHICLE_ICON_LEFT_FWIND HMI_ACC_ADJACENT_VEHICLE_BLINK_LEFT WRN_ADAS_ACC_G23 |
(*1) This image is just a reference. Refer GUI SRD for the actual asset images.

#### TFDCX32348-10981: Group 1: Set speed (Heading)

##### TFDCX32348-18153: Logic Table - InternalSignal - ACC_Set_Speed (System Requirement)
| No. | Input |  |  |  |  | Output |
| --- | --- | --- | --- | --- | --- | --- |
| No. | InternalSignal - IgnMode | CAN Signal Communication Status – ACCSP (*1), (*2) | CANSignal - ACCSP | CANSignal - ACCSPEXC | CANSignal - ACCSPST1 | InternalSignal – ACC_Set_Speed |
| 1 | OFF | x | x | x | x | OFF |
| 2 | ON | Communication starting Never Received: 1 Communication Failure: 0 | x | x | x | OFF |
| 3 | ON | Communication establishment Never Received: 0 Communication Failure: 0 | 0x00 | x | x | OFF |
| 4 | ON | Communication establishment Never Received: 0 Communication Failure: 0 | 0xFF | 1b | x | --- (Excess) |
| 5 | ON | Communication establishment Never Received: 0 Communication Failure: 0 | 0xFF | 0b | 10b | --- (Green) |
| 6 | ON | Communication establishment Never Received: 0 Communication Failure: 0 | 0xFF | 0b | Other than 10b | --- (White) |
| 7 | ON | Communication establishment Never Received: 0 Communication Failure: 0 | 0x01-0xFE | 1b | x | 1-254 (Excess) |
| 8 | ON | Communication establishment Never Received: 0 Communication Failure: 0 | 0x01-0xFE | 0b | 10b | 1-254 (Green) |
| 9 | ON | Communication establishment Never Received: 0 Communication Failure: 0 | 0x01-0xFE | 0b | Other than 10b | 1-254 (White) |
| 10 | ON | Communication abnormality Never Received: x Communication Failure: 1 | x | x | x | OFF |
(*1) Never Received and Communication Failure is defined in CAN General SRD. Please check the CAN General SRD for details.
(*2) In this table, ACCSPST1 and ACCSPEXC are included in the same CAN Msg as ACCSP, so there is no need to check the communication status.
- Verification Criteria: Verify by executing test cases
- Verification Method: Software Qualification Test, System Qualification Test, Unit Test
- Verification Owner: FV, SW
- System Requirement State: Approved
- Primary Discipline: SW
- ASIL Rating: QM

#### TFDCX32348-14291: Group 2: Set speed unit (Heading)

##### TFDCX32348-32225: Logic Table - InternalSignal – ACC_Set_Speed_Unit (System Requirement)
| No. | Input |  |  |  |  | Output |
| --- | --- | --- | --- | --- | --- | --- |
| No. | InternalSignal - IgnMode | CAN Signal Communication Status – ACCSPU (*1), (*2) | CANSignal – ACCSPU | CANSignal – ACCSPEXC | CANSignal – ACCSUST1 | InternalSignal – ACC_Set_Speed_Unit |
| 1 | OFF | x | x | x | x | OFF |
| 2 | ON | Communication starting Never Received: 1 Communication Failure: 0 | x | x | x | OFF |
| 3 | ON | Communication establishment Never Received: 0 Communication Failure: 0 | 01b | 1b | x | km/h (Excess) |
| 4 | ON | Communication establishment Never Received: 0 Communication Failure: 0 | 01b | 0b | 10b | km/h (Green) |
| 5 | ON | Communication establishment Never Received: 0 Communication Failure: 0 | 01b | 0b | Other than 10b | km/h (White) |
| 6 | ON | Communication establishment Never Received: 0 Communication Failure: 0 | 10b | 1b | x | mph (Excess) |
| 7 | ON | Communication establishment Never Received: 0 Communication Failure: 0 | 10b | 0b | 10b | mph (Green) |
| 8 | ON | Communication establishment Never Received: 0 Communication Failure: 0 | 10b | 0b | Other than 10b | mph (White) |
| 9 | ON | Communication establishment Never Received: 0 Communication Failure: 0 | Other than above | x | x | OFF |
| 10 | ON | Communication abnormality Never Received: x Communication Failure: 1 | x | x | x | OFF |
(*1) Never Received and Communication Failure is defined in CAN General SRD. Please check the CAN General SRD for details.
(*2) In this table, ACCSUST1 and ACCSPEXC are included in the same CAN Msg as ACCSPU, so there is no need to check the communication status.
- Verification Criteria: Verify by code review
- Verification Method: Unit Test
- Verification Owner: SW
- System Requirement State: Approved
- Primary Discipline: SW
- ASIL Rating: QM

#### TFDCX32348-14293: Group 3: Preceding vehicle moving (Heading)
Vehicle Speed State

##### TFDCX32348-18155: Logic Table - Local Parameter - ACC_Preceding_Vehicle_Moving (System Requirement)
| No. | Input |  |  | Output |
| --- | --- | --- | --- | --- |
| No. | InternalSignal - IgnMode | CAN Signal Communication Status: ACCPVST3 (*1) | CANSignal - ACCPVST3 | Local Parameter - ACC_Preceding_Vehicle_Moving |
| 1 | OFF | - | - | OFF |
| 2 | ON | Communication starting Never Received: 1 Communication Failure: 0 | x | OFF |
| 3 | ON | Communication establishment Never Received: 0 Communication Failure: 0 | 0b | OFF |
| 4 | ON | Communication establishment Never Received: 0 Communication Failure: 0 | 1b | Moving |
| 5 | ON | Communication abnormality Never Received: x Communication Failure: 1 | x | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-32660: Logic Table - HMI - HM_ACC_PRECEDING_VEHICLE_MOVING_BLINK (System Requirement)
| No. | Input |  |  | Output |
| --- | --- | --- | --- | --- |
| No. | Local Parameter - ACC_Preceding_Vehicle_Moving | InternalSignal - ACC_Preceding_Vehicle_Presence_Status | InternalSignal - ACC_Preceding_Vehicle_Distance | HMI - HM_ACC_PRECEDING_VEHICLE_MOVING_BLINK (*1) |
| 1 | OFF | x | x | OFF |
| 2 | x | OFF or Pedestrian | x | OFF |
| 3 | x | x | OFF | OFF |
| 4 | Moving | Passenger car | Distance 0 | Car_Dis_0 |
| 5 | Moving | Passenger car | Distance 1 | Car_Dis_1 |
| 6 | Moving | Passenger car | Distance 2 | Car_Dis_2 |
| 7 | Moving | Passenger car | Distance 3 | Car_Dis_3 |
| 8 | Moving | Passenger car | Distance 4 | Car_Dis_4 |
| 9 | Moving | Truck | Distance 0 | Truck_Dis_0 |
| 10 | Moving | Truck | Distance 1 | Truck_Dis_1 |
| 11 | Moving | Truck | Distance 2 | Truck_Dis_2 |
| 12 | Moving | Truck | Distance 3 | Truck_Dis_3 |
| 13 | Moving | Truck | Distance 4 | Truck_Dis_4 |
| 14 | Moving | Motorbike | Distance 0 | Bike_Dis_0 |
| 15 | Moving | Motorbike | Distance 1 | Bike_Dis_1 |
| 16 | Moving | Motorbike | Distance 2 | Bike_Dis_2 |
| 17 | Moving | Motorbike | Distance 3 | Bike_Dis_3 |
| 18 | Moving | Motorbike | Distance 4 | Bike_Dis_4 |
(*1) While HM_ACC_PRECEDING_VEHICLE_MOVING_BLINK = other than OFF, Blink control is necessary for Preceding Vehicle Moving icon.
Requirements for Blink control:
1. Cycle time is 1,000ms.
2. ON Duty is 50%.
3. At the beginning of the blinking, Turn on the icon display.
4. Cancel the icon blinking as soon as HM_ACC_PRECEDING_VEHICLE_MOVING_BLINK is changed from other than OFF to OFF.
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- Verification Criteria: Verify by executing test cases
- Verification Method: Software Qualification Test, System Qualification Test, Unit Test
- Verification Owner: FV, SW
- System Requirement State: Approved
- Primary Discipline: SW
- ASIL Rating: QM

#### TFDCX32348-14295: Group 7: Vehicle to vehicle distance time (Heading)

##### TFDCX32348-18156: Logic Table - HMI - HMI_ACC_DISTANCE_TIME (System Requirement)
| No. | Input |  |  |  |  | Output |
| --- | --- | --- | --- | --- | --- | --- |
| No. | InternalSignal - IgnMode | CAN Signal Communication Status of ACCDST(*1), (*2) | CANSignal - ACCDST | CANSignal - ACCDTST1 | CANSignal - ACCDTST2 | HMI - HMI_ACC_DISTANCE_TIME |
| 1 | OFF | x | x | x | x | OFF |
| 2 | ON | Communication starting Never Received: 1 Communication Failure: 0 | x | x | x | OFF |
| 3 | ON | Communication starting Never Received: 0 Communication Failure: 0 | 001b | 01b | x | Level4_White |
| 4 | ON | Communication starting Never Received: 0 Communication Failure: 0 | 001b | 10b | x | Level4_Green |
| 5 | ON | Communication starting Never Received: 0 Communication Failure: 0 | 001b | 11b | 0b | Level4_Red |
| 6 | ON | Communication starting Never Received: 0 Communication Failure: 0 | 001b | 11b | 1b | Level4_Red_Blink (*3) |
| 7 | ON | Communication starting Never Received: 0 Communication Failure: 0 | 010b | 01b | x | Level3_White |
| 8 | ON | Communication starting Never Received: 0 Communication Failure: 0 | 010b | 10b | x | Level3_Green |
| 9 | ON | Communication starting Never Received: 0 Communication Failure: 0 | 010b | 11b | 0b | Level3_Red |
| 10 | ON | Communication starting Never Received: 0 Communication Failure: 0 | 010b | 11b | 1b | Level3_Red_Blink (*3) |
| 11 | ON | Communication starting Never Received: 0 Communication Failure: 0 | 011b | 01b | x | Level2_White |
| 12 | ON | Communication starting Never Received: 0 Communication Failure: 0 | 011b | 10b | x | Level2_Green |
| 13 | ON | Communication starting Never Received: 0 Communication Failure: 0 | 011b | 11b | 0b | Level2_Red |
| 14 | ON | Communication starting Never Received: 0 Communication Failure: 0 | 011b | 11b | 1b | Level2_Red_Blink (*3) |
| 15 | ON | Communication starting Never Received: 0 Communication Failure: 0 | 100b | 01b | x | Level1_White |
| 16 | ON | Communication starting Never Received: 0 Communication Failure: 0 | 100b | 10b | x | Level1_Green |
| 17 | ON | Communication starting Never Received: 0 Communication Failure: 0 | 100b | 11b | 0b | Level1_Red |
| 18 | ON | Communication starting Never Received: 0 Communication Failure: 0 | 100b | 11b | 1b | Level1_Red_Blink (*3) |
| 19 | ON | Communication starting Never Received: 0 Communication Failure: 0 | Other than above |  |  | OFF |
| 20 | ON | Communication abnormality Never Received: x Communication Failure: 1 | x | x | x | OFF |
(*1) Never Received and Communication Failure is defined in CAN General SRD. Please check the CAN General SRD for details.
(*2) In this table, It is not necessary to check Communication Status for ACCDTST1 and ACCDTST2, since ACCDST is included in the same CAN Msg.
(*3) While HMI- ACC_DISTANCE_TIME == Level*_Red_Blink (*: 1, 2, 3, 4), Blink control is necessary for Distance Time image.
Requirements for Blink control:
1. Cycle time is 1,000ms.
2. ON Duty is 50%.
3. At the beginning of the blinking, Turn on the icon display.
4. Cancel the image blinking as soon as HMI- ACC_DISTANCE_TIME is changed from Level*_Red_Blink (*: 1, 2, 3, 4) to OFF.
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- Verification Criteria: Verify by executing test cases
- Verification Method: Software Qualification Test, System Qualification Test, Unit Test
- Verification Owner: FV, SW
- System Requirement State: Approved
- Primary Discipline: SW
- ASIL Rating: QM

##### TFDCX32348-14030: Logic Table - Warning ID - WRN_ADAS_ACC_G7 (System Requirement)
| No. | Input | Output |
| --- | --- | --- |
| No. | HMI- ACC_DISTANCE_TIME_BLINK | Warning ID - WRN_ADAS_ACC_G7 (*1) |
| 1 | OFF | OFF |
| 2 | Level*_Red_Blink (*: 1, 2, 3, 4) | ON |
(*1) For WRN_ADAS_ACC_G7, Update the value immediately when Input condition changes.
- Verification Criteria: Verify by executing test cases
- Verification Method: Software Qualification Test, System Qualification Test, Unit Test
- Verification Owner: FV, SW
- System Requirement State: Approved
- Primary Discipline: SW
- ASIL Rating: QM

#### TFDCX32348-14047: Group 10: Control Target (Heading)

##### TFDCX32348-18121: Logic Table - HMI - HMI_ACC_CONTROL_OBJECT (System Requirement)
| No. | Input |  |  | Output |
| --- | --- | --- | --- | --- |
| No. | InternalSignal - IgnMode | CAN Signal Communication Status - ACCCNTOB (*1) | CANSignal - ACCCNTOB | HMI - HMI_ACC_CONTROL_OBJECT |
| 1 | OFF | - | - | No_Object |
| 2 | ON | Communication starting Never Received: 1 Communication Failure: 0 | x | No_Object |
| 3 | ON | Communication establishment Never Received: 0 Communication Failure: 0 | 0001b | Curve |
| 4 | ON | Communication establishment Never Received: 0 Communication Failure: 0 | Other than above | No_Object |
| 5 | ON | Communication abnormality Never Received: x Communication Failure: 1 | x | No_Object |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

#### TFDCX32348-14066: Group 11: Message2 (Heading)

##### TFDCX32348-18009: Logic Table - HMI - HMI_ACC_MESSAGE2 (System Requirement)
| No. | Input |  |  | Output |
| --- | --- | --- | --- | --- |
| No. | InternalSignal - IgnMode | CAN Signal Communication Status of ACCMSG2 (*1) | CANSignal - ACCMSG2 | HMI - HMI_ACC_MESSAGE2 |
| 1 | OFF | - | - | OFF |
| 2 | ON | Communication starting Never Received: 1 Communication Failure: 0 | x | OFF |
| 3 | ON | Communication establishment Never Received: 0 Communication Failure: 0 | 00011b | Op_Msg_Waiting |
| 4 | ON | Communication establishment Never Received: 0 Communication Failure: 0 | 00101b | Op_Msg_Acceleration_Supress |
| 5 | ON | Communication establishment Never Received: 0 Communication Failure: 0 | 00110b | Op_Msg_Overtake_Preventation |
| 6 | ON | Communication establishment Never Received: 0 Communication Failure: 0 | Other than the above | OFF |
| 7 | ON | Communication abnormality Never Received: x Communication Failure: 1 | x | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-32258: Logic Table - Warning ID - WRN_ADAS_ACC_G11_** (System Requirement)
| No. | Input | Output |  |  |
| --- | --- | --- | --- | --- |
| No. | HMI - HMI_ACC_Message2 | Warning ID - WRN_ADAS_ACC_G11_01 | Warning ID - WRN_ADAS_ACC_G11_02 | Warning ID - WRN_ADAS_ACC_G11_03 |
| 1 | OFF | OFF | OFF | OFF |
| 2 | Op_Msg_Waiting | ON | OFF | OFF |
| 3 | Op_Msg_Acceleration_Supress | OFF | ON | OFF |
| 4 | Op_Msg_Overtake_Preventation | OFF | OFF | ON |
- Verification Criteria: Verify by executing test cases
- Verification Method: Software Qualification Test, System Qualification Test, Unit Test
- Verification Owner: FV, SW
- System Requirement State: Approved
- Primary Discipline: SW
- ASIL Rating: QM

#### TFDCX32348-14062: Group 12: Message1 (Heading)

##### TFDCX32348-18136: Logic Table - Local parameter - ACC_Message1_Status (System Requirement)
| No. | Input |  |  | Output |
| --- | --- | --- | --- | --- |
| No. | InternalSignal - IgnMode | CAN Signal Communication Status of ACCMSG4 (*1) | CANSignal - ACCMSG4 | Local parameter - ACC_Message1_Status |
| 1 | OFF | x | x | OFF |
| 2 | ON | Communication starting Never Received: 1 Communication Failure: 0 | x | OFF |
| 3 | ON | Communication establishment Never Received: 0 Communication Failure: 0 | 00010b | Msg1_AbletoResume1 |
| 3 | ON | Communication establishment Never Received: 0 Communication Failure: 0 | 00011b | Msg1_OperGuideUp |
| 4 | ON | Communication establishment Never Received: 0 Communication Failure: 0 | 00100b | Msg1_OperGuideDown |
| 5 | ON | Communication establishment Never Received: 0 Communication Failure: 0 | 00101b | Msg1_SetCurrentSpeed |
| 6 | ON | Communication establishment Never Received: 0 Communication Failure: 0 | 00111b | Msg1_AbletoResume2 |
| 7 | ON | Communication establishment Never Received: 0 Communication Failure: 0 | 01000b | Msg1_OperationGuide |
| 8 | ON | Communication establishment Never Received: 0 Communication Failure: 0 | 01001b | Msg1_SetSpeed |
| 9 | ON | Communication establishment Never Received: 0 Communication Failure: 0 | Other than above | OFF |
| 10 | ON | Communication abnormality Never Received: x Communication Failure: 1 | x | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-18138: Logic Table - Local Parameter - Setting_Speed_Status (System Requirement)
| No. | Input |  |  | Output |
| --- | --- | --- | --- | --- |
| No. | InternalSignal - IgnMode | CAN Signal Communication Status of ACCMSGV (*1) | CANSignal - ACCMSGV | Local Parameter - Setting_Speed_Status |
| 1 | OFF | x | x | 0 |
| 2 | ON | Communication starting Never Received: 1 Communication Failure: 0 | x | 0 |
| 3 | ON | Communication establishment \ Never Received: 0 Communication Failure: 0 | 0x00 | 0 |
| 4 | ON | Communication establishment \ Never Received: 0 Communication Failure: 0 | 0xFF | --- |
| 5 | ON | Communication establishment \ Never Received: 0 Communication Failure: 0 | 0x01-0xFE | 1-254 |
| 6 | ON | Communication abnormality Never Received: x Communication Failure: 1 | x | 0 |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-18007: Logic Table - Local Parameter - Setting_Speed_Unit_Status (System Requirement)
| No. | Input |  |  | Output |
| --- | --- | --- | --- | --- |
| No. | InternalSignal - IgnMode | CAN Signal Communication Status of ACCMSGU (*1) | CANSignal - ACCMSGU | Local Parameter - Setting_Speed_Unit_Status |
| 1 | OFF | x | x | OFF |
| 2 | ON | Communication starting Never Received: 1 Communication Failure: 0 | x | OFF |
| 3 | ON | Communication establishment Never Received: 0 Communication Failure: 0 | 00b | OFF |
| 4 | ON | Communication establishment Never Received: 0 Communication Failure: 0 | 01b | km/h |
| 4 | ON | Communication establishment Never Received: 0 Communication Failure: 0 | 10b | MPH |
| 5 | ON | Communication establishment Never Received: 0 Communication Failure: 0 | Other than above | OFF |
| 6 | ON | Communication abnormality Never Received: x Communication Failure: 1 | x | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-28950: Logic Table - HMI - HMI_ACC_MESSAGE1/ HMI_ACC_DISPLAY_LIMITSPEED/HMI_ACC_DISPLAY_LIMITSPEED_UNIT (System Requirement)
| No. | Input |  |  | Output |  |  | <Info> Display Message |
| --- | --- | --- | --- | --- | --- | --- | --- |
| No. | Local Parameter - ACC_Message1_Status | Local Parameter - Setting_Speed_Status | Local Parameter - Setting_Speed_Unit_Status | HMI - HMI_ACC_MESSAGE1 | HMI - HMI_ACC_DISPLAY_LIMITSPEED (#2) | HMI - HMI_ACC_DISPLAY_LIMITSPEED_UNIT (#3) | <Info> Display Message |
| 1 | OFF | x | x | OFF | 0 | OFF | No Indication |
| 2 | Msg1_AbletoResume1 | x | x | Op_Msg1_AbletoResume1 | 0 | OFF | Push ""#"" or Press Accelerator to Resume |
| 3 | Msg1_OperGuideUp | --- or 0-254 | OFF | Op_Msg1_OperGuideUp | --- or 0-254 | OFF | Hold ""#1"" to Set ""#2"" ""#3"" |
| 3 | Msg1_OperGuideUp | --- or 0-254 | km/h | Op_Msg1_OperGuideUp | --- or 0-254 | km/h | Hold ""#1"" to Set ""#2"" ""#3"" |
| 3 | Msg1_OperGuideUp | --- or 0-254 | MPH | Op_Msg1_OperGuideUp | --- or 0-254 | MPH | Hold ""#1"" to Set ""#2"" ""#3"" |
| 4 | Msg1_OperGuideDown | --- or 0-254“ | OFF | Op_Msg1_OperGuideDown | --- or 0-254 | OFF | Hold ""#1"" to Set ""#2"" ""#3"" |
| 4 | Msg1_OperGuideDown | --- or 0-254“ | km/h | Op_Msg1_OperGuideDown | --- or 0-254 | km/h | Hold ""#1"" to Set ""#2"" ""#3"" |
| 4 | Msg1_OperGuideDown | --- or 0-254“ | MPH | Op_Msg1_OperGuideDown | --- or 0-254 | MPH | Hold ""#1"" to Set ""#2"" ""#3"" |
| 5 | Msg1_SetCurrentSpeed | x | x | Op_Msg1_SetCurrentSpeed | 0 | OFF | Push ""#"" to Set Current Speed |
| 6 | Msg1_AbletoResume2 | x | x | Op_Msg1_AbletoResume2 | 0 | OFF | Push ""#"" or Press Accelerator to Resume |
| 7 | Msg1_OperationGuide | --- or 0-254 | OFF | Op_Msg1_OperationGuide | --- or 0-254 | OFF | Hold ""#1"" to Set ""#2"" ""#3"" |
| 7 | Msg1_OperationGuide | --- or 0-254 | km/h | Op_Msg1_OperationGuide | --- or 0-254 | km/h | Hold ""#1"" to Set ""#2"" ""#3"" |
| 7 | Msg1_OperationGuide | --- or 0-254 | MPH | Op_Msg1_OperationGuide | --- or 0-254 | MPH | Hold ""#1"" to Set ""#2"" ""#3"" |
| 8 | Msg1_SetSpeed | x | x | Op_Msg1_SetSpeed | 0 | OFF | Push ""#"" to Set Current Speed |
- Verification Criteria: Verify by executing test cases
- Verification Method: Software Qualification Test, System Qualification Test, Unit Test
- Verification Owner: FV, SW
- System Requirement State: Approved
- Primary Discipline: SW
- ASIL Rating: QM

##### TFDCX32348-28952: Logic Table - WRN_NORM_ACC_ VM01_GME12_** (System Requirement)
| No. | Input | Output |  |  |  |  |  |  | <Info> Display Message |
| --- | --- | --- | --- | --- | --- | --- | --- | --- | --- |
| No. | Local Parameter - ACC_Message1_Status | WRN_NORM_ACC_ VM01_GME12_02 | WRN_NORM_ACC_ VM01_GME12_03 | WRN_NORM_ACC_ VM01_GME12_04 | WRN_NORM_ACC_ VM01_GME12_05 | WRN_NORM_ACC_ VM01_GME12_07 | WRN_NORM_ACC_ VM01_GME12_08 | WRN_NORM_ACC_ VM01_GME12_09 | <Info> Display Message |
| 1 | Msg1_AbletoResume1 | ON | OFF | OFF | OFF | OFF | OFF | OFF | Push ""#"" or Press Accelerator to Resume |
| 2 | Msg1_OperGuideUp | OFF | ON | OFF | OFF | OFF | OFF | OFF | Hold ""#1"" to Set ""#2"" ""#3"" |
| 3 | Msg1_OperGuideDown | OFF | OFF | ON | OFF | OFF | OFF | OFF | Hold ""#1"" to Set ""#2"" ""#3"" |
| 4 | Msg1_SetCurrentSpeed | OFF | OFF | OFF | ON | OFF | OFF | OFF | Push ""#"" to Set Current Speed |
| 5 | Msg1_AbletoResume2 | OFF | OFF | OFF | OFF | ON | OFF | OFF | Push ""#"" or Press Accelerator to Resume |
| 6 | Msg1_OperationGuide | OFF | OFF | OFF | OFF | OFF | ON | OFF | Hold ""#1"" to Set ""#2"" ""#3"" |
| 7 | Msg1_SetSpeed | OFF | OFF | OFF | OFF | OFF | OFF | ON | Push ""#"" to Set Current Speed |
| 8 | OFF | OFF | OFF | OFF | OFF | OFF | OFF | OFF |  |
- Verification Criteria: Verify by executing test cases
- Verification Method: Software Qualification Test, System Qualification Test, Unit Test
- Verification Owner: FV, SW
- System Requirement State: Approved
- Primary Discipline: SW
- ASIL Rating: QM

#### TFDCX32348-14068: Group 13: Speed suggestion mark (Heading)

##### TFDCX32348-18011: Logic Table - HMI - HMI_ACC_FRAME_RSA (System Requirement)
| No. | Input |  |  | Output |
| --- | --- | --- | --- | --- |
| No. | InternalSignal - IgnMode | CAN Signal Communication Status - ACCRSAC (*1) | CANSignal - ACCRSAC | HMI - HMI_ACC_FRAME_RSA |
| 1 | OFF | x | x | OFF |
| 2 | ON | Communication starting Never Received: 1 Communication Failure: 0 | x | OFF |
| 3 | ON | Communication establishment Never Received: 0 Communication Failure: 0 | 0b | OFF |
| 4 | ON | Communication establishment Never Received: 0 Communication Failure: 0 | 1b | ON |
| 5 | ON | Communication abnormality Never Received: x Communication Failure: 1 | x | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

#### TFDCX32348-14070: Group 14: Speed guide mark (Heading)

##### TFDCX32348-18015: Logic Table - HMI - HMI_ACC_SPEED_UPDOWN_RSA (System Requirement)
| No. | Input |  |  | Output |
| --- | --- | --- | --- | --- |
| No. | InternalSignal - IgnMode | CAN Signal Communication Status - ACCSSAG (*1) | CANSignal - ACCSSAG | HMI - HMI_ACC_SPEED_UPDOWN_ RSA |
| 1 | OFF | x | x | OFF |
| 2 | ON | Communication starting Never Received: 1 Communication Failure: 0 | x | OFF |
| 3 | ON | Communication establishment Never Received: 0 Communication Failure: 0 | 00b | OFF |
| 4 | ON | Communication establishment Never Received: 0 Communication Failure: 0 | 01b | UP |
| 5 | ON | Communication establishment Never Received: 0 Communication Failure: 0 | 10b | DOWN |
| 6 | ON | Communication establishment Never Received: 0 Communication Failure: 0 | 11b | OFF |
| 7 | ON | Communication abnormality Never Received: x Communication Failure: 1 | x | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

#### TFDCX32348-32292: Group 19: SET mark (Heading)

##### TFDCX32348-32293: Logic Table - InternalSignal - ACC_SET_Indicator (System Requirement)
| No. | Input |  |  |  |  |  | Output |
| --- | --- | --- | --- | --- | --- | --- | --- |
| No. | InternalSignal - IgnMode | CAN Signal Communication Status - ACCSP (*1), (*2) | CANSignal - ACCSP | CANSignal - ISALIMID | CANSignal - ERMMAXID | CANSignal - ACCSPST1 | InternalSignal - ACC_SET_Indicator |
| 1 | OFF | x | x | x | x | x | OFF |
| 2 | ON | Communication starting Never Received: 1 Communication Failure: 0 | x | x | x | x | OFF |
| 3 | ON | Communication establishment Never Received: 0 Communication Failure: 0 | 0x01-0xFE | 0b | 0b | 10b | SET (Green) |
| 4 | ON | Communication establishment Never Received: 0 Communication Failure: 0 | 0x01-0xFE | 0b | 0b | Other than 10b | SET (White) |
| 5 | ON | Communication establishment Never Received: 0 Communication Failure: 0 | Other than above |  |  |  | OFF |
| 6 | ON | Communication abnormality Never Received: x Communication Failure: 1 | x | x | x | x | OFF |
(*1) Never Received and Communication Failure is defined in CAN General SRD. Please check the CAN General SRD for details.
(*2) In this table, ACCSPST1, ACCSPEXC, ISALIMID and ERMMAXID are included in the same CAN Msg as ACCSP, so there is no need to check the communication status.
- Verification Criteria: Verify by executing test cases
- Verification Method: Software Qualification Test, System Qualification Test, Unit Test
- Verification Owner: FV, SW
- System Requirement State: Approved
- Primary Discipline: SW
- ASIL Rating: QM

#### TFDCX32348-18108: Group 21: Preceding vehicle (Heading)

##### TFDCX32348-20796: Logic Table - InternalSignal - ACC_Preceding_Vehicle_Presence_Status (System Requirement)
| No. | Input |  |  |  | Output |
| --- | --- | --- | --- | --- | --- |
| No. | InternalSignal - IgnMode | CAN Signal Communication Status - ACCPVTY (*1), (*2) | CANSignal - ACCPVTY | CANSignal - ACCPVST1 | InternalSignal - ACC_Preceding_Vehicle_Presence_Status |
| 1 | OFF | x | x | x | OFF |
| 2 | ON | Communication starting Never Received: 1 Communication Failure: 0 | x | x | OFF |
| 3 | ON | Communication establishment Never Received: 0 Communication Failure: 0 | 000b | x | OFF |
| 4 | ON | Communication establishment Never Received: 0 Communication Failure: 0 | 001b | x | Passenger car |
| 5 | ON | Communication establishment Never Received: 0 Communication Failure: 0 | 010b | x | Truck |
| 6 | ON | Communication establishment Never Received: 0 Communication Failure: 0 | 011b | x | Motorbike |
| 7 | ON | Communication establishment Never Received: 0 Communication Failure: 0 | 100b | Other than 01b | Pedestrian |
| 8 | ON | Communication establishment Never Received: 0 Communication Failure: 0 | 100b | 01b | OFF |
| 9 | ON | Communication establishment Never Received: 0 Communication Failure: 0 | Other than above |  | OFF |
| 10 | ON | Communication abnormality Never Received: x Communication Failure: 1 | x |  | OFF |
(*1) Never Received and Communication Failure is defined in CAN General SRD. Please check the CAN General SRD for details.
(*2) In this table, ACCPVST1 is included in the same CAN Msg as ACCPVTY, so there is no need to check the communication status.
- Verification Criteria: Verify by executing test cases
- Verification Method: Software Qualification Test, System Qualification Test, Unit Test
- Verification Owner: FV, SW
- System Requirement State: Approved
- Primary Discipline: SW
- ASIL Rating: QM

##### TFDCX32348-20798: Logic Table - InternalSignal - ACC_Preceding_Vehicle_Distance (System Requirement)
| No. | Input |  |  | Output |
| --- | --- | --- | --- | --- |
| No. | InternalSignal - IgnMode | CAN Signal Communication Status - ACCPVDST (*1) | CANSignal -ACCPVDST | InternalSignal - ACC_Preceding_Vehicle_Distance |
| 1 | OFF | x | x | OFF |
| 2 | ON | Communication starting Never Received: 1 Communication Failure: 0 | x | Distance 0 |
| 3 | ON | Communication establishment Never Received: 0 Communication Failure: 0 | 000b | Distance 0 |
| 4 | ON | Communication establishment Never Received: 0 Communication Failure: 0 | 001b | Distance 1 |
| 5 | ON | Communication establishment Never Received: 0 Communication Failure: 0 | 010b | Distance 2 |
| 6 | ON | Communication establishment Never Received: 0 Communication Failure: 0 | 011b | Distance 3 |
| 7 | ON | Communication establishment Never Received: 0 Communication Failure: 0 | 100b | Distance 4 |
| 8 | ON | Communication establishment Never Received: 0 Communication Failure: 0 | Other than above | OFF |
| 9 | ON | Communication abnormality Never Received: x Communication Failure: 1 | x | Distance 0 |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-20800: Logic Table - Local Parameter - Preceding_Vehicle_Color (System Requirement)
| No. | Input |  |  | Output |
| --- | --- | --- | --- | --- |
| No. | InternalSignal - IgnMode | CAN Signal Communication Status - ACCPVST1 (*1) | CANSignal - ACCPVST1 | Local Parameter - Preceding_Vehicle_Color |
| 1 | OFF | x | x | OFF |
| 2 | ON | Communication starting Never Received: 1 Communication Failure: 0 | x | OFF |
| 3 | ON | Communication establishment Never Received: 0 Communication Failure: 0 | 00b | OFF |
| 4 | ON | Communication establishment Never Received: 0 Communication Failure: 0 | 01b | White |
| 5 | ON | Communication establishment Never Received: 0 Communication Failure: 0 | 10b | Gray |
| 6 | ON | Communication establishment Never Received: 0 Communication Failure: 0 | 11b | Red |
| 7 | ON | Communication abnormality Never Received: x Communication Failure: 1 | x | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-20802: Logic Table - Local Parameter - Preceding_Vehicle_Blinking (System Requirement)
| No. | Input |  |  | Output |
| --- | --- | --- | --- | --- |
| No. | InternalSignal - IgnMode | CAN Signal Communication Status - ACCPVST2 (*1) | CANSignal - ACCPVST2 | Local Parameter - Preceding_Vehicle_Blinking |
| 1 | OFF | - | - | OFF |
| 2 | ON | Communication starting Never Received: 1 Communication Failure: 0 | x | OFF |
| 3 | ON | Communication establishment Never Received: 0 Communication Failure: 0 | 0b | OFF |
| 4 | ON | Communication establishment Never Received: 0 Communication Failure: 0 | 1b | ON |
| 5 | ON | Communication abnormality Never Received: x Communication Failure: 1 | x | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-13949: Logic Table - HMI - HMI_ACC_PRECEDING_VEHICLE_ICON (Heading)

###### TFDCX32348-28189: HMI - HMI_ACC_PRECEDING_VEHICLE_ICON (1 of 2) (System Requirement)
| No. | Input |  |  | Output | <Info> Meaning |
| --- | --- | --- | --- | --- | --- |
| No. | InternalSignal - ACC_Preceding_Vehicle_Distance | InternalSignal - ACC_Preceding_Vehicle_Presence_Status | Local Parameter - Preceding_Vehicle_Color | HMI - HMI_ACC_PRECEDING_VEHICLE_ICON | <Info> Meaning |
| 1 | OFF | x | x | OFF | For invalid distance value, No preceding vehicle shall be displayed |
| 2 | x | OFF | x | OFF | No preceding vehicle is displayed |
| 3 | x | x | OFF | OFF | For invalid color, No preceding vehicle shall be displayed |
| 4 | x | Pedestrian | White | OFF | No white Pedestrian is displayed |
| 5 | Distance 0 | Passenger car | White | Car_D0_White |  |
| 6 | Distance 0 | Passenger car | Gray | Car_D0_Gray |  |
| 7 | Distance 0 | Passenger car | Red | Car_D0_Red |  |
| 8 | Distance 1 | Passenger car | White | Car_D1_White |  |
| 9 | Distance 1 | Passenger car | Gray | Car_D1_Gray |  |
| 10 | Distance 1 | Passenger car | Red | Car_D1_Red |  |
| 11 | Distance 2 | Passenger car | White | Car_D2_White |  |
| 12 | Distance 2 | Passenger car | Gray | Car_D2_Gray |  |
| 13 | Distance 2 | Passenger car | Red | Car_D2_Red |  |
| 14 | Distance 3 | Passenger car | White | Car_D3_White |  |
| 15 | Distance 3 | Passenger car | Gray | Car_D3_Gray |  |
| 16 | Distance 3 | Passenger car | Red | Car_D3_Red |  |
| 17 | Distance 4 | Passenger car | White | Car_D4_White |  |
| 18 | Distance 4 | Passenger car | Gray | Car_D4_Gray |  |
| 19 | Distance 4 | Passenger car | Red | Car_D4_Red |  |
| 20 | Distance 0 | Truck | White | Truck_D0_White |  |
| 21 | Distance 0 | Truck | Gray | Truck_D0_Gray |  |
| 22 | Distance 0 | Truck | Red | Truck_D0_Red |  |
| 23 | Distance 1 | Truck | White | Truck_D1_White |  |
| 24 | Distance 1 | Truck | Gray | Truck_D1_Gray |  |
| 25 | Distance 1 | Truck | Red | Truck_D1_Red |  |
| 26 | Distance 2 | Truck | White | Truck_D2_White |  |
| 27 | Distance 2 | Truck | Gray | Truck_D2_Gray |  |
| 28 | Distance 2 | Truck | Red | Truck_D2_Red |  |
| 29 | Distance 3 | Truck | White | Truck_D3_White |  |
| 30 | Distance 3 | Truck | Gray | Truck_D3_Gray |  |
| 31 | Distance 3 | Truck | Red | Truck_D3_Red |  |
| 32 | Distance 4 | Truck | White | Truck_D4_White |  |
| 33 | Distance 4 | Truck | Gray | Truck_D4_Gray |  |
| 34 | Distance 4 | Truck | Red | Truck_D4_Red |  |
Continue to next artifact
- Verification Criteria: Verify by executing test cases
- Verification Method: Software Qualification Test, System Qualification Test, Unit Test
- Verification Owner: FV, SW
- System Requirement State: Approved
- Primary Discipline: SW
- ASIL Rating: QM

###### TFDCX32348-33712: HMI - HMI_ACC_PRECEDING_VEHICLE_ICON (2 of 2) (System Requirement)
| No. | Input |  |  | Output | <Info> Meaning |
| --- | --- | --- | --- | --- | --- |
| No. | InternalSignal - ACC_Preceding_Vehicle_Distance | InternalSignal - ACC_Preceding_Vehicle_Presence_Status | Local Parameter - Preceding_Vehicle_Color | HMI - HMI_ACC_PRECEDING_VEHICLE_ICON | <Info> Meaning |
| 35 | Distance 0 | Motorbike | White | Bike_D0_White |  |
| 36 | Distance 0 | Motorbike | Gray | Bike_D0_Gray |  |
| 37 | Distance 0 | Motorbike | Red | Bike_D0_Red |  |
| 38 | Distance 1 | Motorbike | White | Bike_D1_White |  |
| 39 | Distance 1 | Motorbike | Gray | Bike_D1_Gray |  |
| 40 | Distance 1 | Motorbike | Red | Bike_D1_Red |  |
| 41 | Distance 2 | Motorbike | White | Bike_D2_White |  |
| 42 | Distance 2 | Motorbike | Gray | Bike_D2_Gray |  |
| 43 | Distance 2 | Motorbike | Red | Bike_D2_Red |  |
| 44 | Distance 3 | Motorbike | White | Bike_D3_White |  |
| 45 | Distance 3 | Motorbike | Gray | Bike_D3_Gray |  |
| 46 | Distance 3 | Motorbike | Red | Bike_D3_Red |  |
| 47 | Distance 4 | Motorbike | White | Bike_D4_White |  |
| 48 | Distance 4 | Motorbike | Gray | Bike_D4_Gray |  |
| 50 | Distance 4 | Motorbike | Red | Bike_D4_Red |  |
| 51 | Distance 0 | Pedestrian | Gray | Pedestrian_D0_Gray |  |
| 52 | Distance 0 | Pedestrian | Red | Pedestrian_D0_Red |  |
| 53 | Distance 1 | Pedestrian | Gray | Pedestrian_D1_Gray |  |
| 54 | Distance 1 | Pedestrian | Red | Pedestrian_D1_Red |  |
| 55 | Distance 2 | Pedestrian | Gray | Pedestrian_D2_Gray |  |
| 56 | Distance 2 | Pedestrian | Red | Pedestrian_D2_Red |  |
| 57 | Distance 3 | Pedestrian | Gray | Pedestrian_D3_Gray |  |
| 58 | Distance 3 | Pedestrian | Red | Pedestrian_D3_Red |  |
| 59 | Distance 4 | Pedestrian | Gray | Pedestrian_D4_Gray |  |
| 60 | Distance 4 | Pedestrian | Red | Pedestrian_D4_Red |  |
- Verification Criteria: Verify by executing test cases
- Verification Method: Software Qualification Test, System Qualification Test, Unit Test
- Verification Owner: FV, SW
- System Requirement State: Approved
- Primary Discipline: SW
- ASIL Rating: QM

##### TFDCX32348-33696: Logic Table - HMI - HMI_ACC_PRECEDING_VEHICLE_ICON_FWIND (System Requirement)
| No. | Input |  |  | Output | <Info> Meaning |
| --- | --- | --- | --- | --- | --- |
| No. | InternalSignal - ACC_Preceding_Vehicle_Distance | InternalSignal - ACC_Preceding_Vehicle_Presence_Status | Local Parameter - Preceding_Vehicle_Color | HMI_ACC_PRECEDING_VEHICLE_ICON_FWIND | <Info> Meaning |
| 1 | OFF | x | x | OFF | For invalid distance value, No preceding vehicle shall be displayed |
| 2 | x | OFF | x | OFF | No preceding vehicle is displayed |
| 3 | x | x | OFF | OFF | For invalid color, No preceding vehicle shall be displayed |
| 4 | x | Pedestrian | White | OFF | No white Pedestrian is displayed |
| 5 | Distance 0 | Passenger car or Truck or Motorbike | White | Car_D0_White | In F window, three vehicle shall be expressed by same icon. |
| 6 | Distance 0 | Passenger car or Truck or Motorbike | Gray | Car_D0_Gray | In F window, three vehicle shall be expressed by same icon. |
| 7 | Distance 0 | Passenger car or Truck or Motorbike | Red | Car_D0_Red | In F window, three vehicle shall be expressed by same icon. |
| 8 | Distance 1 | Passenger car or Truck or Motorbike | White | Car_D1_White | In F window, three vehicle shall be expressed by same icon. |
| 9 | Distance 1 | Passenger car or Truck or Motorbike | Gray | Car_D1_Gray | In F window, three vehicle shall be expressed by same icon. |
| 10 | Distance 1 | Passenger car or Truck or Motorbike | Red | Car_D1_Red | In F window, three vehicle shall be expressed by same icon. |
| 11 | Distance 2 | Passenger car or Truck or Motorbike | White | Car_D2_White | In F window, three vehicle shall be expressed by same icon. |
| 12 | Distance 2 | Passenger car or Truck or Motorbike | Gray | Car_D2_Gray | In F window, three vehicle shall be expressed by same icon. |
| 13 | Distance 2 | Passenger car or Truck or Motorbike | Red | Car_D2_Red | In F window, three vehicle shall be expressed by same icon. |
| 14 | Distance 3 | Passenger car or Truck or Motorbike | White | Car_D3_White | In F window, three vehicle shall be expressed by same icon. |
| 15 | Distance 3 | Passenger car or Truck or Motorbike | Gray | Car_D3_Gray | In F window, three vehicle shall be expressed by same icon. |
| 16 | Distance 3 | Passenger car or Truck or Motorbike | Red | Car_D3_Red | In F window, three vehicle shall be expressed by same icon. |
| 17 | Distance 4 | Passenger car or Truck or Motorbike | White | Car_D4_White | In F window, three vehicle shall be expressed by same icon. |
| 18 | Distance 4 | Passenger car or Truck or Motorbike | Gray | Car_D4_Gray | In F window, three vehicle shall be expressed by same icon. |
| 19 | Distance 4 | Passenger car or Truck or Motorbike | Red | Car_D4_Red | In F window, three vehicle shall be expressed by same icon. |
| 20 | Distance 0 | Pedestrian | Gray | Pedestrian_D0_Gray |  |
| 21 | Distance 0 | Pedestrian | Red | Pedestrian_D0_Red |  |
| 22 | Distance 1 | Pedestrian | Gray | Pedestrian_D1_Gray |  |
| 23 | Distance 1 | Pedestrian | Red | Pedestrian_D1_Red |  |
| 24 | Distance 2 | Pedestrian | Gray | Pedestrian_D2_Gray |  |
| 25 | Distance 2 | Pedestrian | Red | Pedestrian_D2_Red |  |
| 26 | Distance 3 | Pedestrian | Gray | Pedestrian_D3_Gray |  |
| 27 | Distance 3 | Pedestrian | Red | Pedestrian_D3_Red |  |
| 28 | Distance 4 | Pedestrian | Gray | Pedestrian_D4_Gray |  |
| 29 | Distance 4 | Pedestrian | Red | Pedestrian_D4_Red |  |
- Verification Criteria: Verify by executing test cases
- Verification Method: Software Qualification Test, System Qualification Test, Unit Test
- Verification Owner: FV, SW
- System Requirement State: Approved
- Primary Discipline: SW
- ASIL Rating: QM

##### TFDCX32348-28190: Logic Table - HMI - HMI_ACC_PRECEDING_VEHICLE_BLINK/Warning ID - WRN_ADAS_ACC_G20 (System Requirement)
| No. | Input |  | Output |  |
| --- | --- | --- | --- | --- |
| No. | HMI - HMI_ACC_PRECEDING_VEHICLE_ICON | Local Parameter - Preceding_Vehicle_Blinking | HMI - HMI_ACC_PRECEDING_VEHICLE_BLINK (*1) | Warning ID - WRN_ADAS_ACC_G20 (*2) (*3) |
| 1 | OFF | X | OFF | OFF |
| 2 | Other than above | OFF | OFF | OFF |
| 3 | Other than above | ON | ON | ON |
(*1)Detailed requirements on HMI_ACC_PRECEDING_VEHICLE_BLINK
Case 1. Until 2 cycle time (2,000ms) passes since HMI_ACC_PRECEDING_VEHICLE_BLINK = OFF -> ON is detected, Do not execute No.2 even if Preceding_Vehicle_Blinking = OFF is detected.
Case 2. After 2 cycle time (2,000ms) passes since HMI_ACC_PRECEDING_VEHICLE_BLINK = OFF -> ON is detected, Execute No.2 immediately when Preceding_Vehicle_Blinking = OFF is detected.
Case 3. When HMI_ACC_PRECEDING_VEHICLE_BLINK = OFF is detected, Execute No.1 immediately.
(*2) The same requirements as for HMI_ACC_PRECEDING_VEHICLE_BLINK also apply to the WRN_ADAS_ACC_G20.
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While HM_ACC_PRECEDING_VEHICLE_MOVING_BLINK == ON, Blink control is necessary for Preceding Vehicle Moving icon.
Requirements for Blink control:
1. Cycle time is 1,000ms.
2. ON Duty is 50%.
3. At the beginning of the blinking, Turn on the icon display.
4. Cancel the icon blinking as soon as HMI_ACC_PRECEDING_VEHICLE_BLINK is changed from ON to OFF.
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(*3) For WRN_ADAS_ACC_G20, Update the value immediately when Input condition changes.
- Verification Criteria: Verify by executing test cases
- Verification Method: Software Qualification Test, System Qualification Test, Unit Test
- Verification Owner: FV, SW
- System Requirement State: Approved
- Primary Discipline: SW
- ASIL Rating: QM

#### TFDCX32348-27924: Group 22: Adjacent vehicle (right) (Heading)

##### TFDCX32348-28205: Logic Table - Local Parameter - Adjacent_Vehicle_Type_Right (System Requirement)
| No. | Input |  |  | Output |
| --- | --- | --- | --- | --- |
| No. | Internal Signal - IgnMode | CAN Signal Communication Status - ACCAVTYR (*1) | CANSignal - ACCAVTYR | Local Parameter - Adjacent _Vehicle_Type_Right |
| 1 | OFF | x | x | OFF |
| 2 | ON | Communication Starting Never Received: 1 Communication Failure: 0 | x | OFF |
| 3 | ON | Communication Establishment Never Received: 0 Communication Failure: 0 | 000b | OFF |
| 4 | ON | Communication Establishment Never Received: 0 Communication Failure: 0 | 001b | Passenger car |
| 5 | ON | Communication Establishment Never Received: 0 Communication Failure: 0 | 010b | Truck |
| 6 | ON | Communication Establishment Never Received: 0 Communication Failure: 0 | 011b | Motorbike |
| 7 | ON | Communication Establishment Never Received: 0 Communication Failure: 0 | 100b | Pedestrian |
| 8 | ON | Communication Establishment Never Received: 0 Communication Failure: 0 | Other than above | OFF |
| 9 | ON | Communication Abnormality Never Received: x Communication Failure: 1 | x | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-28212: Logic Table - Local Parameter - Adjacent_Vehicle_Distance_Right (System Requirement)
| No. | Input |  |  | Output |
| --- | --- | --- | --- | --- |
| No. | Internal Signal - IgnMode | CAN Signal Communication Status - ACCAVDTR (*1) | CANSignal - ACCAVDTR | Local Parameter - Adjacent_Vehicle_Distance_Right |
| 1 | OFF | X | X | OFF |
| 2 | ON | Communication Starting Never Received: 1 Communication Failure: 0 | X | OFF |
| 3 | ON | Communication Establishment Never Received: 0 Communication Failure: 0 | 001b | Distance 1 |
| 4 | ON | Communication Establishment Never Received: 0 Communication Failure: 0 | 010b | Distance 2 |
| 5 | ON | Communication Establishment Never Received: 0 Communication Failure: 0 | 011b | Distance 3 |
| 6 | ON | Communication Establishment Never Received: 0 Communication Failure: 0 | 100b | Distance 4 |
| 7 | ON | Communication Establishment Never Received: 0 Communication Failure: 0 | Other than above | OFF |
| 8 | ON | Communication Abnormality Never Received: x Communication Failure: 1 | X | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-28214: Logic Table - Local Parameter - Adjacent_Vehicle_Color_Right (System Requirement)
| No. | Input |  |  | Output |
| --- | --- | --- | --- | --- |
| No. | Internal Signal - IgnMode | CAN Signal Communication Status - ACCAVS1R (*1) | CANSignal - ACCAVS1R | Local Parameter - Adjacent_Vehicle_Color_Right |
| 1 | OFF | X | X | OFF |
| 2 | ON | Communication Starting Never Received: 1 Communication Failure: 0 | X | OFF |
| 3 | ON | Communication Establishment Never Received: 0 Communication Failure: 0 | 00b | OFF |
| 4 | ON | Communication Establishment Never Received: 0 Communication Failure: 0 | 01b | White |
| 5 | ON | Communication Establishment Never Received: 0 Communication Failure: 0 | 10b | Gray |
| 6 | ON | Communication Establishment Never Received: 0 Communication Failure: 0 | 11b | Red |
| 7 | ON | Communication Abnormality Never Received: x Communication Failure: 1 | X | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-28217: Logic Table - Local Parameter - Adjacent_Vehicle_Blinking_Right (System Requirement)
| No. | Input |  |  | Output |
| --- | --- | --- | --- | --- |
| No. | Internal Signal - IgnMode | CAN Signal Communication Status - ACCAVS2R (*1) | CANSignal - ACCAVS2R | Local Parameter - Adjacent_Vehicle_Blinking_Right |
| 1 | OFF | X | X | OFF |
| 2 | ON | Communication Starting Never Received: 1 Communication Failure: 0 | X | OFF |
| 3 | ON | Communication Establishment Never Received: 0 Communication Failure: 0 | 0b | OFF |
| 4 | ON | Communication Establishment Never Received: 0 Communication Failure: 0 | 1b | ON |
| 5 | ON | Communication Abnormality Never Received: x Communication Failure: 1 | X | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-28210: Logic Table - Local Parameter - Adjacent_Vehicle_Position_Right/ Adjacent_Vehicle_Position_Right_FWIND (System Requirement)
| No. | Input |  |  | Output |  |
| --- | --- | --- | --- | --- | --- |
| No. | Internal Signal - IgnMode | CAN Signal Communication Status - ACCAVLPR (*1) | CANSignal - ACCAVLPR | Local Parameter - Adjacent_Vehicle_Position_Right | Local Parameter - Adjacent_Vehicle_Position_Right_FWIND |
| 1 | OFF | x | x | OFF | OFF |
| 2 | ON | Communication Starting Never Received: 1 Communication Failure: 0 | x | OFF | OFF |
| 3 | ON | Communication Establishment Never Received: 0 Communication Failure: 0 | 000b | OFF | OFF |
| 4 | ON | Communication Establishment Never Received: 0 Communication Failure: 0 | 001b | Pos_1 | Center |
| 5 | ON | Communication Establishment Never Received: 0 Communication Failure: 0 | 010b | Pos_2 | Right |
| 6 | ON | Communication Establishment Never Received: 0 Communication Failure: 0 | 011b | Pos_3 | Center |
| 7 | ON | Communication Establishment Never Received: 0 Communication Failure: 0 | 100b | Pos_4 | Right_Type1 |
| 8 | ON | Communication Establishment Never Received: 0 Communication Failure: 0 | 101b | Pos_5 | Center |
| 9 | ON | Communication Establishment Never Received: 0 Communication Failure: 0 | 110b | Pos_6 | Center |
| 10 | ON | Communication Establishment Never Received: 0 Communication Failure: 0 | 111b | Pos_7 | OFF |
| 11 | ON | Communication Abnormality Never Received: x Communication Failure: 1 | x | OFF | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-29122: Logic Table - HMI - HMI_ACC_ADJACENT_VEHICLE_ICON_RIGHT (Heading)

###### TFDCX32348-33889: HMI - HMI_ACC_ADJACENT_VEHICLE_ICON_RIGHT (1 of 7) (System Requirement)
| No. | Input |  |  |  | Output | <Info> Meaning |
| --- | --- | --- | --- | --- | --- | --- |
| No. | Local Parameter - Adjacent_Vehicle_Distance_Right | Local Parameter - Adjacent_Vehicle_Position_Right | Local Parameter - Adjacent_Vehicle_Color_Right | Local Parameter - Adjacent_Vehicle_Type_Right | HMI - HMI_ACC_ADJACENT_VEHICLE_ICON_RIGHT | <Info> Meaning |
| 1 | OFF | x | x | x | OFF | For invalid distance, adjacent vehicle not displayed. |
| 2 | x | OFF | x | x | OFF | For invalid position, adjacent vehicle not displayed. |
| 3 | x | x | OFF | x | OFF | For invalid color, adjacent vehicle not displayed. |
| 4 | x | x | x | OFF | OFF | No adjacent vehicle is detected. |
| 5 | x | Other than Pos_4 | x | Pedestrian | OFF | Pedestrian can't be displayed at other than Pos_4. |
| 6 | x | Pos_4 | White | Pedestrian | OFF | Pedestrian of white color can't be displayed at Pos_4. |
| 7 | Distance 1 | Pos_1 | White | Passenger car | Car_Dis1_Pos1_White |  |
| 8 | Distance 1 | Pos_1 | White | Truck | Truck_Dis1_Pos1_White |  |
| 9 | Distance 1 | Pos_1 | White | Motorbike | Bike_Dis1_Pos1_White |  |
| 10 | Distance 1 | Pos_1 | Gray | Passenger car | Car_Dis1_Pos1_Gray |  |
| 11 | Distance 1 | Pos_1 | Gray | Truck | Truck_Dis1_Pos1_Gray |  |
| 12 | Distance 1 | Pos_1 | Gray | Motorbike | Bike_Dis1_Pos1_Gray |  |
| 13 | Distance 1 | Pos_1 | Red | Passenger car | Car_Dis1_Pos1_Red |  |
| 14 | Distance 1 | Pos_1 | Red | Truck | Truck_Dis1_Pos1_Red |  |
| 15 | Distance 1 | Pos_1 | Red | Motorbike | Bike_Dis1_Pos1_Red |  |
| 16 | Distance 2 | Pos_1 | White | Passenger car | Car_Dis2_Pos1_White |  |
| 17 | Distance 2 | Pos_1 | White | Truck | Truck_Dis2_Pos1_White |  |
| 18 | Distance 2 | Pos_1 | White | Motorbike | Bike_Dis2_Pos1_White |  |
| 19 | Distance 2 | Pos_1 | Gray | Passenger car | Car_Dis2_Pos1_Gray |  |
| 20 | Distance 2 | Pos_1 | Gray | Truck | Truck_Dis2_Pos1_Gray |  |
| 21 | Distance 2 | Pos_1 | Gray | Motorbike | Bike_Dis2_Pos1_Gray |  |
| 22 | Distance 2 | Pos_1 | Red | Passenger car | Car_Dis2_Pos1_Red |  |
| 23 | Distance 2 | Pos_1 | Red | Truck | Truck_Dis2_Pos1_Red |  |
| 24 | Distance 2 | Pos_1 | Red | Motorbike | Bike_Dis2_Pos1_Red |  |
| 25 | Distance 3 | Pos_1 | White | Passenger car | Car_Dis3_Pos1_White |  |
| 26 | Distance 3 | Pos_1 | White | Truck | Truck_Dis3_Pos1_White |  |
| 27 | Distance 3 | Pos_1 | White | Motorbike | Bike_Dis3_Pos1_White |  |
| 28 | Distance 3 | Pos_1 | Gray | Passenger car | Car_Dis3_Pos1_Gray |  |
| 29 | Distance 3 | Pos_1 | Gray | Truck | Truck_Dis3_Pos1_Gray |  |
| 30 | Distance 3 | Pos_1 | Gray | Motorbike | Bike_Dis3_Pos1_Gray |  |
| 31 | Distance 3 | Pos_1 | Red | Passenger car | Car_Dis3_Pos1_Red |  |
| 32 | Distance 3 | Pos_1 | Red | Truck | Truck_Dis3_Pos1_Red |  |
| 33 | Distance 3 | Pos_1 | Red | Motorbike | Bike_Dis3_Pos1_Red |  |
| 34 | Distance 4 | Pos_1 | White | Passenger car | Car_Dis4_Pos1_White |  |
| 35 | Distance 4 | Pos_1 | White | Truck | Truck_Dis4_Pos1_White |  |
| 36 | Distance 4 | Pos_1 | White | Motorbike | Bike_Dis4_Pos1_White |  |
| 37 | Distance 4 | Pos_1 | Gray | Passenger car | Car_Dis4_Pos1_Gray |  |
| 38 | Distance 4 | Pos_1 | Gray | Truck | Truck_Dis4_Pos1_Gray |  |
| 39 | Distance 4 | Pos_1 | Gray | Motorbike | Bike_Dis4_Pos1_Gray |  |
| 40 | Distance 4 | Pos_1 | Red | Passenger car | Car_Dis4_Pos1_Red |  |
| 41 | Distance 4 | Pos_1 | Red | Truck | Truck_Dis4_Pos1_Red |  |
| 42 | Distance 4 | Pos_1 | Red | Motorbike | Bike_Dis4_Pos1_Red |  |
Continue to next artifact
- Verification Criteria: Verify by executing test cases
- Verification Method: Software Qualification Test, System Qualification Test, Unit Test
- Verification Owner: FV, SW
- System Requirement State: Approved
- Primary Discipline: SW
- ASIL Rating: QM

###### TFDCX32348-33920: HMI - HMI_ACC_ADJACENT_VEHICLE_ICON_RIGHT (2 of 7) (System Requirement)
| No. | Input |  |  |  | Output | <Info> Meaning |
| --- | --- | --- | --- | --- | --- | --- |
| No. | Local Parameter - Adjacent_Vehicle_Distance_Right | Local Parameter - Adjacent_Vehicle_Position_Right | Local Parameter - Adjacent_Vehicle_Color_Right | Local Parameter - Adjacent_Vehicle_Type_Right | HMI - HMI_ACC_ADJACENT_VEHICLE_ICON_RIGHT | <Info> Meaning |
| 43 | Distance 1 | Pos_2 | White | Passenger car | Car_Dis1_Pos2_White |  |
| 44 | Distance 1 | Pos_2 | White | Truck | Truck_Dis1_Pos2_White |  |
| 45 | Distance 1 | Pos_2 | White | Motorbike | Bike_Dis1_Pos2_White |  |
| 46 | Distance 1 | Pos_2 | Gray | Passenger car | Car_Dis1_Pos2_Gray |  |
| 47 | Distance 1 | Pos_2 | Gray | Truck | Truck_Dis1_Pos2_Gray |  |
| 48 | Distance 1 | Pos_2 | Gray | Motorbike | Bike_Dis1_Pos2_Gray |  |
| 49 | Distance 1 | Pos_2 | Red | Passenger car | Car_Dis1_Pos2_Red |  |
| 50 | Distance 1 | Pos_2 | Red | Truck | Truck_Dis1_Pos2_Red |  |
| 51 | Distance 1 | Pos_2 | Red | Motorbike | Bike_Dis1_Pos2_Red |  |
| 52 | Distance 2 | Pos_2 | White | Passenger car | Car_Dis2_Pos2_White |  |
| 53 | Distance 2 | Pos_2 | White | Truck | Truck_Dis2_Pos2_White |  |
| 54 | Distance 2 | Pos_2 | White | Motorbike | Bike_Dis2_Pos2_White |  |
| 55 | Distance 2 | Pos_2 | Gray | Passenger car | Car_Dis2_Pos2_Gray |  |
| 56 | Distance 2 | Pos_2 | Gray | Truck | Truck_Dis2_Pos2_Gray |  |
| 57 | Distance 2 | Pos_2 | Gray | Motorbike | Bike_Dis2_Pos2_Gray |  |
| 58 | Distance 2 | Pos_2 | Red | Passenger car | Car_Dis2_Pos2_Red |  |
| 59 | Distance 2 | Pos_2 | Red | Truck | Truck_Dis2_Pos2_Red |  |
| 60 | Distance 2 | Pos_2 | Red | Motorbike | Bike_Dis2_Pos2_Red |  |
| 61 | Distance 3 | Pos_2 | White | Passenger car | Car_Dis3_Pos2_White |  |
| 62 | Distance 3 | Pos_2 | White | Truck | Truck_Dis3_Pos2_White |  |
| 63 | Distance 3 | Pos_2 | White | Motorbike | Bike_Dis3_Pos2_White |  |
| 64 | Distance 3 | Pos_2 | Gray | Passenger car | Car_Dis3_Pos2_Gray |  |
| 65 | Distance 3 | Pos_2 | Gray | Truck | Truck_Dis3_Pos2_Gray |  |
| 66 | Distance 3 | Pos_2 | Gray | Motorbike | Bike_Dis3_Pos2_Gray |  |
| 67 | Distance 3 | Pos_2 | Red | Passenger car | Car_Dis3_Pos2_Red |  |
| 68 | Distance 3 | Pos_2 | Red | Truck | Truck_Dis3_Pos2_Red |  |
| 69 | Distance 3 | Pos_2 | Red | Motorbike | Bike_Dis3_Pos2_Red |  |
| 70 | Distance 4 | Pos_2 | White | Passenger car | Car_Dis4_Pos2_White |  |
| 71 | Distance 4 | Pos_2 | White | Truck | Truck_Dis4_Pos2_White |  |
| 72 | Distance 4 | Pos_2 | White | Motorbike | Bike_Dis4_Pos2_White |  |
| 73 | Distance 4 | Pos_2 | Gray | Passenger car | Car_Dis4_Pos2_Gray |  |
| 74 | Distance 4 | Pos_2 | Gray | Truck | Truck_Dis4_Pos2_Gray |  |
| 75 | Distance 4 | Pos_2 | Gray | Motorbike | Bike_Dis4_Pos2_Gray |  |
| 76 | Distance 4 | Pos_2 | Red | Passenger car | Car_Dis4_Pos2_Red |  |
| 77 | Distance 4 | Pos_2 | Red | Truck | Truck_Dis4_Pos2_Red |  |
| 78 | Distance 4 | Pos_2 | Red | Motorbike | Bike_Dis4_Pos2_Red |  |
Continue to next artifact
- Verification Criteria: Verify by executing test cases
- Verification Method: Software Qualification Test, System Qualification Test, Unit Test
- Verification Owner: FV, SW
- System Requirement State: Approved
- Primary Discipline: SW
- ASIL Rating: QM

###### TFDCX32348-33930: HMI - HMI_ACC_ADJACENT_VEHICLE_ICON_RIGHT (3 of 7) (System Requirement)
| No. | Input |  |  |  | Output | <Info> Meaning |
| --- | --- | --- | --- | --- | --- | --- |
| No. | Local Parameter - Adjacent_Vehicle_Distance_Right | Local Parameter - Adjacent_Vehicle_Position_Right | Local Parameter - Adjacent_Vehicle_Color_Right | Local Parameter - Adjacent_Vehicle_Type_Right | HMI - HMI_ACC_ADJACENT_VEHICLE_ICON_RIGHT | <Info> Meaning |
| 79 | Distance 1 | Pos_3 | White | Passenger car | Car_Dis1_Pos3_White |  |
| 80 | Distance 1 | Pos_3 | White | Truck | Truck_Dis1_Pos3_White |  |
| 81 | Distance 1 | Pos_3 | White | Motorbike | Bike_Dis1_Pos3_White |  |
| 82 | Distance 1 | Pos_3 | Gray | Passenger car | Car_Dis1_Pos3_Gray |  |
| 83 | Distance 1 | Pos_3 | Gray | Truck | Truck_Dis1_Pos3_Gray |  |
| 84 | Distance 1 | Pos_3 | Gray | Motorbike | Bike_Dis1_Pos3_Gray |  |
| 85 | Distance 1 | Pos_3 | Red | Passenger car | Car_Dis1_Pos3_Red |  |
| 86 | Distance 1 | Pos_3 | Red | Truck | Truck_Dis1_Pos3_Red |  |
| 87 | Distance 1 | Pos_3 | Red | Motorbike | Bike_Dis1_Pos3_Red |  |
| 88 | Distance 2 | Pos_3 | White | Passenger car | Car_Dis2_Pos3_White |  |
| 89 | Distance 2 | Pos_3 | White | Truck | Truck_Dis2_Pos3_White |  |
| 90 | Distance 2 | Pos_3 | White | Motorbike | Bike_Dis2_Pos3_White |  |
| 91 | Distance 2 | Pos_3 | Gray | Passenger car | Car_Dis2_Pos3_Gray |  |
| 92 | Distance 2 | Pos_3 | Gray | Truck | Truck_Dis2_Pos3_Gray |  |
| 93 | Distance 2 | Pos_3 | Gray | Motorbike | Bike_Dis2_Pos3_Gray |  |
| 94 | Distance 2 | Pos_3 | Red | Passenger car | Car_Dis2_Pos3_Red |  |
| 95 | Distance 2 | Pos_3 | Red | Truck | Truck_Dis2_Pos3_Red |  |
| 96 | Distance 2 | Pos_3 | Red | Motorbike | Bike_Dis2_Pos3_Red |  |
| 97 | Distance 3 | Pos_3 | White | Passenger car | Car_Dis3_Pos3_White |  |
| 98 | Distance 3 | Pos_3 | White | Truck | Truck_Dis3_Pos3_White |  |
| 99 | Distance 3 | Pos_3 | White | Motorbike | Bike_Dis3_Pos3_White |  |
| 100 | Distance 3 | Pos_3 | Gray | Passenger car | Car_Dis3_Pos3_Gray |  |
| 101 | Distance 3 | Pos_3 | Gray | Truck | Truck_Dis3_Pos3_Gray |  |
| 102 | Distance 3 | Pos_3 | Gray | Motorbike | Bike_Dis3_Pos3_Gray |  |
| 103 | Distance 3 | Pos_3 | Red | Passenger car | Car_Dis3_Pos3_Red |  |
| 104 | Distance 3 | Pos_3 | Red | Truck | Truck_Dis3_Pos3_Red |  |
| 105 | Distance 3 | Pos_3 | Red | Motorbike | Bike_Dis3_Pos3_Red |  |
| 106 | Distance 4 | Pos_3 | White | Passenger car | Car_Dis4_Pos3_White |  |
| 107 | Distance 4 | Pos_3 | White | Truck | Truck_Dis4_Pos3_White |  |
| 108 | Distance 4 | Pos_3 | White | Motorbike | Bike_Dis4_Pos3_White |  |
| 109 | Distance 4 | Pos_3 | Gray | Passenger car | Car_Dis4_Pos3_Gray |  |
| 110 | Distance 4 | Pos_3 | Gray | Truck | Truck_Dis4_Pos3_Gray |  |
| 111 | Distance 4 | Pos_3 | Gray | Motorbike | Bike_Dis4_Pos3_Gray |  |
| 112 | Distance 4 | Pos_3 | Red | Passenger car | Car_Dis4_Pos3_Red |  |
| 113 | Distance 4 | Pos_3 | Red | Truck | Truck_Dis4_Pos3_Red |  |
| 114 | Distance 4 | Pos_3 | Red | Motorbike | Bike_Dis4_Pos3_Red |  |
Continue to next artifact
- Verification Criteria: Verify by executing test cases
- Verification Method: Software Qualification Test, System Qualification Test, Unit Test
- Verification Owner: FV, SW
- System Requirement State: Approved
- Primary Discipline: SW
- ASIL Rating: QM

###### TFDCX32348-33932: HMI - HMI_ACC_ADJACENT_VEHICLE_ICON_RIGHT (4 of 7) (System Requirement)
| No. | Input |  |  |  | Output | <Info> Meaning |
| --- | --- | --- | --- | --- | --- | --- |
| No. | Local Parameter - Adjacent_Vehicle_Distance_Right | Local Parameter - Adjacent_Vehicle_Position_Right | Local Parameter - Adjacent_Vehicle_Color_Right | Local Parameter - Adjacent_Vehicle_Type_Right | HMI - HMI_ACC_ADJACENT_VEHICLE_ICON_RIGHT | <Info> Meaning |
| 115 | Distance 1 | Pos_4 | White | Passenger car | Car_Dis1_Pos4_White |  |
| 116 | Distance 1 | Pos_4 | White | Truck | Truck_Dis1_Pos4_White |  |
| 117 | Distance 1 | Pos_4 | White | Motorbike | Bike_Dis1_Pos4_White |  |
| 118 | Distance 1 | Pos_4 | Gray | Passenger car | Car_Dis1_Pos4_Gray |  |
| 119 | Distance 1 | Pos_4 | Gray | Truck | Truck_Dis1_Pos4_Gray |  |
| 120 | Distance 1 | Pos_4 | Gray | Motorbike | Bike_Dis1_Pos4_Gray |  |
| 121 | Distance 1 | Pos_4 | Gray | Pedestrian | Pedestrian_Dis1_Pos4_Gray |  |
| 122 | Distance 1 | Pos_4 | Red | Passenger car | Car_Dis1_Pos4_Red |  |
| 123 | Distance 1 | Pos_4 | Red | Truck | Truck_Dis1_Pos4_Red |  |
| 124 | Distance 1 | Pos_4 | Red | Motorbike | Bike_Dis1_Pos4_Red |  |
| 125 | Distance 1 | Pos_4 | Red | Pedestrian | Pedestrian_Dis1_Pos4_Red |  |
| 126 | Distance 2 | Pos_4 | White | Passenger car | Car_Dis2_Pos4_White |  |
| 127 | Distance 2 | Pos_4 | White | Truck | Truck_Dis2_Pos4_White |  |
| 128 | Distance 2 | Pos_4 | White | Motorbike | Bike_Dis2_Pos4_White |  |
| 129 | Distance 2 | Pos_4 | Gray | Passenger car | Car_Dis2_Pos4_Gray |  |
| 130 | Distance 2 | Pos_4 | Gray | Truck | Truck_Dis2_Pos4_Gray |  |
| 131 | Distance 2 | Pos_4 | Gray | Motorbike | Bike_Dis2_Pos4_Gray |  |
| 132 | Distance 2 | Pos_4 | Gray | Pedestrian | Pedestrian_Dis2_Pos4_Gray |  |
| 133 | Distance 2 | Pos_4 | Red | Passenger car | Car_Dis2_Pos4_Red |  |
| 134 | Distance 2 | Pos_4 | Red | Truck | Truck_Dis2_Pos4_Red |  |
| 135 | Distance 2 | Pos_4 | Red | Motorbike | Bike_Dis2_Pos4_Red |  |
| 136 | Distance 2 | Pos_4 | Red | Pedestrian | Pedestrian_Dis2_Pos4_Red |  |
| 137 | Distance 3 | Pos_4 | White | Passenger car | Car_Dis3_Pos4_White |  |
| 138 | Distance 3 | Pos_4 | White | Truck | Truck_Dis3_Pos4_White |  |
| 139 | Distance 3 | Pos_4 | White | Motorbike | Bike_Dis3_Pos4_White |  |
| 140 | Distance 3 | Pos_4 | Gray | Passenger car | Car_Dis3_Pos4_Gray |  |
| 141 | Distance 3 | Pos_4 | Gray | Truck | Truck_Dis3_Pos4_Gray |  |
| 142 | Distance 3 | Pos_4 | Gray | Motorbike | Bike_Dis3_Pos4_Gray |  |
| 143 | Distance 3 | Pos_4 | Gray | Pedestrian | Pedestrian_Dis3_Pos4_Gray |  |
| 144 | Distance 3 | Pos_4 | Red | Passenger car | Car_Dis3_Pos4_Red |  |
| 145 | Distance 3 | Pos_4 | Red | Truck | Truck_Dis3_Pos4_Red |  |
| 146 | Distance 3 | Pos_4 | Red | Motorbike | Bike_Dis3_Pos4_Red |  |
| 147 | Distance 3 | Pos_4 | Red | Pedestrian | Pedestrian_Dis3_Pos4_Red |  |
| 148 | Distance 4 | Pos_4 | White | Passenger car | Car_Dis4_Pos4_White |  |
| 149 | Distance 4 | Pos_4 | White | Truck | Truck_Dis4_Pos4_White |  |
| 150 | Distance 4 | Pos_4 | White | Motorbike | Bike_Dis4_Pos4_White |  |
| 151 | Distance 4 | Pos_4 | Gray | Passenger car | Car_Dis4_Pos4_Gray |  |
| 152 | Distance 4 | Pos_4 | Gray | Truck | Truck_Dis4_Pos4_Gray |  |
| 153 | Distance 4 | Pos_4 | Gray | Motorbike | Bike_Dis4_Pos4_Gray |  |
| 154 | Distance 4 | Pos_4 | Gray | Pedestrian | Pedestrian_Dis4_Pos4_Gray |  |
| 155 | Distance 4 | Pos_4 | Red | Passenger car | Car_Dis4_Pos4_Red |  |
| 156 | Distance 4 | Pos_4 | Red | Truck | Truck_Dis4_Pos4_Red |  |
| 157 | Distance 4 | Pos_4 | Red | Motorbike | Bike_Dis4_Pos4_Red |  |
| 158 | Distance 4 | Pos_4 | Red | Pedestrian | Pedestrian_Dis4_Pos4_Red |  |
Continue to next artifact
- Verification Criteria: Verify by executing test cases
- Verification Method: Software Qualification Test, System Qualification Test, Unit Test
- Verification Owner: FV, SW
- System Requirement State: Approved
- Primary Discipline: SW
- ASIL Rating: QM

###### TFDCX32348-33944: HMI - HMI_ACC_ADJACENT_VEHICLE_ICON_RIGHT (5 of 7) (System Requirement)
| No. | Input |  |  |  | Output | <Info> Meaning |
| --- | --- | --- | --- | --- | --- | --- |
| No. | Local Parameter - Adjacent_Vehicle_Distance_Right | Local Parameter - Adjacent_Vehicle_Position_Right | Local Parameter - Adjacent_Vehicle_Color_Right | Local Parameter - Adjacent_Vehicle_Type_Right | HMI - HMI_ACC_ADJACENT_VEHICLE_ICON_RIGHT | <Info> Meaning |
| 159 | Distance 1 | Pos_5 | White | Passenger car | Car_Dis1_Pos5_White |  |
| 160 | Distance 1 | Pos_5 | White | Truck | Truck_Dis1_Pos5_White |  |
| 161 | Distance 1 | Pos_5 | White | Motorbike | Bike_Dis1_Pos5_White |  |
| 162 | Distance 1 | Pos_5 | Gray | Passenger car | Car_Dis1_Pos5_Gray |  |
| 163 | Distance 1 | Pos_5 | Gray | Truck | Truck_Dis1_Pos5_Gray |  |
| 164 | Distance 1 | Pos_5 | Gray | Motorbike | Bike_Dis1_Pos5_Gray |  |
| 165 | Distance 1 | Pos_5 | Red | Passenger car | Car_Dis1_Pos5_Red |  |
| 166 | Distance 1 | Pos_5 | Red | Truck | Truck_Dis1_Pos5_Red |  |
| 167 | Distance 1 | Pos_5 | Red | Motorbike | Bike_Dis1_Pos5_Red |  |
| 168 | Distance 2 | Pos_5 | White | Passenger car | Car_Dis2_Pos5_White |  |
| 169 | Distance 2 | Pos_5 | White | Truck | Truck_Dis2_Pos5_White |  |
| 170 | Distance 2 | Pos_5 | White | Motorbike | Bike_Dis2_Pos5_White |  |
| 171 | Distance 2 | Pos_5 | Gray | Passenger car | Car_Dis2_Pos5_Gray |  |
| 172 | Distance 2 | Pos_5 | Gray | Truck | Truck_Dis2_Pos5_Gray |  |
| 173 | Distance 2 | Pos_5 | Gray | Motorbike | Bike_Dis2_Pos5_Gray |  |
| 174 | Distance 2 | Pos_5 | Red | Passenger car | Car_Dis2_Pos5_Red |  |
| 175 | Distance 2 | Pos_5 | Red | Truck | Truck_Dis2_Pos5_Red |  |
| 176 | Distance 2 | Pos_5 | Red | Motorbike | Bike_Dis2_Pos5_Red |  |
| 177 | Distance 3 | Pos_5 | White | Passenger car | Car_Dis3_Pos5_White |  |
| 178 | Distance 3 | Pos_5 | White | Truck | Truck_Dis3_Pos5_White |  |
| 179 | Distance 3 | Pos_5 | White | Motorbike | Bike_Dis3_Pos5_White |  |
| 180 | Distance 3 | Pos_5 | Gray | Passenger car | Car_Dis3_Pos5_Gray |  |
| 181 | Distance 3 | Pos_5 | Gray | Truck | Truck_Dis3_Pos5_Gray |  |
| 182 | Distance 3 | Pos_5 | Gray | Motorbike | Bike_Dis3_Pos5_Gray |  |
| 183 | Distance 3 | Pos_5 | Red | Passenger car | Car_Dis3_Pos5_Red |  |
| 184 | Distance 3 | Pos_5 | Red | Truck | Truck_Dis3_Pos5_Red |  |
| 185 | Distance 3 | Pos_5 | Red | Motorbike | Bike_Dis3_Pos5_Red |  |
| 186 | Distance 4 | Pos_5 | White | Passenger car | Car_Dis4_Pos5_White |  |
| 187 | Distance 4 | Pos_5 | White | Truck | Truck_Dis4_Pos5_White |  |
| 188 | Distance 4 | Pos_5 | White | Motorbike | Bike_Dis4_Pos5_White |  |
| 189 | Distance 4 | Pos_5 | Gray | Passenger car | Car_Dis4_Pos5_Gray |  |
| 190 | Distance 4 | Pos_5 | Gray | Truck | Truck_Dis4_Pos5_Gray |  |
| 191 | Distance 4 | Pos_5 | Gray | Motorbike | Bike_Dis4_Pos5_Gray |  |
| 192 | Distance 4 | Pos_5 | Red | Passenger car | Car_Dis4_Pos5_Red |  |
| 193 | Distance 4 | Pos_5 | Red | Truck | Truck_Dis4_Pos5_Red |  |
| 194 | Distance 4 | Pos_5 | Red | Motorbike | Bike_Dis4_Pos5_Red |  |
Continue to next artifact
- Verification Criteria: Verify by executing test cases
- Verification Method: Software Qualification Test, System Qualification Test, Unit Test
- Verification Owner: FV, SW
- System Requirement State: Approved
- Primary Discipline: SW
- ASIL Rating: QM

###### TFDCX32348-33949: HMI - HMI_ACC_ADJACENT_VEHICLE_ICON_RIGHT (6 of 7) (System Requirement)
| No. | Input |  |  |  | Output | <Info> Meaning |
| --- | --- | --- | --- | --- | --- | --- |
| No. | Local Parameter - Adjacent_Vehicle_Distance_Right | Local Parameter - Adjacent_Vehicle_Position_Right | Local Parameter - Adjacent_Vehicle_Color_Right | Local Parameter - Adjacent_Vehicle_Type_Right | HMI - HMI_ACC_ADJACENT_VEHICLE_ICON_RIGHT | <Info> Meaning |
| 195 | Distance 1 | Pos_6 | White | Passenger car | Car_Dis1_Pos6_White |  |
| 196 | Distance 1 | Pos_6 | White | Truck | Truck_Dis1_Pos6_White |  |
| 197 | Distance 1 | Pos_6 | White | Motorbike | Bike_Dis1_Pos6_White |  |
| 198 | Distance 1 | Pos_6 | Gray | Passenger car | Car_Dis1_Pos6_Gray |  |
| 199 | Distance 1 | Pos_6 | Gray | Truck | Truck_Dis1_Pos6_Gray |  |
| 200 | Distance 1 | Pos_6 | Gray | Motorbike | Bike_Dis1_Pos6_Gray |  |
| 201 | Distance 1 | Pos_6 | Red | Passenger car | Car_Dis1_Pos6_Red |  |
| 202 | Distance 1 | Pos_6 | Red | Truck | Truck_Dis1_Pos6_Red |  |
| 203 | Distance 1 | Pos_6 | Red | Motorbike | Bike_Dis1_Pos6_Red |  |
| 204 | Distance 2 | Pos_6 | White | Passenger car | Car_Dis2_Pos6_White |  |
| 205 | Distance 2 | Pos_6 | White | Truck | Truck_Dis2_Pos6_White |  |
| 206 | Distance 2 | Pos_6 | White | Motorbike | Bike_Dis2_Pos6_White |  |
| 207 | Distance 2 | Pos_6 | Gray | Passenger car | Car_Dis2_Pos6_Gray |  |
| 208 | Distance 2 | Pos_6 | Gray | Truck | Truck_Dis2_Pos6_Gray |  |
| 209 | Distance 2 | Pos_6 | Gray | Motorbike | Bike_Dis2_Pos6_Gray |  |
| 210 | Distance 2 | Pos_6 | Red | Passenger car | Car_Dis2_Pos6_Red |  |
| 211 | Distance 2 | Pos_6 | Red | Truck | Truck_Dis2_Pos6_Red |  |
| 212 | Distance 2 | Pos_6 | Red | Motorbike | Bike_Dis2_Pos6_Red |  |
| 213 | Distance 3 | Pos_6 | White | Passenger car | Car_Dis3_Pos6_White |  |
| 214 | Distance 3 | Pos_6 | White | Truck | Truck_Dis3_Pos6_White |  |
| 215 | Distance 3 | Pos_6 | White | Motorbike | Bike_Dis3_Pos6_White |  |
| 216 | Distance 3 | Pos_6 | Gray | Passenger car | Car_Dis3_Pos6_Gray |  |
| 217 | Distance 3 | Pos_6 | Gray | Truck | Truck_Dis3_Pos6_Gray |  |
| 218 | Distance 3 | Pos_6 | Gray | Motorbike | Bike_Dis3_Pos6_Gray |  |
| 219 | Distance 3 | Pos_6 | Red | Passenger car | Car_Dis3_Pos6_Red |  |
| 220 | Distance 3 | Pos_6 | Red | Truck | Truck_Dis3_Pos6_Red |  |
| 221 | Distance 3 | Pos_6 | Red | Motorbike | Bike_Dis3_Pos6_Red |  |
| 222 | Distance 4 | Pos_6 | White | Passenger car | Car_Dis4_Pos6_White |  |
| 223 | Distance 4 | Pos_6 | White | Truck | Truck_Dis4_Pos6_White |  |
| 224 | Distance 4 | Pos_6 | White | Motorbike | Bike_Dis4_Pos6_White |  |
| 225 | Distance 4 | Pos_6 | Gray | Passenger car | Car_Dis4_Pos6_Gray |  |
| 226 | Distance 4 | Pos_6 | Gray | Truck | Truck_Dis4_Pos6_Gray |  |
| 227 | Distance 4 | Pos_6 | Gray | Motorbike | Bike_Dis4_Pos6_Gray |  |
| 228 | Distance 4 | Pos_6 | Red | Passenger car | Car_Dis4_Pos6_Red |  |
| 229 | Distance 4 | Pos_6 | Red | Truck | Truck_Dis4_Pos6_Red |  |
| 230 | Distance 4 | Pos_6 | Red | Motorbike | Bike_Dis4_Pos6_Red |  |
Continue to next artifact
- Verification Criteria: Verify by executing test cases
- Verification Method: Software Qualification Test, System Qualification Test, Unit Test
- Verification Owner: FV, SW
- System Requirement State: Approved
- Primary Discipline: SW
- ASIL Rating: QM

###### TFDCX32348-33962: HMI - HMI_ACC_ADJACENT_VEHICLE_ICON_RIGHT (7 of 7) (System Requirement)
| No. | Input |  |  |  | Output | <Info> Meaning |
| --- | --- | --- | --- | --- | --- | --- |
| No. | Local Parameter - Adjacent_Vehicle_Distance_Right | Local Parameter - Adjacent_Vehicle_Position_Right | Local Parameter - Adjacent_Vehicle_Color_Right | Local Parameter - Adjacent_Vehicle_Type_Right | HMI - HMI_ACC_ADJACENT_VEHICLE_ICON_RIGHT | <Info> Meaning |
| 231 | Distance 1 | Pos_7 | x | Passenger car | Car_Dis1_Pos7_Gray | Pos_7 is gray only |
| 232 | Distance 1 | Pos_7 | x | Truck | Truck_Dis1_Pos7_Gray | Pos_7 is gray only |
| 233 | Distance 1 | Pos_7 | x | Motorbike | Bike_Dis1_Pos7_Gray | Pos_7 is gray only |
| 234 | Distance 2 | Pos_7 | x | Passenger car | Car_Dis2_Pos7_Gray | Pos_7 is gray only |
| 235 | Distance 2 | Pos_7 | x | Truck | Truck_Dis2_Pos7_Gray | Pos_7 is gray only |
| 236 | Distance 2 | Pos_7 | x | Motorbike | Bike_Dis2_Pos7_Gray | Pos_7 is gray only |
| 237 | Distance 3 | Pos_7 | x | Passenger car | Car_Dis3_Pos7_Gray | Pos_7 is gray only |
| 238 | Distance 3 | Pos_7 | x | Truck | Truck_Dis3_Pos7_Gray | Pos_7 is gray only |
| 239 | Distance 3 | Pos_7 | x | Motorbike | Bike_Dis3_Pos7_Gray | Pos_7 is gray only |
| 240 | Distance 4 | Pos_7 | x | Passenger car | Car_Dis4_Pos7_Gray | Pos_7 is gray only |
| 241 | Distance 4 | Pos_7 | x | Truck | Truck_Dis4_Pos7_Gray | Pos_7 is gray only |
| 242 | Distance 4 | Pos_7 | x | Motorbike | Bike_Dis4_Pos7_Gray | Pos_7 is gray only |
- Verification Criteria: Verify by executing test cases
- Verification Method: Software Qualification Test, System Qualification Test, Unit Test
- Verification Owner: FV, SW
- System Requirement State: Approved
- Primary Discipline: SW
- ASIL Rating: QM

##### TFDCX32348-28228: Logic Table - HMI - HMI_ACC_ADJACENT_VEHICLE_ICON_RIGHT_FWIND (Heading)

###### TFDCX32348-33984: HMI - HMI_ACC_ADJACENT_VEHICLE_ICON_RIGHT_FWIND (1 of 2) (System Requirement)
| No. | Input |  |  |  | Output | <Info> Meaning |
| --- | --- | --- | --- | --- | --- | --- |
| No. | Local Parameter - Adjacent_Vehicle_Distance_Right | Adjacent_Vehicle_Position_Right_FWIND | Local Parameter - Adjacent_Vehicle_Color_Right | Local Parameter - Adjacent_Vehicle_Type_Right | HMI - HMI_ACC_ADJACENT_VEHICLE_ICON_RIGHT_FWIND | <Info> Meaning |
| 1 | OFF | x | x | x | OFF | For invalid distance, adjacent vehicle not displayed. |
| 2 | x | OFF | x | x | OFF | For invalid position, adjacent vehicle not displayed. |
| 3 | x | x | OFF | x | OFF | For invalid color, adjacent vehicle not displayed. |
| 4 | x | x | x | OFF | OFF | No adjacent vehicle is detected. |
| 5 | x | Other than Right_Type1 | x | Pedestrian | OFF | Pedestrian can't be displayed at other than Right_Type1. |
| 6 | x | Right_Type1 | White | Pedestrian | OFF | Pedestrian of white color can't be displayed at Right_Type1. |
| 7 | Distance 1 | Center | White | Passenger car or Truck or Motorbike | Car_Dis1_Center_White |  |
| 8 | Distance 1 | Center | Gray | Passenger car or Truck or Motorbike | Car_Dis1_Center_Gray |  |
| 9 | Distance 1 | Center | Red | Passenger car or Truck or Motorbike | Car_Dis1_Center_Red |  |
| 10 | Distance 2 | Center | White | Passenger car or Truck or Motorbike | Car_Dis2_Center_White |  |
| 11 | Distance 2 | Center | Gray | Passenger car or Truck or Motorbike | Car_Dis2_Center_Gray |  |
| 12 | Distance 2 | Center | Red | Passenger car or Truck or Motorbike | Car_Dis2_Center_Red |  |
| 13 | Distance 3 | Center | White | Passenger car or Truck or Motorbike | Car_Dis3_Center_White |  |
| 14 | Distance 3 | Center | Gray | Passenger car or Truck or Motorbike | Car_Dis3_Center_Gray |  |
| 15 | Distance 3 | Center | Red | Passenger car or Truck or Motorbike | Car_Dis3_Center_Red |  |
| 16 | Distance 4 | Center | White | Passenger car or Truck or Motorbike | Car_Dis4_Center_White |  |
| 17 | Distance 4 | Center | Gray | Passenger car or Truck or Motorbike | Car_Dis4_Center_Gray |  |
| 18 | Distance 4 | Center | Red | Passenger car or Truck or Motorbike | Car_Dis4_Center_Red |  |
| 19 | Distance 1 | Right | White | Passenger car or Truck or Motorbike | Car_Dis1_Right_White |  |
| 20 | Distance 1 | Right | Gray | Passenger car or Truck or Motorbike | Car_Dis1_Right_Gray |  |
| 21 | Distance 1 | Right | Red | Passenger car or Truck or Motorbike | Car_Dis1_Right_Red |  |
| 22 | Distance 2 | Right | White | Passenger car or Truck or Motorbike | Car_Dis2_Right_White |  |
| 23 | Distance 2 | Right | Gray | Passenger car or Truck or Motorbike | Car_Dis2_Right_Gray |  |
| 24 | Distance 2 | Right | Red | Passenger car or Truck or Motorbike | Car_Dis2_Right_Red |  |
| 25 | Distance 3 | Right | White | Passenger car or Truck or Motorbike | Car_Dis3_Right_White |  |
| 26 | Distance 3 | Right | Gray | Passenger car or Truck or Motorbike | Car_Dis3_Right_Gray |  |
| 27 | Distance 3 | Right | Red | Passenger car or Truck or Motorbike | Car_Dis3_Right_Red |  |
| 28 | Distance 4 | Right | White | Passenger car or Truck or Motorbike | Car_Dis4_Right_White |  |
| 29 | Distance 4 | Right | Gray | Passenger car or Truck or Motorbike | Car_Dis4_Right_Gray |  |
| 30 | Distance 4 | Right | Red | Passenger car or Truck or Motorbike | Car_Dis4_Right_Red |  |
Continue to next artifact
- Verification Criteria: Verify by executing test cases
- Verification Method: Software Qualification Test, System Qualification Test, Unit Test
- Verification Owner: FV, SW
- System Requirement State: Approved
- Primary Discipline: SW
- ASIL Rating: QM

###### TFDCX32348-33992: HMI - HMI_ACC_ADJACENT_VEHICLE_ICON_RIGHT_FWIND (2 of 2) (System Requirement)
| No. | Input |  |  |  | Output | <Info> Meaning |
| --- | --- | --- | --- | --- | --- | --- |
| No. | Local Parameter - Adjacent_Vehicle_Distance_Right | Adjacent_Vehicle_Position_Right_FWIND | Local Parameter - Adjacent_Vehicle_Color_Right | Local Parameter - Adjacent_Vehicle_Type_Right | HMI - HMI_ACC_ADJACENT_VEHICLE_ICON_RIGHT_FWIND | <Info> Meaning |
| 31 | Distance 1 | Right_Type1 | White | Passenger car or Truck or Motorbike | Car_Dis1_Right_1_White |  |
| 32 | Distance 1 | Right_Type1 | Gray | Passenger car or Truck or Motorbike | Car_Dis1_Right_1_Gray |  |
| 33 | Distance 1 | Right_Type1 | Gray | Pedestrian | Pedestrian_Dis1_Right_1_Gray |  |
| 34 | Distance 1 | Right_Type1 | Red | Passenger car or Truck or Motorbike | Car_Dis1_Right_1_Red |  |
| 35 | Distance 1 | Right_Type1 | Red | Pedestrian | Pedestrian_Dis1_Right_1_Amber |  |
| 36 | Distance 2 | Right_Type1 | White | Passenger car or Truck or Motorbike | Car_Dis2_Right_1_White |  |
| 37 | Distance 2 | Right_Type1 | Gray | Passenger car or Truck or Motorbike | Car_Dis2_Right_1_Gray |  |
| 38 | Distance 2 | Right_Type1 | Gray | Pedestrian | Pedestrian_Dis2_Right_1_Gray |  |
| 39 | Distance 2 | Right_Type1 | Red | Passenger car or Truck or Motorbike | Car_Dis2_Right_1_Red |  |
| 40 | Distance 2 | Right_Type1 | Red | Pedestrian | Pedestrian_Dis2_Right_1_Amber |  |
| 41 | Distance 3 | Right_Type1 | White | Passenger car or Truck or Motorbike | Car_Dis3_Right_1_White |  |
| 42 | Distance 3 | Right_Type1 | Gray | Passenger car or Truck or Motorbike | Car_Dis3_Right_1_Gray |  |
| 43 | Distance 3 | Right_Type1 | Gray | Pedestrian | Pedestrian_Dis3_Right_1_Gray |  |
| 44 | Distance 3 | Right_Type1 | Red | Passenger car or Truck or Motorbike | Car_Dis3_Right_1_Red |  |
| 45 | Distance 3 | Right_Type1 | Red | Pedestrian | Pedestrian_Dis3_Right_1_Amber |  |
| 46 | Distance 4 | Right_Type1 | White | Passenger car or Truck or Motorbike | Car_Dis4_Right_1_White |  |
| 47 | Distance 4 | Right_Type1 | Gray | Passenger car or Truck or Motorbike | Car_Dis4_Right_1_Gray |  |
| 48 | Distance 4 | Right_Type1 | Gray | Pedestrian | Pedestrian_Dis4_Right_1_Gray |  |
| 49 | Distance 4 | Right_Type1 | Red | Passenger car or Truck or Motorbike | Car_Dis4_Right_1_Red |  |
| 50 | Distance 4 | Right_Type1 | Red | Pedestrian | Pedestrian_Dis4_Right_1_Amber |  |
- Verification Criteria: Verify by executing test cases
- Verification Method: Software Qualification Test, System Qualification Test, Unit Test
- Verification Owner: FV, SW
- System Requirement State: Approved
- Primary Discipline: SW
- ASIL Rating: QM

##### TFDCX32348-28230: Logic Table - HMI - HMI_ACC_ADJACENT_VEHICLE_BLINK_RIGHT/Warning ID - WRN_ADAS_ACC_G22 (System Requirement)
| No. | Input |  | Output |  |
| --- | --- | --- | --- | --- |
| No. | HMI - HMI_ACC_ADJACENT_VEHICLE_ICON_RIGHT | Local Parameter - Adjacent_Vehicle_Blinking_Right | HMI - HMI_ACC_ADJACENT_VEHICLE_BLINK_RIGHT (*1) | Warning ID - WRN_ADAS_ACC_G22 (*2) (*3) |
| 1 | OFF | X | OFF | OFF |
| 2 | Other than above | OFF | OFF | OFF |
| 3 | Other than above | ON | ON | ON |
(*1) Detailed requirements on HMI_ACC_ADJACENT_VEHICLE_BLINK_RIGHT
Case 1. Until 2 cycle time (2,000ms) passes since HMI_ACC_ADJACENT_VEHICLE_BLINK_RIGHT = OFF -> ON is detected, Do not execute No.2 even if Adjacent_Vehicle_Blinking_Right = OFF is detected.
Case 2. After 2 cycle time (2,000ms) passes since HMI_ACC_ADJACENT_VEHICLE_BLINK_RIGHT = OFF -> ON is detected, Execute No.2 immediately when Adjacent_Vehicle_Blinking_Right = OFF is detected.
Case 3. When HMI_ACC_ADJACENT_VEHICLE_ICON_RIGHT = OFF is detected, Execute No.1 immediately.
(*2) The same requirements as for HMI_ACC_ADJACENT_VEHICLE_BLINK_RIGHT also apply to the WRN_ADAS_ACC_G22.
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While HMI_ACC_ADJACENT_VEHICLE_BLINK_RIGHT == ON, Blink control is necessary for Adjacent vehicle icon.
Requirements for Blink control:
1. Cycle time is 1,000ms.
2. ON Duty is 50%.
3. At the beginning of the blinking, Turn on the icon display.
4. Cancel the icon blinking as soon as HMI_ACC_ADJACENT_VEHICLE_BLINK_RIGHT is changed from ON to OFF.
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(*3) For WRN_ADAS_ACC_G22, Update the value immediately when Input condition changes.
- Verification Criteria: Verify by executing test cases
- Verification Method: Software Qualification Test, System Qualification Test, Unit Test
- Verification Owner: FV, SW
- System Requirement State: Approved
- Primary Discipline: SW
- ASIL Rating: QM

#### TFDCX32348-32332: Group 23: Adjacent vehicle (left) (Heading)

##### TFDCX32348-32333: Logic Table - Local Parameter - Adjacent_Vehicle_Type_Left (System Requirement)
| No. | Input |  |  | Output |
| --- | --- | --- | --- | --- |
| No. | Internal Signal - IgnMode | CAN Signal Communication Status - ACCAVTYL (*1) | CANSignal - ACCAVTYL | Local Parameter - ACC_Adjacent _Vehicle_Type_Left |
| 1 | OFF | x | x | OFF |
| 2 | ON | Communication Starting Never Received: 1 Communication Failure: 0 | x | OFF |
| 3 | ON | Communication Establishment Never Received: 0 Communication Failure: 0 | 000b | OFF |
| 4 | ON | Communication Establishment Never Received: 0 Communication Failure: 0 | 001b | Passenger car |
| 5 | ON | Communication Establishment Never Received: 0 Communication Failure: 0 | 010b | Truck |
| 6 | ON | Communication Establishment Never Received: 0 Communication Failure: 0 | 011b | Motorbike |
| 7 | ON | Communication Establishment Never Received: 0 Communication Failure: 0 | 100b | Pedestrian |
| 8 | ON | Communication Establishment Never Received: 0 Communication Failure: 0 | Other than above | OFF |
| 9 | ON | Communication Abnormality Never Received: x Communication Failure: 1 | x | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-32334: Logic Table - Local Parameter - Adjacent_Vehicle_Distance_Left (System Requirement)
| No. | Input |  |  | Output |
| --- | --- | --- | --- | --- |
| No. | Internal Signal - IgnMode | CAN Signal Communication Status - ACCAVDTL (*1) | CANSignal - ACCAVDTL | Local Parameter - Adjacent_Vehicle_Distance_Left |
| 1 | OFF | X | X | OFF |
| 2 | ON | Communication Starting Never Received: 1 Communication Failure: 0 | X | OFF |
| 3 | ON | Communication Establishment Never Received: 0 Communication Failure: 0 | 001b | Distance 1 |
| 4 | ON | Communication Establishment Never Received: 0 Communication Failure: 0 | 010b | Distance 2 |
| 5 | ON | Communication Establishment Never Received: 0 Communication Failure: 0 | 011b | Distance 3 |
| 6 | ON | Communication Establishment Never Received: 0 Communication Failure: 0 | 100b | Distance 4 |
| 7 | ON | Communication Establishment Never Received: 0 Communication Failure: 0 | Other than above | OFF |
| 8 | ON | Communication Abnormality Never Received: x Communication Failure: 1 | X | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-32335: Logic Table - Local Parameter - Adjacent_Vehicle_Color_Left (System Requirement)
| No. | Input |  |  | Output |
| --- | --- | --- | --- | --- |
| No. | Internal Signal - IgnMode | CAN Signal Communication Status - ACCAVS1L (*1) | CANSignal - ACCAVS1L | Local Parameter - Adjacent_Vehicle_Color_Left |
| 1 | OFF | X | X | OFF |
| 2 | ON | Communication Starting Never Received: 1 Communication Failure: 0 | X | OFF |
| 3 | ON | Communication Establishment Never Received: 0 Communication Failure: 0 | 00b | OFF |
| 4 | ON | Communication Establishment Never Received: 0 Communication Failure: 0 | 01b | White |
| 5 | ON | Communication Establishment Never Received: 0 Communication Failure: 0 | 10b | Gray |
| 6 | ON | Communication Establishment Never Received: 0 Communication Failure: 0 | 11b | Amber |
| 7 | ON | Communication Abnormality Never Received: x Communication Failure: 1 | X | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-32336: Logic Table - Local Parameter - Adjacent_Vehicle_Blinking_Left (System Requirement)
| No. | Input |  |  | Output |
| --- | --- | --- | --- | --- |
| No. | Internal Signal - IgnMode | CAN Signal Communication Status - ACCAVS2L (*1) | CANSignal - ACCAVS2L | Local Parameter - Adjacent_Vehicle_Blinking_Left |
| 1 | OFF | X | X | OFF |
| 2 | ON | Communication Starting Never Received: 1 Communication Failure: 0 | X | OFF |
| 3 | ON | Communication Establishment Never Received: 0 Communication Failure: 0 | 0b | OFF |
| 4 | ON | Communication Establishment Never Received: 0 Communication Failure: 0 | 1b | ON |
| 5 | ON | Communication Abnormality Never Received: x Communication Failure: 1 | X | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-32337: Logic Table - Local Parameter - Adjacent_Vehicle_Position_Left/ Adjacent_Vehicle_Position_Left_FWIND (System Requirement)
| No. | Input |  |  | Output |  |
| --- | --- | --- | --- | --- | --- |
| No. | Internal Signal - IgnMode | CAN Signal Communication Status - ACCAVLPL (*1) | CANSignal - ACCAVLPL | Local Parameter - Adjacent_Vehicle_Position_Left | Local Parameter - Adjacent_Vehicle_Position_Left_FWIND |
| 1 | OFF | x | x | OFF | OFF |
| 2 | ON | Communication Starting Never Received: 1 Communication Failure: 0 | x | OFF | OFF |
| 3 | ON | Communication Establishment Never Received: 0 Communication Failure: 0 | 000b | OFF | OFF |
| 4 | ON | Communication Establishment Never Received: 0 Communication Failure: 0 | 001b | Pos_1 | Center |
| 5 | ON | Communication Establishment Never Received: 0 Communication Failure: 0 | 010b | Pos_2 | Left |
| 6 | ON | Communication Establishment Never Received: 0 Communication Failure: 0 | 011b | Pos_3 | Center |
| 7 | ON | Communication Establishment Never Received: 0 Communication Failure: 0 | 100b | Pos_4 | Left_Type1 |
| 8 | ON | Communication Establishment Never Received: 0 Communication Failure: 0 | 101b | Pos_5 | Center |
| 9 | ON | Communication Establishment Never Received: 0 Communication Failure: 0 | 110b | Pos_6 | Center |
| 10 | ON | Communication Establishment Never Received: 0 Communication Failure: 0 | 111b | Pos_7 | OFF |
| 11 | ON | Communication Abnormality Never Received: x Communication Failure: 1 | x | OFF | OFF |
(*1) Never Received and Communication Failure is defined in CAN General SRD. Please check the CAN General SRD for details.
- Verification Criteria: Verify by executing test cases
- Verification Method: Software Qualification Test, System Qualification Test, Unit Test
- Verification Owner: FV, SW
- System Requirement State: Approved
- Primary Discipline: SW
- ASIL Rating: QM

##### TFDCX32348-32338: Logic Table - HMI - HMI_ACC_ADJACENT_VEHICLE_ICON_LEFT (Heading)

###### TFDCX32348-13943: HMI - HMI_ACC_ADJACENT_VEHICLE_ICON_LEFT (1 of 7) (System Requirement)
| No. | Input |  |  |  | Output | <Info> Meaning |
| --- | --- | --- | --- | --- | --- | --- |
| No. | Local Parameter - Adjacent_Vehicle_Distance_Left | Local Parameter - Adjacent_Vehicle_Position_Left | Local Parameter - Adjacent_Vehicle_Color_Left | Local Parameter - Adjacent_Vehicle_Type_Left | HMI - HMI_ACC_ADJACENT_VEHICLE_ICON_LEFT | <Info> Meaning |
| 1 | OFF | x | x | x | OFF | For invalid distance, adjacent vehicle not displayed. |
| 2 | x | OFF | x | x | OFF | For invalid position, adjacent vehicle not displayed. |
| 3 | x | x | OFF | x | OFF | For invalid color, adjacent vehicle not displayed. |
| 4 | x | x | x | OFF | OFF | No adjacent vehicle is detected. |
| 5 | x | Other than Pos_4 | x | Pedestrian | OFF | Pedestrian can't be displayed at other than Pos_4. |
| 6 | x | Pos_4 | White | Pedestrian | OFF | Pedestrian of white color can't be displayed at Pos_4. |
| 7 | Distance 1 | Pos_1 | White | Passenger car | Car_Dis1_Pos1_White |  |
| 8 | Distance 1 | Pos_1 | White | Truck | Truck_Dis1_Pos1_White |  |
| 9 | Distance 1 | Pos_1 | White | Motorbike | Bike_Dis1_Pos1_White |  |
| 10 | Distance 1 | Pos_1 | Gray | Passenger car | Car_Dis1_Pos1_Gray |  |
| 11 | Distance 1 | Pos_1 | Gray | Truck | Truck_Dis1_Pos1_Gray |  |
| 12 | Distance 1 | Pos_1 | Gray | Motorbike | Bike_Dis1_Pos1_Gray |  |
| 13 | Distance 1 | Pos_1 | Red | Passenger car | Car_Dis1_Pos1_Red |  |
| 14 | Distance 1 | Pos_1 | Red | Truck | Truck_Dis1_Pos1_Red |  |
| 15 | Distance 1 | Pos_1 | Red | Motorbike | Bike_Dis1_Pos1_Red |  |
| 16 | Distance 2 | Pos_1 | White | Passenger car | Car_Dis2_Pos1_White |  |
| 17 | Distance 2 | Pos_1 | White | Truck | Truck_Dis2_Pos1_White |  |
| 18 | Distance 2 | Pos_1 | White | Motorbike | Bike_Dis2_Pos1_White |  |
| 19 | Distance 2 | Pos_1 | Gray | Passenger car | Car_Dis2_Pos1_Gray |  |
| 20 | Distance 2 | Pos_1 | Gray | Truck | Truck_Dis2_Pos1_Gray |  |
| 21 | Distance 2 | Pos_1 | Gray | Motorbike | Bike_Dis2_Pos1_Gray |  |
| 22 | Distance 2 | Pos_1 | Red | Passenger car | Car_Dis2_Pos1_Red |  |
| 23 | Distance 2 | Pos_1 | Red | Truck | Truck_Dis2_Pos1_Red |  |
| 24 | Distance 2 | Pos_1 | Red | Motorbike | Bike_Dis2_Pos1_Red |  |
| 25 | Distance 3 | Pos_1 | White | Passenger car | Car_Dis3_Pos1_White |  |
| 26 | Distance 3 | Pos_1 | White | Truck | Truck_Dis3_Pos1_White |  |
| 27 | Distance 3 | Pos_1 | White | Motorbike | Bike_Dis3_Pos1_White |  |
| 28 | Distance 3 | Pos_1 | Gray | Passenger car | Car_Dis3_Pos1_Gray |  |
| 29 | Distance 3 | Pos_1 | Gray | Truck | Truck_Dis3_Pos1_Gray |  |
| 30 | Distance 3 | Pos_1 | Gray | Motorbike | Bike_Dis3_Pos1_Gray |  |
| 31 | Distance 3 | Pos_1 | Red | Passenger car | Car_Dis3_Pos1_Red |  |
| 32 | Distance 3 | Pos_1 | Red | Truck | Truck_Dis3_Pos1_Red |  |
| 33 | Distance 3 | Pos_1 | Red | Motorbike | Bike_Dis3_Pos1_Red |  |
| 34 | Distance 4 | Pos_1 | White | Passenger car | Car_Dis4_Pos1_White |  |
| 35 | Distance 4 | Pos_1 | White | Truck | Truck_Dis4_Pos1_White |  |
| 36 | Distance 4 | Pos_1 | White | Motorbike | Bike_Dis4_Pos1_White |  |
| 37 | Distance 4 | Pos_1 | Gray | Passenger car | Car_Dis4_Pos1_Gray |  |
| 38 | Distance 4 | Pos_1 | Gray | Truck | Truck_Dis4_Pos1_Gray |  |
| 39 | Distance 4 | Pos_1 | Gray | Motorbike | Bike_Dis4_Pos1_Gray |  |
| 40 | Distance 4 | Pos_1 | Red | Passenger car | Car_Dis4_Pos1_Red |  |
| 41 | Distance 4 | Pos_1 | Red | Truck | Truck_Dis4_Pos1_Red |  |
| 42 | Distance 4 | Pos_1 | Red | Motorbike | Bike_Dis4_Pos1_Red |  |
Continue to next artifact
- Verification Criteria: Verify by executing test cases
- Verification Method: Software Qualification Test, System Qualification Test, Unit Test
- Verification Owner: FV, SW
- System Requirement State: Approved
- Primary Discipline: SW
- ASIL Rating: QM

###### TFDCX32348-13945: HMI - HMI_ACC_ADJACENT_VEHICLE_ICON_LEFT (2 of 7) (System Requirement)
| No. | Input |  |  |  | Output | <Info> Meaning |
| --- | --- | --- | --- | --- | --- | --- |
| No. | Local Parameter - Adjacent_Vehicle_Distance_Left | Local Parameter - Adjacent_Vehicle_Position_Left | Local Parameter - Adjacent_Vehicle_Color_Left | Local Parameter - Adjacent_Vehicle_Type_Left | HMI - HMI_ACC_ADJACENT_VEHICLE_ICON_LEFT | <Info> Meaning |
| 43 | Distance 1 | Pos_2 | White | Passenger car | Car_Dis1_Pos2_White |  |
| 44 | Distance 1 | Pos_2 | White | Truck | Truck_Dis1_Pos2_White |  |
| 45 | Distance 1 | Pos_2 | White | Motorbike | Bike_Dis1_Pos2_White |  |
| 46 | Distance 1 | Pos_2 | Gray | Passenger car | Car_Dis1_Pos2_Gray |  |
| 47 | Distance 1 | Pos_2 | Gray | Truck | Truck_Dis1_Pos2_Gray |  |
| 48 | Distance 1 | Pos_2 | Gray | Motorbike | Bike_Dis1_Pos2_Gray |  |
| 49 | Distance 1 | Pos_2 | Red | Passenger car | Car_Dis1_Pos2_Red |  |
| 50 | Distance 1 | Pos_2 | Red | Truck | Truck_Dis1_Pos2_Red |  |
| 51 | Distance 1 | Pos_2 | Red | Motorbike | Bike_Dis1_Pos2_Red |  |
| 52 | Distance 2 | Pos_2 | White | Passenger car | Car_Dis2_Pos2_White |  |
| 53 | Distance 2 | Pos_2 | White | Truck | Truck_Dis2_Pos2_White |  |
| 54 | Distance 2 | Pos_2 | White | Motorbike | Bike_Dis2_Pos2_White |  |
| 55 | Distance 2 | Pos_2 | Gray | Passenger car | Car_Dis2_Pos2_Gray |  |
| 56 | Distance 2 | Pos_2 | Gray | Truck | Truck_Dis2_Pos2_Gray |  |
| 57 | Distance 2 | Pos_2 | Gray | Motorbike | Bike_Dis2_Pos2_Gray |  |
| 58 | Distance 2 | Pos_2 | Red | Passenger car | Car_Dis2_Pos2_Red |  |
| 59 | Distance 2 | Pos_2 | Red | Truck | Truck_Dis2_Pos2_Red |  |
| 60 | Distance 2 | Pos_2 | Red | Motorbike | Bike_Dis2_Pos2_Red |  |
| 61 | Distance 3 | Pos_2 | White | Passenger car | Car_Dis3_Pos2_White |  |
| 62 | Distance 3 | Pos_2 | White | Truck | Truck_Dis3_Pos2_White |  |
| 63 | Distance 3 | Pos_2 | White | Motorbike | Bike_Dis3_Pos2_White |  |
| 64 | Distance 3 | Pos_2 | Gray | Passenger car | Car_Dis3_Pos2_Gray |  |
| 65 | Distance 3 | Pos_2 | Gray | Truck | Truck_Dis3_Pos2_Gray |  |
| 66 | Distance 3 | Pos_2 | Gray | Motorbike | Bike_Dis3_Pos2_Gray |  |
| 67 | Distance 3 | Pos_2 | Red | Passenger car | Car_Dis3_Pos2_Red |  |
| 68 | Distance 3 | Pos_2 | Red | Truck | Truck_Dis3_Pos2_Red |  |
| 69 | Distance 3 | Pos_2 | Red | Motorbike | Bike_Dis3_Pos2_Red |  |
| 70 | Distance 4 | Pos_2 | White | Passenger car | Car_Dis4_Pos2_White |  |
| 71 | Distance 4 | Pos_2 | White | Truck | Truck_Dis4_Pos2_White |  |
| 72 | Distance 4 | Pos_2 | White | Motorbike | Bike_Dis4_Pos2_White |  |
| 73 | Distance 4 | Pos_2 | Gray | Passenger car | Car_Dis4_Pos2_Gray |  |
| 74 | Distance 4 | Pos_2 | Gray | Truck | Truck_Dis4_Pos2_Gray |  |
| 75 | Distance 4 | Pos_2 | Gray | Motorbike | Bike_Dis4_Pos2_Gray |  |
| 76 | Distance 4 | Pos_2 | Red | Passenger car | Car_Dis4_Pos2_Red |  |
| 77 | Distance 4 | Pos_2 | Red | Truck | Truck_Dis4_Pos2_Red |  |
| 78 | Distance 4 | Pos_2 | Red | Motorbike | Bike_Dis4_Pos2_Red |  |
- Verification Criteria: Verify by executing test cases
- Verification Method: Software Qualification Test, System Qualification Test, Unit Test
- Verification Owner: FV, SW
- System Requirement State: Approved
- Primary Discipline: SW
- ASIL Rating: QM

###### TFDCX32348-13951: HMI - HMI_ACC_ADJACENT_VEHICLE_ICON_LEFT (3 of 7) (System Requirement)
| No. | Input |  |  |  | Output | <Info> Meaning |
| --- | --- | --- | --- | --- | --- | --- |
| No. | Local Parameter - Adjacent_Vehicle_Distance_Left | Local Parameter - Adjacent_Vehicle_Position_Left | Local Parameter - Adjacent_Vehicle_Color_Left | Local Parameter - Adjacent_Vehicle_Type_Leftt | HMI - HMI_ACC_ADJACENT_VEHICLE_ICON_LEFT | <Info> Meaning |
| 79 | Distance 1 | Pos_3 | White | Passenger car | Car_Dis1_Pos3_White |  |
| 80 | Distance 1 | Pos_3 | White | Truck | Truck_Dis1_Pos3_White |  |
| 81 | Distance 1 | Pos_3 | White | Motorbike | Bike_Dis1_Pos3_White |  |
| 82 | Distance 1 | Pos_3 | Gray | Passenger car | Car_Dis1_Pos3_Gray |  |
| 83 | Distance 1 | Pos_3 | Gray | Truck | Truck_Dis1_Pos3_Gray |  |
| 84 | Distance 1 | Pos_3 | Gray | Motorbike | Bike_Dis1_Pos3_Gray |  |
| 85 | Distance 1 | Pos_3 | Amber | Passenger car | Car_Dis1_Pos3_Amber |  |
| 86 | Distance 1 | Pos_3 | Amber | Truck | Truck_Dis1_Pos3_Amber |  |
| 87 | Distance 1 | Pos_3 | Amber | Motorbike | Bike_Dis1_Pos3_Amber |  |
| 88 | Distance 2 | Pos_3 | White | Passenger car | Car_Dis2_Pos3_White |  |
| 89 | Distance 2 | Pos_3 | White | Truck | Truck_Dis2_Pos3_White |  |
| 90 | Distance 2 | Pos_3 | White | Motorbike | Bike_Dis2_Pos3_White |  |
| 91 | Distance 2 | Pos_3 | Gray | Passenger car | Car_Dis2_Pos3_Gray |  |
| 92 | Distance 2 | Pos_3 | Gray | Truck | Truck_Dis2_Pos3_Gray |  |
| 93 | Distance 2 | Pos_3 | Gray | Motorbike | Bike_Dis2_Pos3_Gray |  |
| 94 | Distance 2 | Pos_3 | Amber | Passenger car | Car_Dis2_Pos3_Amber |  |
| 95 | Distance 2 | Pos_3 | Amber | Truck | Truck_Dis2_Pos3_Amber |  |
| 96 | Distance 2 | Pos_3 | Amber | Motorbike | Bike_Dis2_Pos3_Amber |  |
| 97 | Distance 3 | Pos_3 | White | Passenger car | Car_Dis3_Pos3_White |  |
| 98 | Distance 3 | Pos_3 | White | Truck | Truck_Dis3_Pos3_White |  |
| 99 | Distance 3 | Pos_3 | White | Motorbike | Bike_Dis3_Pos3_White |  |
| 100 | Distance 3 | Pos_3 | Gray | Passenger car | Car_Dis3_Pos3_Gray |  |
| 101 | Distance 3 | Pos_3 | Gray | Truck | Truck_Dis3_Pos3_Gray |  |
| 102 | Distance 3 | Pos_3 | Gray | Motorbike | Bike_Dis3_Pos3_Gray |  |
| 103 | Distance 3 | Pos_3 | Amber | Passenger car | Car_Dis3_Pos3_Amber |  |
| 104 | Distance 3 | Pos_3 | Amber | Truck | Truck_Dis3_Pos3_Amber |  |
| 105 | Distance 3 | Pos_3 | Amber | Motorbike | Bike_Dis3_Pos3_Amber |  |
| 106 | Distance 4 | Pos_3 | White | Passenger car | Car_Dis4_Pos3_White |  |
| 107 | Distance 4 | Pos_3 | White | Truck | Truck_Dis4_Pos3_White |  |
| 108 | Distance 4 | Pos_3 | White | Motorbike | Bike_Dis4_Pos3_White |  |
| 109 | Distance 4 | Pos_3 | Gray | Passenger car | Car_Dis4_Pos3_Gray |  |
| 110 | Distance 4 | Pos_3 | Gray | Truck | Truck_Dis4_Pos3_Gray |  |
| 111 | Distance 4 | Pos_3 | Gray | Motorbike | Bike_Dis4_Pos3_Gray |  |
| 112 | Distance 4 | Pos_3 | Amber | Passenger car | Car_Dis4_Pos3_Amber |  |
| 113 | Distance 4 | Pos_3 | Amber | Truck | Truck_Dis4_Pos3_Amber |  |
| 114 | Distance 4 | Pos_3 | Amber | Motorbike | Bike_Dis4_Pos3_Amber |  |
- Verification Criteria: Verify by executing test cases
- Verification Method: Software Qualification Test, System Qualification Test, Unit Test
- Verification Owner: FV, SW
- System Requirement State: Approved
- Primary Discipline: SW
- ASIL Rating: QM

###### TFDCX32348-13941: HMI - HMI_ACC_ADJACENT_VEHICLE_ICON_LEFT (4 of 7) (System Requirement)
| No. | Input |  |  |  | Output | <Info> Meaning |
| --- | --- | --- | --- | --- | --- | --- |
| No. | Local Parameter - Adjacent_Vehicle_Distance_Left | Local Parameter - Adjacent_Vehicle_Position_Left | Local Parameter - Adjacent_Vehicle_Color_Left | Local Parameter - Adjacent_Vehicle_Type_Left | HMI - HMI_ACC_ADJACENT_VEHICLE_ICON_LEFT | <Info> Meaning |
| 115 | Distance 1 | Pos_4 | White | Passenger car | Car_Dis1_Pos4_White |  |
| 116 | Distance 1 | Pos_4 | White | Truck | Truck_Dis1_Pos4_White |  |
| 117 | Distance 1 | Pos_4 | White | Motorbike | Bike_Dis1_Pos4_White |  |
| 118 | Distance 1 | Pos_4 | Gray | Passenger car | Car_Dis1_Pos4_Gray |  |
| 119 | Distance 1 | Pos_4 | Gray | Truck | Truck_Dis1_Pos4_Gray |  |
| 120 | Distance 1 | Pos_4 | Gray | Motorbike | Bike_Dis1_Pos4_Gray |  |
| 121 | Distance 1 | Pos_4 | Gray | Pedestrian | Pedestrian_Dis1_Pos4_Gray |  |
| 122 | Distance 1 | Pos_4 | Red | Passenger car | Car_Dis1_Pos4_Red |  |
| 123 | Distance 1 | Pos_4 | Red | Truck | Truck_Dis1_Pos4_Red |  |
| 124 | Distance 1 | Pos_4 | Red | Motorbike | Bike_Dis1_Pos4_Red |  |
| 125 | Distance 1 | Pos_4 | Red | Pedestrian | Pedestrian_Dis1_Pos4_Red |  |
| 126 | Distance 2 | Pos_4 | White | Passenger car | Car_Dis2_Pos4_White |  |
| 127 | Distance 2 | Pos_4 | White | Truck | Truck_Dis2_Pos4_White |  |
| 128 | Distance 2 | Pos_4 | White | Motorbike | Bike_Dis2_Pos4_White |  |
| 129 | Distance 2 | Pos_4 | Gray | Passenger car | Car_Dis2_Pos4_Gray |  |
| 130 | Distance 2 | Pos_4 | Gray | Truck | Truck_Dis2_Pos4_Gray |  |
| 131 | Distance 2 | Pos_4 | Gray | Motorbike | Bike_Dis2_Pos4_Gray |  |
| 132 | Distance 2 | Pos_4 | Gray | Pedestrian | Pedestrian_Dis2_Pos4_Gray |  |
| 133 | Distance 2 | Pos_4 | Red | Passenger car | Car_Dis2_Pos4_Red |  |
| 134 | Distance 2 | Pos_4 | Red | Truck | Truck_Dis2_Pos4_Red |  |
| 135 | Distance 2 | Pos_4 | Red | Motorbike | Bike_Dis2_Pos4_Red |  |
| 136 | Distance 2 | Pos_4 | Red | Pedestrian | Pedestrian_Dis2_Pos4_Red |  |
| 137 | Distance 3 | Pos_4 | White | Passenger car | Car_Dis3_Pos4_White |  |
| 138 | Distance 3 | Pos_4 | White | Truck | Truck_Dis3_Pos4_White |  |
| 139 | Distance 3 | Pos_4 | White | Motorbike | Bike_Dis3_Pos4_White |  |
| 140 | Distance 3 | Pos_4 | Gray | Passenger car | Car_Dis3_Pos4_Gray |  |
| 141 | Distance 3 | Pos_4 | Gray | Truck | Truck_Dis3_Pos4_Gray |  |
| 142 | Distance 3 | Pos_4 | Gray | Motorbike | Bike_Dis3_Pos4_Gray |  |
| 143 | Distance 3 | Pos_4 | Gray | Pedestrian | Pedestrian_Dis3_Pos4_Gray |  |
| 144 | Distance 3 | Pos_4 | Red | Passenger car | Car_Dis3_Pos4_Red |  |
| 145 | Distance 3 | Pos_4 | Red | Truck | Truck_Dis3_Pos4_Red |  |
| 146 | Distance 3 | Pos_4 | Red | Motorbike | Bike_Dis3_Pos4_Red |  |
| 147 | Distance 3 | Pos_4 | Red | Pedestrian | Pedestrian_Dis3_Pos4_Red |  |
| 148 | Distance 4 | Pos_4 | White | Passenger car | Car_Dis4_Pos4_White |  |
| 149 | Distance 4 | Pos_4 | White | Truck | Truck_Dis4_Pos4_White |  |
| 150 | Distance 4 | Pos_4 | White | Motorbike | Bike_Dis4_Pos4_White |  |
| 151 | Distance 4 | Pos_4 | Gray | Passenger car | Car_Dis4_Pos4_Gray |  |
| 152 | Distance 4 | Pos_4 | Gray | Truck | Truck_Dis4_Pos4_Gray |  |
| 153 | Distance 4 | Pos_4 | Gray | Motorbike | Bike_Dis4_Pos4_Gray |  |
| 154 | Distance 4 | Pos_4 | Gray | Pedestrian | Pedestrian_Dis4_Pos4_Gray |  |
| 155 | Distance 4 | Pos_4 | Red | Passenger car | Car_Dis4_Pos4_Red |  |
| 156 | Distance 4 | Pos_4 | Red | Truck | Truck_Dis4_Pos4_Red |  |
| 157 | Distance 4 | Pos_4 | Red | Motorbike | Bike_Dis4_Pos4_Red |  |
| 158 | Distance 4 | Pos_4 | Red | Pedestrian | Pedestrian_Dis4_Pos4_Red |  |
- Verification Criteria: Verify by executing test cases
- Verification Method: Software Qualification Test, System Qualification Test, Unit Test
- Verification Owner: FV, SW
- System Requirement State: Approved
- Primary Discipline: SW
- ASIL Rating: QM

###### TFDCX32348-34045: HMI - HMI_ACC_ADJACENT_VEHICLE_ICON_LEFT (5 of 7) (System Requirement)
| No. | Input |  |  |  | Output | <Info> Meaning |
| --- | --- | --- | --- | --- | --- | --- |
| No. | Local Parameter - Adjacent_Vehicle_Distance_Left | Local Parameter - Adjacent_Vehicle_Position_Left | Local Parameter - Adjacent_Vehicle_Color_Left | Local Parameter - Adjacent_Vehicle_Type_Left | HMI - HMI_ACC_ADJACENT_VEHICLE_ICON_LEFT | <Info> Meaning |
| 159 | Distance 1 | Pos_5 | White | Passenger car | Car_Dis1_Pos5_White |  |
| 160 | Distance 1 | Pos_5 | White | Truck | Truck_Dis1_Pos5_White |  |
| 161 | Distance 1 | Pos_5 | White | Motorbike | Bike_Dis1_Pos5_White |  |
| 162 | Distance 1 | Pos_5 | Gray | Passenger car | Car_Dis1_Pos5_Gray |  |
| 163 | Distance 1 | Pos_5 | Gray | Truck | Truck_Dis1_Pos5_Gray |  |
| 164 | Distance 1 | Pos_5 | Gray | Motorbike | Bike_Dis1_Pos5_Gray |  |
| 165 | Distance 1 | Pos_5 | Red | Passenger car | Car_Dis1_Pos5_Red |  |
| 166 | Distance 1 | Pos_5 | Red | Truck | Truck_Dis1_Pos5_Red |  |
| 167 | Distance 1 | Pos_5 | Red | Motorbike | Bike_Dis1_Pos5_Red |  |
| 168 | Distance 2 | Pos_5 | White | Passenger car | Car_Dis2_Pos5_White |  |
| 169 | Distance 2 | Pos_5 | White | Truck | Truck_Dis2_Pos5_White |  |
| 170 | Distance 2 | Pos_5 | White | Motorbike | Bike_Dis2_Pos5_White |  |
| 171 | Distance 2 | Pos_5 | Gray | Passenger car | Car_Dis2_Pos5_Gray |  |
| 172 | Distance 2 | Pos_5 | Gray | Truck | Truck_Dis2_Pos5_Gray |  |
| 173 | Distance 2 | Pos_5 | Gray | Motorbike | Bike_Dis2_Pos5_Gray |  |
| 174 | Distance 2 | Pos_5 | Red | Passenger car | Car_Dis2_Pos5_Red |  |
| 175 | Distance 2 | Pos_5 | Red | Truck | Truck_Dis2_Pos5_Red |  |
| 176 | Distance 2 | Pos_5 | Red | Motorbike | Bike_Dis2_Pos5_Red |  |
| 177 | Distance 3 | Pos_5 | White | Passenger car | Car_Dis3_Pos5_White |  |
| 178 | Distance 3 | Pos_5 | White | Truck | Truck_Dis3_Pos5_White |  |
| 179 | Distance 3 | Pos_5 | White | Motorbike | Bike_Dis3_Pos5_White |  |
| 180 | Distance 3 | Pos_5 | Gray | Passenger car | Car_Dis3_Pos5_Gray |  |
| 181 | Distance 3 | Pos_5 | Gray | Truck | Truck_Dis3_Pos5_Gray |  |
| 182 | Distance 3 | Pos_5 | Gray | Motorbike | Bike_Dis3_Pos5_Gray |  |
| 183 | Distance 3 | Pos_5 | Red | Passenger car | Car_Dis3_Pos5_Red |  |
| 184 | Distance 3 | Pos_5 | Red | Truck | Truck_Dis3_Pos5_Red |  |
| 185 | Distance 3 | Pos_5 | Red | Motorbike | Bike_Dis3_Pos5_Red |  |
| 186 | Distance 4 | Pos_5 | White | Passenger car | Car_Dis4_Pos5_White |  |
| 187 | Distance 4 | Pos_5 | White | Truck | Truck_Dis4_Pos5_White |  |
| 188 | Distance 4 | Pos_5 | White | Motorbike | Bike_Dis4_Pos5_White |  |
| 189 | Distance 4 | Pos_5 | Gray | Passenger car | Car_Dis4_Pos5_Gray |  |
| 190 | Distance 4 | Pos_5 | Gray | Truck | Truck_Dis4_Pos5_Gray |  |
| 191 | Distance 4 | Pos_5 | Gray | Motorbike | Bike_Dis4_Pos5_Gray |  |
| 192 | Distance 4 | Pos_5 | Red | Passenger car | Car_Dis4_Pos5_Red |  |
| 193 | Distance 4 | Pos_5 | Red | Truck | Truck_Dis4_Pos5_Red |  |
| 194 | Distance 4 | Pos_5 | Red | Motorbike | Bike_Dis4_Pos5_Red |  |
Continue to next artifact
- Verification Criteria: Verify by executing test cases
- Verification Method: Software Qualification Test, System Qualification Test, Unit Test
- Verification Owner: FV, SW
- System Requirement State: Approved
- Primary Discipline: SW
- ASIL Rating: QM

###### TFDCX32348-34044: HMI - HMI_ACC_ADJACENT_VEHICLE_ICON_LEFT (6 of 7) (System Requirement)
| No. | Input |  |  |  | Output | <Info> Meaning |
| --- | --- | --- | --- | --- | --- | --- |
| No. | Local Parameter - Adjacent_Vehicle_Distance_Left | Local Parameter - Adjacent_Vehicle_Position_Left | Local Parameter - Adjacent_Vehicle_Color_Left | Local Parameter - Adjacent_Vehicle_Type_Left | HMI - HMI_ACC_ADJACENT_VEHICLE_ICON_LEFT | <Info> Meaning |
| 195 | Distance 1 | Pos_6 | White | Passenger car | Car_Dis1_Pos6_White |  |
| 196 | Distance 1 | Pos_6 | White | Truck | Truck_Dis1_Pos6_White |  |
| 197 | Distance 1 | Pos_6 | White | Motorbike | Bike_Dis1_Pos6_White |  |
| 198 | Distance 1 | Pos_6 | Gray | Passenger car | Car_Dis1_Pos6_Gray |  |
| 199 | Distance 1 | Pos_6 | Gray | Truck | Truck_Dis1_Pos6_Gray |  |
| 200 | Distance 1 | Pos_6 | Gray | Motorbike | Bike_Dis1_Pos6_Gray |  |
| 201 | Distance 1 | Pos_6 | Red | Passenger car | Car_Dis1_Pos6_Red |  |
| 202 | Distance 1 | Pos_6 | Red | Truck | Truck_Dis1_Pos6_Red |  |
| 203 | Distance 1 | Pos_6 | Red | Motorbike | Bike_Dis1_Pos6_Red |  |
| 204 | Distance 2 | Pos_6 | White | Passenger car | Car_Dis2_Pos6_White |  |
| 205 | Distance 2 | Pos_6 | White | Truck | Truck_Dis2_Pos6_White |  |
| 206 | Distance 2 | Pos_6 | White | Motorbike | Bike_Dis2_Pos6_White |  |
| 207 | Distance 2 | Pos_6 | Gray | Passenger car | Car_Dis2_Pos6_Gray |  |
| 208 | Distance 2 | Pos_6 | Gray | Truck | Truck_Dis2_Pos6_Gray |  |
| 209 | Distance 2 | Pos_6 | Gray | Motorbike | Bike_Dis2_Pos6_Gray |  |
| 210 | Distance 2 | Pos_6 | Red | Passenger car | Car_Dis2_Pos6_Red |  |
| 211 | Distance 2 | Pos_6 | Red | Truck | Truck_Dis2_Pos6_Red |  |
| 212 | Distance 2 | Pos_6 | Red | Motorbike | Bike_Dis2_Pos6_Red |  |
| 213 | Distance 3 | Pos_6 | White | Passenger car | Car_Dis3_Pos6_White |  |
| 214 | Distance 3 | Pos_6 | White | Truck | Truck_Dis3_Pos6_White |  |
| 215 | Distance 3 | Pos_6 | White | Motorbike | Bike_Dis3_Pos6_White |  |
| 216 | Distance 3 | Pos_6 | Gray | Passenger car | Car_Dis3_Pos6_Gray |  |
| 217 | Distance 3 | Pos_6 | Gray | Truck | Truck_Dis3_Pos6_Gray |  |
| 218 | Distance 3 | Pos_6 | Gray | Motorbike | Bike_Dis3_Pos6_Gray |  |
| 219 | Distance 3 | Pos_6 | Red | Passenger car | Car_Dis3_Pos6_Red |  |
| 220 | Distance 3 | Pos_6 | Red | Truck | Truck_Dis3_Pos6_Red |  |
| 221 | Distance 3 | Pos_6 | Red | Motorbike | Bike_Dis3_Pos6_Red |  |
| 222 | Distance 4 | Pos_6 | White | Passenger car | Car_Dis4_Pos6_White |  |
| 223 | Distance 4 | Pos_6 | White | Truck | Truck_Dis4_Pos6_White |  |
| 224 | Distance 4 | Pos_6 | White | Motorbike | Bike_Dis4_Pos6_White |  |
| 225 | Distance 4 | Pos_6 | Gray | Passenger car | Car_Dis4_Pos6_Gray |  |
| 226 | Distance 4 | Pos_6 | Gray | Truck | Truck_Dis4_Pos6_Gray |  |
| 227 | Distance 4 | Pos_6 | Gray | Motorbike | Bike_Dis4_Pos6_Gray |  |
| 228 | Distance 4 | Pos_6 | Red | Passenger car | Car_Dis4_Pos6_Red |  |
| 229 | Distance 4 | Pos_6 | Red | Truck | Truck_Dis4_Pos6_Red |  |
| 230 | Distance 4 | Pos_6 | Red | Motorbike | Bike_Dis4_Pos6_Red |  |
Continue to next artifact
- Verification Criteria: Verify by executing test cases
- Verification Method: Software Qualification Test, System Qualification Test, Unit Test
- Verification Owner: FV, SW
- System Requirement State: Approved
- Primary Discipline: SW
- ASIL Rating: QM

###### TFDCX32348-34043: HMI - HMI_ACC_ADJACENT_VEHICLE_ICON_LEFT (7 of 7) (System Requirement)
| No. | Input |  |  |  | Output | <Info> Meaning |
| --- | --- | --- | --- | --- | --- | --- |
| No. | Local Parameter - Adjacent_Vehicle_Distance_Left | Local Parameter - Adjacent_Vehicle_Position_Left | Local Parameter - Adjacent_Vehicle_Color_Left | Local Parameter - Adjacent_Vehicle_Type_Left | HMI - HMI_ACC_ADJACENT_VEHICLE_ICON_LEFT | <Info> Meaning |
| 231 | Distance 1 | Pos_7 | x | Passenger car | Car_Dis1_Pos7_Gray | Pos_7 is gray only |
| 232 | Distance 1 | Pos_7 | x | Truck | Truck_Dis1_Pos7_Gray | Pos_7 is gray only |
| 233 | Distance 1 | Pos_7 | x | Motorbike | Bike_Dis1_Pos7_Gray | Pos_7 is gray only |
| 234 | Distance 2 | Pos_7 | x | Passenger car | Car_Dis2_Pos7_Gray | Pos_7 is gray only |
| 235 | Distance 2 | Pos_7 | x | Truck | Truck_Dis2_Pos7_Gray | Pos_7 is gray only |
| 236 | Distance 2 | Pos_7 | x | Motorbike | Bike_Dis2_Pos7_Gray | Pos_7 is gray only |
| 237 | Distance 3 | Pos_7 | x | Passenger car | Car_Dis3_Pos7_Gray | Pos_7 is gray only |
| 238 | Distance 3 | Pos_7 | x | Truck | Truck_Dis3_Pos7_Gray | Pos_7 is gray only |
| 239 | Distance 3 | Pos_7 | x | Motorbike | Bike_Dis3_Pos7_Gray | Pos_7 is gray only |
| 240 | Distance 4 | Pos_7 | x | Passenger car | Car_Dis4_Pos7_Gray | Pos_7 is gray only |
| 241 | Distance 4 | Pos_7 | x | Truck | Truck_Dis4_Pos7_Gray | Pos_7 is gray only |
| 242 | Distance 4 | Pos_7 | x | Motorbike | Bike_Dis4_Pos7_Gray | Pos_7 is gray only |
- Verification Criteria: Verify by executing test cases
- Verification Method: Software Qualification Test, System Qualification Test, Unit Test
- Verification Owner: FV, SW
- System Requirement State: Approved
- Primary Discipline: SW
- ASIL Rating: QM

##### TFDCX32348-13934: Logic Table - HMI - HMI_ACC_ADJACENT_VEHICLE_ICON_LEFT_FWIND (Heading)

###### TFDCX32348-13954: HMI - HMI_ACC_ADJACENT_VEHICLE_ICON_LEFT_FWIND (1 of 2) (System Requirement)
| No. | Input |  |  |  | Output | <Info> Meaning |
| --- | --- | --- | --- | --- | --- | --- |
| No. | Local Parameter - Adjacent_Vehicle_Distance_Left | Adjacent_Vehicle_Position_Left_FWIND | Local Parameter - Adjacent_Vehicle_Color_Left | Local Parameter - Adjacent_Vehicle_Type_Left | HMI - HMI_ACC_ADJACENT_VEHICLE_ICON_LEFT_FWIND | <Info> Meaning |
| 1 | OFF | x | x | x | OFF | For invalid distance, adjacent vehicle not displayed. |
| 2 | x | OFF | x | x | OFF | For invalid position, adjacent vehicle not displayed. |
| 3 | x | x | OFF | x | OFF | For invalid color, adjacent vehicle not displayed. |
| 4 | x | x | x | OFF | OFF | No adjacent vehicle is detected. |
| 5 | x | Other than Left_Type1 | x | Pedestrian | OFF | Pedestrian can't be displayed at other than Left_Type1. |
| 6 | x | Left_Type1 | White | Pedestrian | OFF | Pedestrian of white color can't be displayed at Left_Type1. |
| 7 | Distance 1 | Center | White | Passenger car or Truck or Motorbike | Car_Dis1_Center_White |  |
| 8 | Distance 1 | Center | Gray | Passenger car or Truck or Motorbike | Car_Dis1_Center_Gray |  |
| 9 | Distance 1 | Center | Red | Passenger car or Truck or Motorbike | Car_Dis1_Center_Red |  |
| 10 | Distance 2 | Center | White | Passenger car or Truck or Motorbike | Car_Dis2_Center_White |  |
| 11 | Distance 2 | Center | Gray | Passenger car or Truck or Motorbike | Car_Dis2_Center_Gray |  |
| 12 | Distance 2 | Center | Red | Passenger car or Truck or Motorbike | Car_Dis2_Center_Red |  |
| 13 | Distance 3 | Center | White | Passenger car or Truck or Motorbike | Car_Dis3_Center_White |  |
| 14 | Distance 3 | Center | Gray | Passenger car or Truck or Motorbike | Car_Dis3_Center_Gray |  |
| 15 | Distance 3 | Center | Red | Passenger car or Truck or Motorbike | Car_Dis3_Center_Red |  |
| 16 | Distance 4 | Center | White | Passenger car or Truck or Motorbike | Car_Dis4_Center_White |  |
| 17 | Distance 4 | Center | Gray | Passenger car or Truck or Motorbike | Car_Dis4_Center_Gray |  |
| 18 | Distance 4 | Center | Red | Passenger car or Truck or Motorbike | Car_Dis4_Center_Red |  |
| 19 | Distance 1 | Left | White | Passenger car or Truck or Motorbike | Car_Dis1_Left_White |  |
| 20 | Distance 1 | Left | Gray | Passenger car or Truck or Motorbike | Car_Dis1_Left_Gray |  |
| 21 | Distance 1 | Left | Red | Passenger car or Truck or Motorbike | Car_Dis1_Left_Red |  |
| 22 | Distance 2 | Left | White | Passenger car or Truck or Motorbike | Car_Dis2_Left_White |  |
| 23 | Distance 2 | Left | Gray | Passenger car or Truck or Motorbike | Car_Dis2_Left_Gray |  |
| 24 | Distance 2 | Left | Red | Passenger car or Truck or Motorbike | Car_Dis2_Left_Red |  |
| 25 | Distance 3 | Left | White | Passenger car or Truck or Motorbike | Car_Dis3_Left_White |  |
| 26 | Distance 3 | Left | Gray | Passenger car or Truck or Motorbike | Car_Dis3_Left_Gray |  |
| 27 | Distance 3 | Left | Red | Passenger car or Truck or Motorbike | Car_Dis3_Left_Red |  |
| 28 | Distance 4 | Left | White | Passenger car or Truck or Motorbike | Car_Dis4_Left_White |  |
| 29 | Distance 4 | Left | Gray | Passenger car or Truck or Motorbike | Car_Dis4_Left_Gray |  |
| 30 | Distance 4 | Left | Red | Passenger car or Truck or Motorbike | Car_Dis4_Left_Red |  |
- Verification Criteria: Verify by executing test cases
- Verification Method: Software Qualification Test, System Qualification Test, Unit Test
- Verification Owner: FV, SW
- System Requirement State: Approved
- Primary Discipline: SW
- ASIL Rating: QM

###### TFDCX32348-13956: HMI - HMI_ACC_ADJACENT_VEHICLE_ICON_LEFT_FWIND (2 of 2) (System Requirement)
| No. | Input |  |  |  | Output | <Info> Meaning |
| --- | --- | --- | --- | --- | --- | --- |
| No. | Local Parameter - Adjacent_Vehicle_Distance_Left | Adjacent_Vehicle_Position_Left_FWIND | Local Parameter - Adjacent_Vehicle_Color_Left | Local Parameter - Adjacent_Vehicle_Type_Left | HMI - HMI_ACC_ADJACENT_VEHICLE_ICON_LEFT_FWIND | <Info> Meaning |
| 31 | Distance 1 | Left_Type1 | White | Passenger car or Truck or Motorbike | Car_Dis1_Left_1_White |  |
| 32 | Distance 1 | Left_Type1 | Gray | Passenger car or Truck or Motorbike | Car_Dis1_Left_1_Gray |  |
| 33 | Distance 1 | Left_Type1 | Gray | Pedestrian | Pedestrian_Dis1_Left_1_Gray |  |
| 34 | Distance 1 | Left_Type1 | Red | Passenger car or Truck or Motorbike | Car_Dis1_Left_1_Red |  |
| 35 | Distance 1 | Left_Type1 | Red | Pedestrian | Pedestrian_Dis1_Left_1_Red |  |
| 36 | Distance 2 | Left_Type1 | White | Passenger car or Truck or Motorbike | Car_Dis2_Left_1_White |  |
| 37 | Distance 2 | Left_Type1 | Gray | Passenger car or Truck or Motorbike | Car_Dis2_Left_1_Gray |  |
| 38 | Distance 2 | Left_Type1 | Gray | Pedestrian | Pedestrian_Dis2_Left_1_Gray |  |
| 39 | Distance 2 | Left_Type1 | Red | Passenger car or Truck or Motorbike | Car_Dis2_Left_1_Red |  |
| 40 | Distance 2 | Left_Type1 | Red | Pedestrian | Pedestrian_Dis2_Left_1_Red |  |
| 41 | Distance 3 | Left_Type1 | White | Passenger car or Truck or Motorbike | Car_Dis3_Left_1_White |  |
| 42 | Distance 3 | Left_Type1 | Gray | Passenger car or Truck or Motorbike | Car_Dis3_Left_1_Gray |  |
| 43 | Distance 3 | Left_Type1 | Gray | Pedestrian | Pedestrian_Dis3_Left_1_Gray |  |
| 44 | Distance 3 | Left_Type1 | Red | Passenger car or Truck or Motorbike | Car_Dis3_Left_1_Red |  |
| 45 | Distance 3 | Left_Type1 | Red | Pedestrian | Pedestrian_Dis3_Left_1_Red |  |
| 46 | Distance 4 | Left_Type1 | White | Passenger car or Truck or Motorbike | Car_Dis4_Left_1_White |  |
| 47 | Distance 4 | Left_Type1 | Gray | Passenger car or Truck or Motorbike | Car_Dis4_Left_1_Gray |  |
| 48 | Distance 4 | Left_Type1 | Gray | Pedestrian | Pedestrian_Dis4_Left_1_Gray |  |
| 49 | Distance 4 | Left_Type1 | Red | Passenger car or Truck or Motorbike | Car_Dis4_Left_1_Red |  |
| 50 | Distance 4 | Left_Type1 | Red | Pedestrian | Pedestrian_Dis4_Left_1_Red |  |
- Verification Criteria: Verify by executing test cases
- Verification Method: Software Qualification Test, System Qualification Test, Unit Test
- Verification Owner: FV, SW
- System Requirement State: Approved
- Primary Discipline: SW
- ASIL Rating: QM

##### TFDCX32348-32339: Logic Table - HMI - HMI_ACC_ADJACENT_VEHICLE_BLINK_LEFT/Warning ID - WRN_ADAS_ACC_G23 (System Requirement)
| No. | Input |  | Output |  |
| --- | --- | --- | --- | --- |
| No. | HMI - HMI_ACC_ADJACENT_VEHICLE_ICON_LEFT | Local Parameter - Adjacent_Vehicle_Blinking_left | HMI - HMI_ACC_ADJACENT_VEHICLE_BLINK_LEFT (*1) | Warning ID - WRN_ADAS_ACC_G23 (*2) (*3) |
| 1 | OFF | X | OFF | OFF |
| 2 | Other than above | OFF | OFF | OFF |
| 3 | Other than above | ON | ON | ON |
(*1) Detailed requirements on HMI_ACC_ADJACENT_VEHICLE_BLINK_LEFT
Case 1. Until 2 cycle time (2,000ms) passes since HMI_ACC_ADJACENT_VEHICLE_BLINK_LEFT = OFF -> ON is detected, Do not execute No.2 even if Adjacent_Vehicle_Blinking_Left = OFF is detected.
Case 2. After 2 cycle time (2,000ms) passes since HMI_ACC_ADJACENT_VEHICLE_BLINK_LEFT = OFF -> ON is detected, Execute No.2 immediately when Adjacent_Vehicle_Blinking_Left = OFF is detected.
Case 3. When HMI_ACC_ADJACENT_VEHICLE_ICON_LEFT = OFF is detected, Execute No.1 immediately.
(*2) The same requirements as for HMI_ACC_ADJACENT_VEHICLE_BLINK_LEFT also apply to the WRN_ADAS_ACC_G23.
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While HMI_ACC_ADJACENT_VEHICLE_BLINK_LEFT == ON, Blink control is necessary for Preceding Vehicle Moving icon.
Requirements for Blink control:
1. Cycle time is 1,000ms.
2. ON Duty is 50%.
3. At the beginning of the blinking, Turn on the icon display.
4. Cancel the icon blinking as soon as HMI_ACC_ADJACENT_VEHICLE_BLINK_LEFT is changed from ON to OFF.
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(*3) For WRN_ADAS_ACC_G23, Update the value immediately when Input condition changes.
- Verification Criteria: Verify by executing test cases
- Verification Method: Software Qualification Test, System Qualification Test, Unit Test
- Verification Owner: FV, SW
- System Requirement State: Approved
- Primary Discipline: SW
- ASIL Rating: QM

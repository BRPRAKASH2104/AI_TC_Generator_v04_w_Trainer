# Json2ReqIF Transformation

# Specification: MM_NAV_Map_Drawing
- JDA Snapshot Date: 2025-09-04 03:04:45

## TFDCX32348-49732: MM_NAV_Map_Drawing (Heading)

## TFDCX32348-49733: History (Heading)

### TFDCX32348-49740: Table (Information)
| Version | Date | Name | Description of change | Baseline |
| --- | --- | --- | --- | --- |
| 0.1 | 18/Oct/2024 | Hiromune Wachi | Newly create for 12.3inch FDC. [SYS-Story] : TFDCX32348-34270: [SYS][12.3FDC][APP][MM] [Common] GVIF Video display sequence Specification | BL_20241024_01 |
| 0.2 | 6/Feb/2025 | Hiromune Wachi | Changed the judgment of MMNavMAPViewPresence and added change to keep MMNavMAPViewPresence in backup RAM. [SYS-Story] : TFDCX32348-67202: [SYS][12.3FDC][APP][MM] [Common] GVIF Video display sequence Specification(changed by MET-G_T_SCREEN-CSTD-A0-09-A-C0 update) | BL_20250218_01 |
| 0.3 | May/30/2025 | Hiromune Wachi | Changed the method for determining M_GVIF_FLG (added a check for MCUID). [SYS-Story] : TFDCX32348-85835: [SYS][12.3FDC][R6.1][D3632][APP][MM] 24MM meter x multimedia linkage requirement specifications for "Audio and Navi map" | BL_20250710_01 |

## TFDCX32348-49734: Overview (Heading)

### TFDCX32348-49741: This SRD defines the control for displaying GVIF video sent from MM on MET. (Information)

## TFDCX32348-49735: References (Heading)

### TFDCX32348-49736: External Sources (Heading)

#### TFDCX32348-49828 (Information)
156_MM×MET 映像表示シーケンス仕様書 Ver3.50_19v3-R2.xlsx
【別紙】3.3.04.4.8 NAV地図描画機能仕様書_19v3_METXMM-NAVMAP-X3-3.30_19v3-R4.docx

## TFDCX32348-49737: Input Requirements (Heading)

### TFDCX32348-50075: InternalSignal - ACCStatus (System Interface)
- System Requirement State: Approved

### TFDCX32348-50076: Internal Signal - HMI_BaseView (System Interface)
- System Requirement State: Approved

### TFDCX32348-50279: Internal Signal - HMI_ScreenMode (System Interface)
- System Requirement State: Approved

### TFDCX32348-50077: MMCANSignal - V_OUT_MODE (System Interface)
- System Requirement State: Approved

### TFDCX32348-50078: MMCANSignal - V_OUT_COUNT (System Interface)
- System Requirement State: Approved

### TFDCX32348-50079: MMCANSignal - V_OUT_NAV_STS (System Interface)
- System Requirement State: Approved

### TFDCX32348-50080: MMCANSignal - V_OUT_PROJ_STS (System Interface)
- System Requirement State: Approved

### TFDCX32348-50081: MMCANSignal - V_OUT_ACT_MAP (System Interface)
- System Requirement State: Approved

### TFDCX32348-50082: MMCANSignal - V_OUT_STS (System Interface)
- System Requirement State: Approved

### TFDCX32348-88270: MCUCONST - MCUID1123 (System Interface)
- System Requirement State: Approved

## TFDCX32348-49738: Output Requirements (Heading)

### TFDCX32348-50083: MMCANSignal - V_REQ_MODE (System Interface)
- System Requirement State: Approved

### TFDCX32348-50084: MMCANSignal - V_REQ_COUNT (System Interface)
- System Requirement State: Approved

### TFDCX32348-50085: MMCANSignal - M_RESOLUTION (System Interface)
- System Requirement State: Approved

### TFDCX32348-50087: MMCANSignal - M_DISP_INCH (System Interface)
- System Requirement State: Approved

### TFDCX32348-50088: MMCANSignal - M_GVIF_FLG (System Interface)
- System Requirement State: Approved

### TFDCX32348-50089: HMI - HMI_NAV_MAP_DISP (System Interface)
HMI - HMI_NAV_MAP_DISP
Range : 0[No display], 1[Map display(Navi)], 2[Map display(CarPlay)], 3[Map display(AndroidAuto)], 4[Map display(Blank)]
- System Requirement State: Approved

### TFDCX32348-51031: InternalSignal - MMNavMAPViewPresence (System Interface)
InternalSignal - MMNavMAPViewPresence
Range : 0[Absence], 1[Presence]
- System Requirement State: Approved

## TFDCX32348-49739: Performance Requirements (Heading)

### TFDCX32348-50092: General (Heading)

#### TFDCX32348-50093: MM_NAV_Map_Drawing Relationship (Heading)

##### TFDCX32348-50095: Figure - MM_NAV_Map_Drawing Relationship (Information)
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
#### TFDCX32348-50094: Processing block structure (Heading)

##### TFDCX32348-50091: Figure - Processing block structure (System Requirement)
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- Verification Criteria: Verify by design review
- Verification Method: Code/Design Review
- Verification Owner: SW
- System Requirement State: Approved
- Primary Discipline: SW
- ASIL Rating: QM

##### TFDCX32348-50258: Table - Processing block structure (System Requirement)
| # | Signal name | Range |
| --- | --- | --- |
| ①-1 | ReqMode | 0000b[No output], 0001b[Map] |
| ①-2 | ReqCount | 00h, 01h, 02h, …, FFh |
- Verification Criteria: Verify by design review
- Verification Method: Code/Design Review
- Verification Owner: SW
- System Requirement State: Approved
- Primary Discipline: SW
- ASIL Rating: QM

### TFDCX32348-50260: Processing (Heading)

#### TFDCX32348-50261: [A] Initialization (Heading)

##### TFDCX32348-50265: Table - Initialization (System Requirement)
| # | Output Signal name | Initilize @ Battery Connect | Initialize @ Module Wake-Up | Init Value | Remark |
| --- | --- | --- | --- | --- | --- |
| 1 | MMCANSignal - V_REQ_MODE | 〇 | 〇 | 0000b[No output] | Output from this feature. |
| 2 | MMCANSignal - V_REQ_COUNT | 〇 | 〇 | 00h | Output from this feature. |
| 3 | MMCANSignal - M_RESOLUTION | 〇 | 〇 | 0000b[Initial value] | Output from this feature. |
| 4 | MMCANSignal - M_DISP_INCH | 〇 | 〇 | 0000b[Initial value] | Output from this feature. |
| 5 | MMCANSignal - M_GVIF_FLG | 〇 | 〇 | 00b[Initial value] | Output from this feature. |
| 6 | HMI - HMI_NAV_MAP_DISP | 〇 | 〇 | 0[No display] | Output from this feature. |
| 7 | BURAM_MMNavMAPViewPresence | 〇 | X | 0[Absence] | Using by [A] block and [D] block. (Battery backup required) |
| 8 | InternalSignal - MMNavMAPViewPresence | 〇 | 〇 | BURAM_MMNavMAPViewPresence | Output from this feature. |
| 9 | ReqMode | 〇 | 〇 | 0000b[No output] | Output form [D] block. |
| 10 | ReqCount | 〇 | 〇 | 00h | Output form [D] block. |
| 11 | Previous_HMI_BaseView | 〇 | 〇 | FFh | Using by [D] block. |
- Verification Criteria: Verify by executing test cases
- Verification Method: System Qualification Test, Unit Test
- Verification Owner: FV, SW
- System Requirement State: Approved
- Primary Discipline: SW
- ASIL Rating: QM

#### TFDCX32348-51034: [B] MMNavigtion MAP View check (Heading)
- System Requirement State: Draft
- Primary Discipline: TBD
- ASIL Rating: TBD

##### TFDCX32348-51035: Table - MMNavigtion MAP View check (System Requirement)
| # | Input |  |  |  | Output |
| --- | --- | --- | --- | --- | --- |
| # | InternalSignal - ACCStatus | MMCANSignal Communication Status – V_OUT_NAV_STS [*1] | MMCANSignal - V_OUT_NAV_STS [*1] | MMCANSignal - V_OUT_PROJ_STS [*1] | BURAM_MMNavMAPViewPresence |
| 1 | OFF | X | X | X | No change |
| 2 | ON | Never received (Never Received: 1 Communication Failure: 0) | X | X | No change |
| 3 | ON | Normal (Never Received: 0 Communication Failure: 0) | 0000b[Init value] | 0000b[Init value] | No change |
| 4 | ON | Normal (Never Received: 0 Communication Failure: 0) | 0000b[Init value] | 0001b[Available] | 1[Presence] |
| 5 | ON | Normal (Never Received: 0 Communication Failure: 0) | 0000b[Init value] | 0011b[Non-available] | 1[Presence] |
| 6 | ON | Normal (Never Received: 0 Communication Failure: 0) | 0000b[Init value] | Other than above | 0[Absence] |
| 7 | ON | Normal (Never Received: 0 Communication Failure: 0) | 0001b[Available] | X | 1[Presence] |
| 8 | ON | Normal (Never Received: 0 Communication Failure: 0) | 0011b[Non-available] | X | 1[Presence] |
| 9 | ON | Normal (Never Received: 0 Communication Failure: 0) | Other than above | 0000b[Init value] | 0[Absence] |
| 10 | ON | Normal (Never Received: 0 Communication Failure: 0) | Other than above | 0001b[Available] | 1[Presence] |
| 11 | ON | Normal (Never Received: 0 Communication Failure: 0) | Other than above | 0011b[Non-available] | 1[Presence] |
| 12 | ON | Normal (Never Received: 0 Communication Failure: 0) | Other than above | Other than above | 0[Absence] |
[*1] : All Input MMCAN Signals are included in AVNMS81, so it only needs to check one signal.
And these MMCAN signals have no communication failure state.
| # | Input | Output |
| --- | --- | --- |
| # | InternalSignal - ACCStatus | InternalSignal - MMNavMAPViewPresence |
| 1 | OFF | No change |
| 2 | ON | BURAM_MMNavMAPViewPresence |
- Verification Criteria: Verify by executing test cases
- Verification Method: System Qualification Test, Unit Test
- Verification Owner: FV, SW
- System Requirement State: Approved
- Primary Discipline: SW
- ASIL Rating: QM

#### TFDCX32348-50262: [C] Meter status notification control (Heading)

##### TFDCX32348-50266: Table - Meter status notification control (System Requirement)
| # | Input |  | Output |  |  |
| --- | --- | --- | --- | --- | --- |
| # | InternalSignal - ACCStatus | MCUCONST - MCUID1123 | MMCANSignal - M_RESOLUTION | MMCANSignal - M_DISP_INCH | MMCANSignal - M_GVIF_FLG |
| 1 | OFF | X | No change | No change | No change |
| 2 | ON | 1[present] | 0010b[1920×720(Display size is 12.3inch)] | 0011b[12.3inch] | 01b[Present] |
| 3 | ON | 0[not present] | 0010b[1920×720(Display size is 12.3inch)] | 0011b[12.3inch] | 10b[Not present] |
- Verification Criteria: Verify by executing test cases
- Verification Method: System Qualification Test, Unit Test
- Verification Owner: FV, SW
- System Requirement State: Approved
- Primary Discipline: SW
- ASIL Rating: QM

#### TFDCX32348-50263: [D] Video display status control (Heading)

##### TFDCX32348-50269: Table - Video display status control (System Requirement)
| # | Input |  |  |  | Output |  |  |
| --- | --- | --- | --- | --- | --- | --- | --- |
| # | InternalSignal - ACCStatus | Internal Signal - HMI_ScreenMode | Previous_HMI_BaseView | ReqCount(Previous value) | MMCANSignal - V_REQ_MODE / ReqMode | MMCANSignal - V_REQ_COUNT / ReqCount | Previous_HMI_BaseView |
| 1 | OFF | X | X | X | 0000b[No output] | 00h | FFh |
| 2 | ON | Other than NORMAL | == FFh | X | No change | No change | No change |
| 3 | ON | Other than NORMAL | != FFh | Other than FFh | 0000b[No output] | Increase by 1. | FFh |
| 4 | ON | Other than NORMAL | != FFh | FFh | 0000b[No output] | 01h | FFh |
| 5 | ON | NORMAL | != Internal Signal - HMI_BaseView | X | Refer to [*1] |  | Internal Signal - HMI_BaseView |
| 6 | ON | NORMAL | == Internal Signal - HMI_BaseView | X | No change | No change | No change |
[*1] : Judge according to the table below.
| # | Input |  | Output |  |
| --- | --- | --- | --- | --- |
| # | Internal Signal - HMI_BaseView | ReqCount(Previous value) | MMCANSignal - V_REQ_MODE / ReqMode | MMCANSignal - V_REQ_COUNT / ReqCount |
| 1 | 3:VIEW_MAP | Other than FFh | 0001b[Map] | Increase by 1. |
| 2 | 3:VIEW_MAP | FFh | 0001b[Map] | 01h |
| 3 | Other than “3:VIEW_MAP” | Other than FFh | 0000b[No output] | Increase by 1. |
| 4 | Other than “3:VIEW_MAP” | FFh | 0000b[No output] | 01h |
- Verification Criteria: Verify by executing test cases
- Verification Method: System Qualification Test, Unit Test
- Verification Owner: FV, SW
- System Requirement State: Approved
- Primary Discipline: SW
- ASIL Rating: QM

#### TFDCX32348-50264: [E] HMI output data control (Heading)

##### TFDCX32348-50326: Table - HMI output data control (System Requirement)
| # | Input |  |  |  | Output |
| --- | --- | --- | --- | --- | --- |
| # | InternalSignal - ACCStatus | ReqMode | MMCANSignal Communication Status – V_OUT_COUNT [*1] | ReqCount | HMI - HMI_NAV_MAP_DISP |
| 1 | OFF | X | X | X | 0[No display] |
| 2 | ON | 0000b[No output] | X | X | 0[No display] |
| 3 | ON | 0001b[Map] | Never received (Never Received: 1 Communication Failure: 0) | X | 4[Map display(Blank)] |
| 4 | ON | 0001b[Map] | Normal (Never Received: 0 Communication Failure: 0) | != MMCANSignal - V_OUT_COUNT | 4[Map display(Blank)] |
| 5 | ON | 0001b[Map] | Normal (Never Received: 0 Communication Failure: 0) | == MMCANSignal - V_OUT_COUNT | Refer to [*2] |
[*1] : “MMCANSignal - V_OUT_COUNT” has no communication failure state.
And this signal is included in AVNMS80.
[*2] : Judge according to the table below.
| # | Input |  |  |  |  |  | Output |
| --- | --- | --- | --- | --- | --- | --- | --- |
| # | MMCANSignal Communication Status – V_OUT_STS [*3] | MMCANSignal - V_OUT_MODE [*4] | MMCANSignal - V_OUT_STS [*3] | MMCANSignal - V_OUT_ACT_MAP [*3] | MMCANSignal - V_OUT_NAV_STS [*3] | MMCANSignal - V_OUT_PROJ_STS [*3] | HMI - HMI_NAV_MAP_DISP |
| 1 | Never received (Never Received: 1 Communication Failure: 0) | X | X | X | X | X | 4[Map display(Blank)] |
| 2 | Normal (Never Received: 0 Communication Failure: 0) | Other than 0001b[Map] | X | X | X | X | 4[Map display(Blank)] |
| 3 | Normal (Never Received: 0 Communication Failure: 0) | 0001b[Map] | Other than 01b[Outputting] | X | X | X | 4[Map display(Blank)] |
| 4 | Normal (Never Received: 0 Communication Failure: 0) | 0001b[Map] | 01b[Outputting] | 0010b[Navi] | Other than 0001b[Available] | X | 4[Map display(Blank)] |
| 5 | Normal (Never Received: 0 Communication Failure: 0) | 0001b[Map] | 01b[Outputting] | 0010b[Navi] | 0001b[Available] | X | 1[Map display(Navi)] |
| 6 | Normal (Never Received: 0 Communication Failure: 0) | 0001b[Map] | 01b[Outputting] | 0011b[CarPlay] | X | Other than 0001b[Available] | 4[Map display(Blank)] |
| 7 | Normal (Never Received: 0 Communication Failure: 0) | 0001b[Map] | 01b[Outputting] | 0011b[CarPlay] | X | 0001b[Available] | 2[Map display(CarPlay)] |
| 8 | Normal (Never Received: 0 Communication Failure: 0) | 0001b[Map] | 01b[Outputting] | 0100b[Android Auto] | X | Other than 0001b[Available] | 4[Map display(Blank)] |
| 9 | Normal (Never Received: 0 Communication Failure: 0) | 0001b[Map] | 01b[Outputting] | 0100b[Android Auto] | X | 0001b[Available] | 3[Map display(AndroidAuto)] |
| 10 | Normal (Never Received: 0 Communication Failure: 0) | 0001b[Map] | Other than above |  |  |  | 4[Map display(Blank)] |
[*3] : All Input MMCAN Signals are included in AVNMS81, so it only needs to check one signal.
And these MMCAN signals have no communication failure state.
[*4] : “MMCANSignal - V_OUT_MODE” has no communication failure state.
And this signal is included in AVNMS80, and the "Never received" status has been checked at [*1].
- Verification Criteria: Verify by executing test cases
- Verification Method: System Qualification Test, Unit Test
- Verification Owner: FV, SW
- System Requirement State: Approved
- Primary Discipline: SW
- ASIL Rating: QM

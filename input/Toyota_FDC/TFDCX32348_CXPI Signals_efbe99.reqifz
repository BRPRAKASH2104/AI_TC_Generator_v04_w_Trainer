# Json2ReqIF Transformation

# Specification: CXPI Signals
- JDA Snapshot Date: 2025-09-04 02:36:26

## TFDCX32348-9429: CXPI Signals (Heading)

## TFDCX32348-9431: History (Heading)

### TFDCX32348-12097: History (Information)
| Version | Date | Name | Description of change | SRD Baseline |
| --- | --- | --- | --- | --- |
| 1.0 | 10/Jun/2024 | ttakaba | TFDCX32348-23804: [SYS][12.3FDC][APP][CXPI] General Specification First release. | BL_20240617_01 |
| 1.1 | 11/Mar/2025 | ttakaba | TFDCX32348-34151 [SYS][12.3FDC][APP][CXPI] Zone CXPI2 communication specification 27788, 72802 Added CXMET1S01 - METEER (Meter Error) output signal. | BL_20250311_01 |
| 1.1a | 21/Mar/2025 | ttakaba | Specification level up through the defect dialog in TFDCX32348-71715: [12.3 FDC] CXPI Tx Event message transmitted without Event trigger . Added a comment that Cycle time specified in the CXPI summary is just information since the PID transmission for the periodic timing is done by the master. |  |

## TFDCX32348-9433: Overview (Heading)

### TFDCX32348-12099: Overview (Information)
This module is provided to make links between CXPI signals and the appications. The application which uses or outputs CXPI signals shall make links to the CXPI signals defined in this module. Also CXPI signal characteristics shall be registered into CXPI summary sheet in below.

## TFDCX32348-27722: Reference Documents (Heading)

### TFDCX32348-27723: Reference documents (Information)
gncxpivehcs-ZON2-1006-a.xlsx

## TFDCX32348-9435: CXPI Summary Sheet (Heading)

### TFDCX32348-27788: CXPI Summary Sheet (Excel File) (System Interface)
Rev. 1.1a (Attachment)
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- Verification Criteria: Verify by code review
- Verification Method: Code/Design Review
- Verification Owner: SW
- System Requirement State: Approved
- Primary Discipline: SW
- ASIL Rating: QM

## TFDCX32348-9437: CXPI Rx signals (Heading)

### TFDCX32348-27664: PID $68 CXSWS1S01 (System Interface)
- Verification Criteria: Verify by code review
- Verification Method: Code/Design Review
- Verification Owner: SW
- System Requirement State: Approved
- Primary Discipline: SW
- ASIL Rating: QM

#### TFDCX32348-27665: $68 CXSWS1S01 - COUNT_1 (System Interface)
- Verification Criteria: Verify by code review
- Verification Method: Code/Design Review
- Verification Owner: SW
- System Requirement State: Approved
- Primary Discipline: SW
- ASIL Rating: QM

#### TFDCX32348-27666: $68 CXSWS1S01 - SWS_1_1 (System Interface)
- Verification Criteria: Verify by code review
- Verification Method: Code/Design Review
- Verification Owner: SW
- System Requirement State: Approved
- Primary Discipline: SW
- ASIL Rating: QM

#### TFDCX32348-27667: $68 CXSWS1S01 - SWS_1_9 (System Interface)
- Verification Criteria: Verify by code review
- Verification Method: Code/Design Review
- Verification Owner: SW
- System Requirement State: Approved
- Primary Discipline: SW
- ASIL Rating: QM

#### TFDCX32348-27668: $68 CXSWS1S01 - SWS_1_10 (System Interface)
- Verification Criteria: Verify by code review
- Verification Method: Code/Design Review
- Verification Owner: SW
- System Requirement State: Approved
- Primary Discipline: SW
- ASIL Rating: QM

#### TFDCX32348-27669: $68 CXSWS1S01 - SWS_1_11 (System Interface)
- Verification Criteria: Verify by code review
- Verification Method: Code/Design Review
- Verification Owner: SW
- System Requirement State: Approved
- Primary Discipline: SW
- ASIL Rating: QM

#### TFDCX32348-27670: $68 CXSWS1S01 - SWS_1_12 (System Interface)
- Verification Criteria: Verify by code review
- Verification Method: Code/Design Review
- Verification Owner: SW
- System Requirement State: Approved
- Primary Discipline: SW
- ASIL Rating: QM

#### TFDCX32348-27671: $68 CXSWS1S01 - SWS_1_13 (System Interface)
- Verification Criteria: Verify by code review
- Verification Method: Code/Design Review
- Verification Owner: SW
- System Requirement State: Approved
- Primary Discipline: SW
- ASIL Rating: QM

#### TFDCX32348-27672: $68 CXSWS1S01 - SWS_1_14 (System Interface)
- Verification Criteria: Verify by code review
- Verification Method: Code/Design Review
- Verification Owner: SW
- System Requirement State: Approved
- Primary Discipline: SW
- ASIL Rating: QM

#### TFDCX32348-27673: $68 CXSWS1S01 - SWS_1_15 (System Interface)
- Verification Criteria: Verify by code review
- Verification Method: Code/Design Review
- Verification Owner: SW
- System Requirement State: Approved
- Primary Discipline: SW
- ASIL Rating: QM

#### TFDCX32348-27674: $68 CXSWS1S01 - SWS_1_16 (System Interface)
- Verification Criteria: Verify by code review
- Verification Method: Code/Design Review
- Verification Owner: SW
- System Requirement State: Approved
- Primary Discipline: SW
- ASIL Rating: QM

#### TFDCX32348-27675: $68 CXSWS1S01 - SWS_1_17 (System Interface)
- Verification Criteria: Verify by code review
- Verification Method: Code/Design Review
- Verification Owner: SW
- System Requirement State: Approved
- Primary Discipline: SW
- ASIL Rating: QM

#### TFDCX32348-27676: $68 CXSWS1S01 - SWS_1_18 (System Interface)
- Verification Criteria: Verify by code review
- Verification Method: Code/Design Review
- Verification Owner: SW
- System Requirement State: Approved
- Primary Discipline: SW
- ASIL Rating: QM

#### TFDCX32348-27677: $68 CXSWS1S01 - SWS_1_19 (System Interface)
- Verification Criteria: Verify by code review
- Verification Method: Code/Design Review
- Verification Owner: SW
- System Requirement State: Approved
- Primary Discipline: SW
- ASIL Rating: QM

#### TFDCX32348-27678: $68 CXSWS1S01 - SWS_1_20 (System Interface)
- Verification Criteria: Verify by code review
- Verification Method: Code/Design Review
- Verification Owner: SW
- System Requirement State: Approved
- Primary Discipline: SW
- ASIL Rating: QM

#### TFDCX32348-27679: $68 CXSWS1S01 - SWS_1_21 (System Interface)
- Verification Criteria: Verify by code review
- Verification Method: Code/Design Review
- Verification Owner: SW
- System Requirement State: Approved
- Primary Discipline: SW
- ASIL Rating: QM

#### TFDCX32348-27680: $68 CXSWS1S01 - SWS_1_22 (System Interface)
- Verification Criteria: Verify by code review
- Verification Method: Code/Design Review
- Verification Owner: SW
- System Requirement State: Approved
- Primary Discipline: SW
- ASIL Rating: QM

#### TFDCX32348-27681: $68 CXSWS1S01 - SWS_1_23 (System Interface)
- Verification Criteria: Verify by code review
- Verification Method: Code/Design Review
- Verification Owner: SW
- System Requirement State: Approved
- Primary Discipline: SW
- ASIL Rating: QM

#### TFDCX32348-27682: $68 CXSWS1S01 - SWS_1_24 (System Interface)
- Verification Criteria: Verify by code review
- Verification Method: Code/Design Review
- Verification Owner: SW
- System Requirement State: Approved
- Primary Discipline: SW
- ASIL Rating: QM

#### TFDCX32348-27683: $68 CXSWS1S01 - SWS_1_25 (System Interface)
- Verification Criteria: Verify by code review
- Verification Method: Code/Design Review
- Verification Owner: SW
- System Requirement State: Approved
- Primary Discipline: SW
- ASIL Rating: QM

#### TFDCX32348-27684: $68 CXSWS1S01 - SWS_1_26 (System Interface)
- Verification Criteria: Verify by code review
- Verification Method: Code/Design Review
- Verification Owner: SW
- System Requirement State: Approved
- Primary Discipline: SW
- ASIL Rating: QM

#### TFDCX32348-27685: $68 CXSWS1S01 - SWS_1_27 (System Interface)
- Verification Criteria: Verify by code review
- Verification Method: Code/Design Review
- Verification Owner: SW
- System Requirement State: Approved
- Primary Discipline: SW
- ASIL Rating: QM

#### TFDCX32348-27686: $68 CXSWS1S01 - SWS_1_28 (System Interface)
- Verification Criteria: Verify by code review
- Verification Method: Code/Design Review
- Verification Owner: SW
- System Requirement State: Approved
- Primary Discipline: SW
- ASIL Rating: QM

#### TFDCX32348-27687: $68 CXSWS1S01 - SWS_1_29 (System Interface)
- Verification Criteria: Verify by code review
- Verification Method: Code/Design Review
- Verification Owner: SW
- System Requirement State: Approved
- Primary Discipline: SW
- ASIL Rating: QM

#### TFDCX32348-27688: $68 CXSWS1S01 - SWS_1_30 (System Interface)
- Verification Criteria: Verify by code review
- Verification Method: Code/Design Review
- Verification Owner: SW
- System Requirement State: Approved
- Primary Discipline: SW
- ASIL Rating: QM

#### TFDCX32348-27689: $68 CXSWS1S01 - SWS_1_31 (System Interface)
- Verification Criteria: Verify by code review
- Verification Method: Code/Design Review
- Verification Owner: SW
- System Requirement State: Approved
- Primary Discipline: SW
- ASIL Rating: QM

#### TFDCX32348-27690: $68 CXSWS1S01 - SWS_1_32 (System Interface)
- Verification Criteria: Verify by code review
- Verification Method: Code/Design Review
- Verification Owner: SW
- System Requirement State: Approved
- Primary Discipline: SW
- ASIL Rating: QM

#### TFDCX32348-27691: $68 CXSWS1S01 - SWS_1_33 (System Interface)
- Verification Criteria: Verify by code review
- Verification Method: Code/Design Review
- Verification Owner: SW
- System Requirement State: Approved
- Primary Discipline: SW
- ASIL Rating: QM

#### TFDCX32348-27692: $68 CXSWS1S01 - SWS_1_34 (System Interface)
- Verification Criteria: Verify by code review
- Verification Method: Code/Design Review
- Verification Owner: SW
- System Requirement State: Approved
- Primary Discipline: SW
- ASIL Rating: QM

#### TFDCX32348-27693: $68 CXSWS1S01 - SWS_1_35 (System Interface)
- Verification Criteria: Verify by code review
- Verification Method: Code/Design Review
- Verification Owner: SW
- System Requirement State: Approved
- Primary Discipline: SW
- ASIL Rating: QM

#### TFDCX32348-27694: $68 CXSWS1S01 - SWS_1_36 (System Interface)
- Verification Criteria: Verify by code review
- Verification Method: Code/Design Review
- Verification Owner: SW
- System Requirement State: Approved
- Primary Discipline: SW
- ASIL Rating: QM

#### TFDCX32348-27695: $68 CXSWS1S01 - SWS_1_37 (System Interface)
- Verification Criteria: Verify by code review
- Verification Method: Code/Design Review
- Verification Owner: SW
- System Requirement State: Approved
- Primary Discipline: SW
- ASIL Rating: QM

#### TFDCX32348-27696: $68 CXSWS1S01 - SWS_1_38 (System Interface)
- Verification Criteria: Verify by code review
- Verification Method: Code/Design Review
- Verification Owner: SW
- System Requirement State: Approved
- Primary Discipline: SW
- ASIL Rating: QM

#### TFDCX32348-27697: $68 CXSWS1S01 - SWS_1_39 (System Interface)
- Verification Criteria: Verify by code review
- Verification Method: Code/Design Review
- Verification Owner: SW
- System Requirement State: Approved
- Primary Discipline: SW
- ASIL Rating: QM

#### TFDCX32348-27698: $68 CXSWS1S01 - SWS_1_40 (System Interface)
- Verification Criteria: Verify by code review
- Verification Method: Code/Design Review
- Verification Owner: SW
- System Requirement State: Approved
- Primary Discipline: SW
- ASIL Rating: QM

#### TFDCX32348-27699: $68 CXSWS1S01 - SWS_1_41 (System Interface)
- Verification Criteria: Verify by code review
- Verification Method: Code/Design Review
- Verification Owner: SW
- System Requirement State: Approved
- Primary Discipline: SW
- ASIL Rating: QM

#### TFDCX32348-27700: $68 CXSWS1S01 - SWS_1_42 (System Interface)
- Verification Criteria: Verify by code review
- Verification Method: Code/Design Review
- Verification Owner: SW
- System Requirement State: Approved
- Primary Discipline: SW
- ASIL Rating: QM

#### TFDCX32348-27701: $68 CXSWS1S01 - SWS_1_43 (System Interface)
- Verification Criteria: Verify by code review
- Verification Method: Code/Design Review
- Verification Owner: SW
- System Requirement State: Approved
- Primary Discipline: SW
- ASIL Rating: QM

#### TFDCX32348-27702: $68 CXSWS1S01 - SWS_1_44 (System Interface)
- Verification Criteria: Verify by code review
- Verification Method: Code/Design Review
- Verification Owner: SW
- System Requirement State: Approved
- Primary Discipline: SW
- ASIL Rating: QM

#### TFDCX32348-27703: $68 CXSWS1S01 - SWS_1_45 (System Interface)
- Verification Criteria: Verify by code review
- Verification Method: Code/Design Review
- Verification Owner: SW
- System Requirement State: Approved
- Primary Discipline: SW
- ASIL Rating: QM

#### TFDCX32348-27704: $68 CXSWS1S01 - SWS_1_46 (System Interface)
- Verification Criteria: Verify by code review
- Verification Method: Code/Design Review
- Verification Owner: SW
- System Requirement State: Approved
- Primary Discipline: SW
- ASIL Rating: QM

#### TFDCX32348-27705: $68 CXSWS1S01 - SWS_1_47 (System Interface)
- Verification Criteria: Verify by code review
- Verification Method: Code/Design Review
- Verification Owner: SW
- System Requirement State: Approved
- Primary Discipline: SW
- ASIL Rating: QM

#### TFDCX32348-27706: $68 CXSWS1S01 - SWS_1_48 (System Interface)
- Verification Criteria: Verify by code review
- Verification Method: Code/Design Review
- Verification Owner: SW
- System Requirement State: Approved
- Primary Discipline: SW
- ASIL Rating: QM

#### TFDCX32348-27707: $68 CXSWS1S01 - SWS_1_49 (System Interface)
- Verification Criteria: Verify by code review
- Verification Method: Code/Design Review
- Verification Owner: SW
- System Requirement State: Approved
- Primary Discipline: SW
- ASIL Rating: QM

#### TFDCX32348-27708: $68 CXSWS1S01 - SWS_1_50 (System Interface)
- Verification Criteria: Verify by code review
- Verification Method: Code/Design Review
- Verification Owner: SW
- System Requirement State: Approved
- Primary Discipline: SW
- ASIL Rating: QM

#### TFDCX32348-27709: $68 CXSWS1S01 - SWS_1_51 (System Interface)
- Verification Criteria: Verify by code review
- Verification Method: Code/Design Review
- Verification Owner: SW
- System Requirement State: Approved
- Primary Discipline: SW
- ASIL Rating: QM

#### TFDCX32348-27710: $68 CXSWS1S01 - SWS_1_52 (System Interface)
- Verification Criteria: Verify by code review
- Verification Method: Code/Design Review
- Verification Owner: SW
- System Requirement State: Approved
- Primary Discipline: SW
- ASIL Rating: QM

#### TFDCX32348-27711: $68 CXSWS1S01 - SWS_1_53 (System Interface)
- Verification Criteria: Verify by code review
- Verification Method: Code/Design Review
- Verification Owner: SW
- System Requirement State: Approved
- Primary Discipline: SW
- ASIL Rating: QM

#### TFDCX32348-27712: $68 CXSWS1S01 - SWS_1_54 (System Interface)
- Verification Criteria: Verify by code review
- Verification Method: Code/Design Review
- Verification Owner: SW
- System Requirement State: Approved
- Primary Discipline: SW
- ASIL Rating: QM

#### TFDCX32348-27713: $68 CXSWS1S01 - SWS_1_55 (System Interface)
- Verification Criteria: Verify by code review
- Verification Method: Code/Design Review
- Verification Owner: SW
- System Requirement State: Approved
- Primary Discipline: SW
- ASIL Rating: QM

#### TFDCX32348-27714: $68 CXSWS1S01 - SWS_1_56 (System Interface)
- Verification Criteria: Verify by code review
- Verification Method: Code/Design Review
- Verification Owner: SW
- System Requirement State: Approved
- Primary Discipline: SW
- ASIL Rating: QM

#### TFDCX32348-27715: $68 CXSWS1S01 - SWS_1_57 (System Interface)
- Verification Criteria: Verify by code review
- Verification Method: Code/Design Review
- Verification Owner: SW
- System Requirement State: Approved
- Primary Discipline: SW
- ASIL Rating: QM

#### TFDCX32348-27716: $68 CXSWS1S01 - SWS_1_58 (System Interface)
- Verification Criteria: Verify by code review
- Verification Method: Code/Design Review
- Verification Owner: SW
- System Requirement State: Approved
- Primary Discipline: SW
- ASIL Rating: QM

#### TFDCX32348-27717: $68 CXSWS1S01 - SWS_1_59 (System Interface)
- Verification Criteria: Verify by code review
- Verification Method: Code/Design Review
- Verification Owner: SW
- System Requirement State: Approved
- Primary Discipline: SW
- ASIL Rating: QM

#### TFDCX32348-27718: $68 CXSWS1S01 - SWS_1_60 (System Interface)
- Verification Criteria: Verify by code review
- Verification Method: Code/Design Review
- Verification Owner: SW
- System Requirement State: Approved
- Primary Discipline: SW
- ASIL Rating: QM

#### TFDCX32348-27719: $68 CXSWS1S01 - SWS_1_61 (System Interface)
- Verification Criteria: Verify by code review
- Verification Method: Code/Design Review
- Verification Owner: SW
- System Requirement State: Approved
- Primary Discipline: SW
- ASIL Rating: QM

#### TFDCX32348-27720: $68 CXSWS1S01 - SWS_1_62 (System Interface)
- Verification Criteria: Verify by code review
- Verification Method: Code/Design Review
- Verification Owner: SW
- System Requirement State: Approved
- Primary Discipline: SW
- ASIL Rating: QM

#### TFDCX32348-27721: $68 CXSWS1S01 - SWS_1_63 (System Interface)
- Verification Criteria: Verify by code review
- Verification Method: Code/Design Review
- Verification Owner: SW
- System Requirement State: Approved
- Primary Discipline: SW
- ASIL Rating: QM

### TFDCX32348-12107: PID $F8 CXSWS1S02 (System Interface)
- Verification Criteria: Verify by code review
- Verification Method: Code/Design Review
- Verification Owner: SW
- System Requirement State: Approved
- Primary Discipline: SW
- ASIL Rating: QM

#### TFDCX32348-27725: $F8 CXSWS1S02 - COUNT_2 (System Interface)
- Verification Criteria: Verify by code review
- Verification Method: Code/Design Review
- Verification Owner: SW
- System Requirement State: Approved
- Primary Discipline: SW
- ASIL Rating: QM

#### TFDCX32348-27726: $F8 CXSWS1S02 - SWS_2_1 (System Interface)
- Verification Criteria: Verify by code review
- Verification Method: Code/Design Review
- Verification Owner: SW
- System Requirement State: Approved
- Primary Discipline: SW
- ASIL Rating: QM

#### TFDCX32348-27727: $F8 CXSWS1S02 - SWS_2_9 (System Interface)
- Verification Criteria: Verify by code review
- Verification Method: Code/Design Review
- Verification Owner: SW
- System Requirement State: Approved
- Primary Discipline: SW
- ASIL Rating: QM

#### TFDCX32348-27728: $F8 CXSWS1S02 - SWS_2_10 (System Interface)
- Verification Criteria: Verify by code review
- Verification Method: Code/Design Review
- Verification Owner: SW
- System Requirement State: Approved
- Primary Discipline: SW
- ASIL Rating: QM

#### TFDCX32348-27729: $F8 CXSWS1S02 - SWS_2_11 (System Interface)
- Verification Criteria: Verify by code review
- Verification Method: Code/Design Review
- Verification Owner: SW
- System Requirement State: Approved
- Primary Discipline: SW
- ASIL Rating: QM

#### TFDCX32348-27730: $F8 CXSWS1S02 - SWS_2_12 (System Interface)
- Verification Criteria: Verify by code review
- Verification Method: Code/Design Review
- Verification Owner: SW
- System Requirement State: Approved
- Primary Discipline: SW
- ASIL Rating: QM

#### TFDCX32348-27731: $F8 CXSWS1S02 - SWS_2_13 (System Interface)
- Verification Criteria: Verify by code review
- Verification Method: Code/Design Review
- Verification Owner: SW
- System Requirement State: Approved
- Primary Discipline: SW
- ASIL Rating: QM

#### TFDCX32348-27732: $F8 CXSWS1S02 - SWS_2_14 (System Interface)
- Verification Criteria: Verify by code review
- Verification Method: Code/Design Review
- Verification Owner: SW
- System Requirement State: Approved
- Primary Discipline: SW
- ASIL Rating: QM

#### TFDCX32348-27733: $F8 CXSWS1S02 - SWS_2_15 (System Interface)
- Verification Criteria: Verify by code review
- Verification Method: Code/Design Review
- Verification Owner: SW
- System Requirement State: Approved
- Primary Discipline: SW
- ASIL Rating: QM

#### TFDCX32348-27734: $F8 CXSWS1S02 - SWS_2_16 (System Interface)
- Verification Criteria: Verify by code review
- Verification Method: Code/Design Review
- Verification Owner: SW
- System Requirement State: Approved
- Primary Discipline: SW
- ASIL Rating: QM

#### TFDCX32348-27735: $F8 CXSWS1S02 - SWS_2_17 (System Interface)
- Verification Criteria: Verify by code review
- Verification Method: Code/Design Review
- Verification Owner: SW
- System Requirement State: Approved
- Primary Discipline: SW
- ASIL Rating: QM

#### TFDCX32348-27736: $F8 CXSWS1S02 - SWS_2_18 (System Interface)
- Verification Criteria: Verify by code review
- Verification Method: Code/Design Review
- Verification Owner: SW
- System Requirement State: Approved
- Primary Discipline: SW
- ASIL Rating: QM

#### TFDCX32348-27737: $F8 CXSWS1S02 - SWS_2_19 (System Interface)
- Verification Criteria: Verify by code review
- Verification Method: Code/Design Review
- Verification Owner: SW
- System Requirement State: Approved
- Primary Discipline: SW
- ASIL Rating: QM

#### TFDCX32348-27738: $F8 CXSWS1S02 - SWS_2_20 (System Interface)
- Verification Criteria: Verify by code review
- Verification Method: Code/Design Review
- Verification Owner: SW
- System Requirement State: Approved
- Primary Discipline: SW
- ASIL Rating: QM

#### TFDCX32348-27739: $F8 CXSWS1S02 - SWS_2_21 (System Interface)
- Verification Criteria: Verify by code review
- Verification Method: Code/Design Review
- Verification Owner: SW
- System Requirement State: Approved
- Primary Discipline: SW
- ASIL Rating: QM

#### TFDCX32348-27740: $F8 CXSWS1S02 - SWS_2_22 (System Interface)
- Verification Criteria: Verify by code review
- Verification Method: Code/Design Review
- Verification Owner: SW
- System Requirement State: Approved
- Primary Discipline: SW
- ASIL Rating: QM

#### TFDCX32348-27741: $F8 CXSWS1S02 - SWS_2_23 (System Interface)
- Verification Criteria: Verify by code review
- Verification Method: Code/Design Review
- Verification Owner: SW
- System Requirement State: Approved
- Primary Discipline: SW
- ASIL Rating: QM

#### TFDCX32348-27742: $F8 CXSWS1S02 - SWS_2_24 (System Interface)
- Verification Criteria: Verify by code review
- Verification Method: Code/Design Review
- Verification Owner: SW
- System Requirement State: Approved
- Primary Discipline: SW
- ASIL Rating: QM

#### TFDCX32348-27743: $F8 CXSWS1S02 - SWS_2_25 (System Interface)
- Verification Criteria: Verify by code review
- Verification Method: Code/Design Review
- Verification Owner: SW
- System Requirement State: Approved
- Primary Discipline: SW
- ASIL Rating: QM

#### TFDCX32348-27744: $F8 CXSWS1S02 - SWS_2_26 (System Interface)
- Verification Criteria: Verify by code review
- Verification Method: Code/Design Review
- Verification Owner: SW
- System Requirement State: Approved
- Primary Discipline: SW
- ASIL Rating: QM

#### TFDCX32348-27745: $F8 CXSWS1S02 - SWS_2_27 (System Interface)
- Verification Criteria: Verify by code review
- Verification Method: Code/Design Review
- Verification Owner: SW
- System Requirement State: Approved
- Primary Discipline: SW
- ASIL Rating: QM

#### TFDCX32348-27746: $F8 CXSWS1S02 - SWS_2_28 (System Interface)
- Verification Criteria: Verify by code review
- Verification Method: Code/Design Review
- Verification Owner: SW
- System Requirement State: Approved
- Primary Discipline: SW
- ASIL Rating: QM

#### TFDCX32348-27747: $F8 CXSWS1S02 - SWS_2_29 (System Interface)
- Verification Criteria: Verify by code review
- Verification Method: Code/Design Review
- Verification Owner: SW
- System Requirement State: Approved
- Primary Discipline: SW
- ASIL Rating: QM

#### TFDCX32348-27748: $F8 CXSWS1S02 - SWS_2_30 (System Interface)
- Verification Criteria: Verify by code review
- Verification Method: Code/Design Review
- Verification Owner: SW
- System Requirement State: Approved
- Primary Discipline: SW
- ASIL Rating: QM

#### TFDCX32348-27749: $F8 CXSWS1S02 - SWS_2_31 (System Interface)
- Verification Criteria: Verify by code review
- Verification Method: Code/Design Review
- Verification Owner: SW
- System Requirement State: Approved
- Primary Discipline: SW
- ASIL Rating: QM

#### TFDCX32348-27750: $F8 CXSWS1S02 - SWS_2_32 (System Interface)
- Verification Criteria: Verify by code review
- Verification Method: Code/Design Review
- Verification Owner: SW
- System Requirement State: Approved
- Primary Discipline: SW
- ASIL Rating: QM

#### TFDCX32348-27751: $F8 CXSWS1S02 - SWS_2_33 (System Interface)
- Verification Criteria: Verify by code review
- Verification Method: Code/Design Review
- Verification Owner: SW
- System Requirement State: Approved
- Primary Discipline: SW
- ASIL Rating: QM

#### TFDCX32348-27752: $F8 CXSWS1S02 - SWS_2_34 (System Interface)
- Verification Criteria: Verify by code review
- Verification Method: Code/Design Review
- Verification Owner: SW
- System Requirement State: Approved
- Primary Discipline: SW
- ASIL Rating: QM

#### TFDCX32348-27753: $F8 CXSWS1S02 - SWS_2_35 (System Interface)
- Verification Criteria: Verify by code review
- Verification Method: Code/Design Review
- Verification Owner: SW
- System Requirement State: Approved
- Primary Discipline: SW
- ASIL Rating: QM

#### TFDCX32348-27754: $F8 CXSWS1S02 - SWS_2_36 (System Interface)
- Verification Criteria: Verify by code review
- Verification Method: Code/Design Review
- Verification Owner: SW
- System Requirement State: Approved
- Primary Discipline: SW
- ASIL Rating: QM

#### TFDCX32348-27755: $F8 CXSWS1S02 - SWS_2_37 (System Interface)
- Verification Criteria: Verify by code review
- Verification Method: Code/Design Review
- Verification Owner: SW
- System Requirement State: Approved
- Primary Discipline: SW
- ASIL Rating: QM

#### TFDCX32348-27756: $F8 CXSWS1S02 - SWS_2_38 (System Interface)
- Verification Criteria: Verify by code review
- Verification Method: Code/Design Review
- Verification Owner: SW
- System Requirement State: Approved
- Primary Discipline: SW
- ASIL Rating: QM

#### TFDCX32348-27757: $F8 CXSWS1S02 - SWS_2_39 (System Interface)
- Verification Criteria: Verify by code review
- Verification Method: Code/Design Review
- Verification Owner: SW
- System Requirement State: Approved
- Primary Discipline: SW
- ASIL Rating: QM

#### TFDCX32348-27758: $F8 CXSWS1S02 - SWS_2_40 (System Interface)
- Verification Criteria: Verify by code review
- Verification Method: Code/Design Review
- Verification Owner: SW
- System Requirement State: Approved
- Primary Discipline: SW
- ASIL Rating: QM

#### TFDCX32348-27759: $F8 CXSWS1S02 - SWS_2_41 (System Interface)
- Verification Criteria: Verify by code review
- Verification Method: Code/Design Review
- Verification Owner: SW
- System Requirement State: Approved
- Primary Discipline: SW
- ASIL Rating: QM

#### TFDCX32348-27760: $F8 CXSWS1S02 - SWS_2_42 (System Interface)
- Verification Criteria: Verify by code review
- Verification Method: Code/Design Review
- Verification Owner: SW
- System Requirement State: Approved
- Primary Discipline: SW
- ASIL Rating: QM

#### TFDCX32348-27761: $F8 CXSWS1S02 - SWS_2_43 (System Interface)
- Verification Criteria: Verify by code review
- Verification Method: Code/Design Review
- Verification Owner: SW
- System Requirement State: Approved
- Primary Discipline: SW
- ASIL Rating: QM

#### TFDCX32348-27762: $F8 CXSWS1S02 - SWS_2_44 (System Interface)
- Verification Criteria: Verify by code review
- Verification Method: Code/Design Review
- Verification Owner: SW
- System Requirement State: Approved
- Primary Discipline: SW
- ASIL Rating: QM

#### TFDCX32348-27763: $F8 CXSWS1S02 - SWS_2_45 (System Interface)
- Verification Criteria: Verify by code review
- Verification Method: Code/Design Review
- Verification Owner: SW
- System Requirement State: Approved
- Primary Discipline: SW
- ASIL Rating: QM

#### TFDCX32348-27764: $F8 CXSWS1S02 - SWS_2_46 (System Interface)
- Verification Criteria: Verify by code review
- Verification Method: Code/Design Review
- Verification Owner: SW
- System Requirement State: Approved
- Primary Discipline: SW
- ASIL Rating: QM

#### TFDCX32348-27765: $F8 CXSWS1S02 - SWS_2_47 (System Interface)
- Verification Criteria: Verify by code review
- Verification Method: Code/Design Review
- Verification Owner: SW
- System Requirement State: Approved
- Primary Discipline: SW
- ASIL Rating: QM

#### TFDCX32348-27766: $F8 CXSWS1S02 - SWS_2_48 (System Interface)
- Verification Criteria: Verify by code review
- Verification Method: Code/Design Review
- Verification Owner: SW
- System Requirement State: Approved
- Primary Discipline: SW
- ASIL Rating: QM

#### TFDCX32348-27767: $F8 CXSWS1S02 - SWS_2_49 (System Interface)
- Verification Criteria: Verify by code review
- Verification Method: Code/Design Review
- Verification Owner: SW
- System Requirement State: Approved
- Primary Discipline: SW
- ASIL Rating: QM

#### TFDCX32348-27768: $F8 CXSWS1S02 - SWS_2_50 (System Interface)
- Verification Criteria: Verify by code review
- Verification Method: Code/Design Review
- Verification Owner: SW
- System Requirement State: Approved
- Primary Discipline: SW
- ASIL Rating: QM

#### TFDCX32348-27769: $F8 CXSWS1S02 - SWS_2_51 (System Interface)
- Verification Criteria: Verify by code review
- Verification Method: Code/Design Review
- Verification Owner: SW
- System Requirement State: Approved
- Primary Discipline: SW
- ASIL Rating: QM

#### TFDCX32348-27770: $F8 CXSWS1S02 - SWS_2_52 (System Interface)
- Verification Criteria: Verify by code review
- Verification Method: Code/Design Review
- Verification Owner: SW
- System Requirement State: Approved
- Primary Discipline: SW
- ASIL Rating: QM

#### TFDCX32348-27771: $F8 CXSWS1S02 - SWS_2_53 (System Interface)
- Verification Criteria: Verify by code review
- Verification Method: Code/Design Review
- Verification Owner: SW
- System Requirement State: Approved
- Primary Discipline: SW
- ASIL Rating: QM

#### TFDCX32348-27772: $F8 CXSWS1S02 - SWS_2_54 (System Interface)
- Verification Criteria: Verify by code review
- Verification Method: Code/Design Review
- Verification Owner: SW
- System Requirement State: Approved
- Primary Discipline: SW
- ASIL Rating: QM

#### TFDCX32348-27773: $F8 CXSWS1S02 - SWS_2_55 (System Interface)
- Verification Criteria: Verify by code review
- Verification Method: Code/Design Review
- Verification Owner: SW
- System Requirement State: Approved
- Primary Discipline: SW
- ASIL Rating: QM

#### TFDCX32348-27774: $F8 CXSWS1S02 - SWS_2_56 (System Interface)
- Verification Criteria: Verify by code review
- Verification Method: Code/Design Review
- Verification Owner: SW
- System Requirement State: Approved
- Primary Discipline: SW
- ASIL Rating: QM

#### TFDCX32348-27775: $F8 CXSWS1S02 - SWS_2_57 (System Interface)
- Verification Criteria: Verify by code review
- Verification Method: Code/Design Review
- Verification Owner: SW
- System Requirement State: Approved
- Primary Discipline: SW
- ASIL Rating: QM

## TFDCX32348-9439: CXPI Tx signals (Heading)

### TFDCX32348-12118: PID $7C CXMET1S01 (System Interface)
- Verification Criteria: Verify by code review
- Verification Method: Code/Design Review
- Verification Owner: SW
- System Requirement State: Approved
- Primary Discipline: SW
- ASIL Rating: QM

#### TFDCX32348-17052: $7C CXMET1S01 - RHEOSTAT (System Interface)
- Verification Criteria: Verify by code review
- Verification Method: Code/Design Review
- Verification Owner: SW
- System Requirement State: Approved
- Primary Discipline: SW
- ASIL Rating: QM

#### TFDCX32348-72802: $7C CXMET1S01 - METEER (System Interface)
$7C CXMET1S01 - METEER
Description : Error status output used for CXPI communication evaluation.
Length : 1 bit
Range : 0 (Normal), 1 (Error)
- Verification Criteria: Verify by code review
- Verification Method: Code/Design Review
- Verification Owner: SW
- System Requirement State: Approved
- Primary Discipline: SW
- ASIL Rating: QM

#### TFDCX32348-27777: $7C CXMET1S01 - SW_LIGHT (System Interface)
$7C CXMET1S01 - SW_LIGHT
Description : Steering SW illumination ON request.
Type : 2 bit
Range : 00b (No request), 01b (Illumination ON), 10b (Not used), 11b (Not used)
- Verification Criteria: Verify by code review
- Verification Method: Code/Design Review
- Verification Owner: SW
- System Requirement State: Approved
- Primary Discipline: SW
- ASIL Rating: QM

### TFDCX32348-12120: PID $4C CXMET1S02 (System Interface)
- Verification Criteria: Verify by code review
- Verification Method: Code/Design Review
- Verification Owner: SW
- System Requirement State: Approved
- Primary Discipline: SW
- ASIL Rating: QM

#### TFDCX32348-27778: $4C CXMET1S02 - RRTT (System Interface)
- Verification Criteria: Verify by code review
- Verification Method: Code/Design Review
- Verification Owner: SW
- System Requirement State: Approved
- Primary Discipline: SW
- ASIL Rating: QM

#### TFDCX32348-27779: $4C CXMET1S02 - RCTT (System Interface)
- Verification Criteria: Verify by code review
- Verification Method: Code/Design Review
- Verification Owner: SW
- System Requirement State: Approved
- Primary Discipline: SW
- ASIL Rating: QM

#### TFDCX32348-27780: $4C CXMET1S02 - RLTT (System Interface)
- Verification Criteria: Verify by code review
- Verification Method: Code/Design Review
- Verification Owner: SW
- System Requirement State: Approved
- Primary Discipline: SW
- ASIL Rating: QM

#### TFDCX32348-27781: $4C CXMET1S02 - RR2TT (System Interface)
- Verification Criteria: Verify by code review
- Verification Method: Code/Design Review
- Verification Owner: SW
- System Requirement State: Approved
- Primary Discipline: SW
- ASIL Rating: QM

#### TFDCX32348-27782: $4C CXMET1S02 - RC2TT (System Interface)
- Verification Criteria: Verify by code review
- Verification Method: Code/Design Review
- Verification Owner: SW
- System Requirement State: Approved
- Primary Discipline: SW
- ASIL Rating: QM

#### TFDCX32348-27783: $4C CXMET1S02 - RL2TT (System Interface)
- Verification Criteria: Verify by code review
- Verification Method: Code/Design Review
- Verification Owner: SW
- System Requirement State: Approved
- Primary Discipline: SW
- ASIL Rating: QM

#### TFDCX32348-27784: $4C CXMET1S02 - RR3TT (System Interface)
- Verification Criteria: Verify by code review
- Verification Method: Code/Design Review
- Verification Owner: SW
- System Requirement State: Approved
- Primary Discipline: SW
- ASIL Rating: QM

#### TFDCX32348-27785: $4C CXMET1S02 - RC3TT (System Interface)
- Verification Criteria: Verify by code review
- Verification Method: Code/Design Review
- Verification Owner: SW
- System Requirement State: Approved
- Primary Discipline: SW
- ASIL Rating: QM

#### TFDCX32348-27786: $4C CXMET1S02 - RL3TT (System Interface)
- Verification Criteria: Verify by code review
- Verification Method: Code/Design Review
- Verification Owner: SW
- System Requirement State: Approved
- Primary Discipline: SW
- ASIL Rating: QM

#### TFDCX32348-27787: $4C CXMET1S02 - REARINDI (System Interface)
- Verification Criteria: Verify by code review
- Verification Method: Code/Design Review
- Verification Owner: SW
- System Requirement State: Approved
- Primary Discipline: SW
- ASIL Rating: QM

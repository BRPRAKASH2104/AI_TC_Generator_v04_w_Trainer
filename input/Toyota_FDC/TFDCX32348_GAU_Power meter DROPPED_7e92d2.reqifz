# Json2ReqIF Transformation

# Specification: GAU_Power meter <DROPPED>
- JDA Snapshot Date: 2025-09-04 02:42:04

## TFDCX32348-32634: GAU_Power meter <DROPPED> (Heading)

## TFDCX32348-32635: History (Heading)

### TFDCX32348-32636: Table (Information)
| Version | Date | Name | Description of change | Baseline |
| --- | --- | --- | --- | --- |
| 0.1 | Jul/11/2024 | Hiromune Wachi | Due to POIL#88, specifications for "EV" and "FCV" are not applicable for 12.3InchFDC. Therefore, this SRD has been dropped. Newly create for 12.3inch FDC. [SYS-Story] : TFDCX32348-28130: [SYS][12.3FDC][APP][Gauges] Power meter display (with output/regenerative limit display) |  |

## TFDCX32348-32637: Reference Document (Heading)

### TFDCX32348-32638: External Sources (Heading)

#### TFDCX32348-32639: MET-H_PWRMET-CSTD-A0-03-A-C0 (Information)
MET-H_PWRMET-CSTD-A0-03-A-C0
MET-H_PWRMET-CSTD-A0-03-A-C0_Appendix

## TFDCX32348-32640: Overview (Heading)

### TFDCX32348-32641: This SRD defines the requirements for Power meter. (Information)

## TFDCX32348-32642: Input Requirements (Heading)

### TFDCX32348-32647: InternalSignal – IgnMode (System Interface)
- System Requirement State: Rejected

### TFDCX32348-32648: InternalSignal - PTSysTypeFlag (System Interface)
- System Requirement State: Rejected

### TFDCX32348-32649: CANSignal - PMEVCR (System Interface)
- System Requirement State: Rejected

### TFDCX32348-32650: CANSignal - PMPWRTH (System Interface)
- System Requirement State: Rejected

### TFDCX32348-32651: CANSignal - PMPWRHL (System Interface)
- System Requirement State: Rejected

### TFDCX32348-32652: CANSignal - PMCHGTH (System Interface)
- System Requirement State: Rejected

### TFDCX32348-32653: CANSignal - PMCHGHL (System Interface)
- System Requirement State: Rejected

### TFDCX32348-33257: CANSignal - IECOHV_PMEV_CR (System Interface)
- System Requirement State: Rejected

### TFDCX32348-33258: CANSignal - EHV1F04_BYTE3_4 (System Interface)
- System Requirement State: Rejected

## TFDCX32348-32643: Output Requirements (Heading)

### TFDCX32348-32663: HMI - HMI_Power_Level (System Interface)
HMI - HMI_Power_Level
(Range : “Blank“, "ReadyOff", -100[-100%], -99[-99%], …, -1[-1%], 0[0%], 1[1%], …, 510[510%], 511[511%])
- System Requirement State: Rejected

### TFDCX32348-32749: HMI - HMI_PWR_MARK (System Interface)
HMI - HMI_PWR_MARK
(Range : 0[Off(Gray-out)], 1[PWR-on], 2[ECO-on])
Note : “2[CHG-on]” is planned to be used for FCV, but currently it is not applicable to FCV, so it will not be used.
- System Requirement State: Rejected

### TFDCX32348-32751: HMI - HMI_CHG_MARK (System Interface)
HMI - HMI_CHG_MARK
(Range : 0[Off(Gray-out)], 1[CHG-on])
- System Requirement State: Rejected

### TFDCX32348-32664: HMI - HMI_Limit_Output (System Interface)
HMI - HMI_Limit_Output
(Range : 0[None], 1[1%], 2[2%] ..., 510[510%], 511[511%])
- System Requirement State: Rejected

### TFDCX32348-32665: HMI - HMI_Limit_Output_Highlight (System Interface)
HMI - HMI_Limit_Output_Highlight
(Range : 0[Off], 1[On])
- System Requirement State: Rejected

### TFDCX32348-32666: HMI - HMI_Limit_Regenerative (System Interface)
HMI - HMI_Limit_Regenerative
(Range : 0[None], 1[-1%], 2[-2%], ..., 99[-99%], 100[-100%])
- System Requirement State: Rejected

### TFDCX32348-32667: HMI - HMI_Limit_Regenerative_Highlight (System Interface)
HMI - HMI_Limit_Regenerative_Highlight
(Range : 0[Off], 1[On])
- System Requirement State: Rejected

## TFDCX32348-32644: Performance Requirements (Heading)

### TFDCX32348-32756: General (Heading)

#### TFDCX32348-32757: Processing block structure (Heading)

##### TFDCX32348-32758: Figure (System Requirement)
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- System Requirement State: Rejected

##### TFDCX32348-32759: Table (System Requirement)
| # | Signal name | Range |
| --- | --- | --- |
| ①-1 | SampleBuffer[【N】] | -100, -99, …, -1, 0, 1, …, 510, 511 |
| ①-2 | BufferIndex | 0, 1, …, “【N】-1” |
| ①-3 | BufferFullFlag | 0[Off], 1[On] |
| ①-4 | ReadyOffFlag | 0[Off], 1[On] |
| ② | CANMesJudgeFlag | 0[Invalid], 1[$247 Valid], 2[$0D9 Valid] |
| ③ | PowerAverageLevel | "ReadyOff", -100, -99, …, -1, 0, 1, …, 510, 511 |
- System Requirement State: Rejected

#### TFDCX32348-32767: Parameters (Heading)

##### TFDCX32348-32768: Table (System Requirement)
| # | Parameter name | Value | Remarks |
| --- | --- | --- | --- |
| 1 | 【N】 | 32 | PMEVCR moving average count |
- System Requirement State: Rejected

### TFDCX32348-32778: Process (Heading)

#### TFDCX32348-32779: [A] Initialization (Heading)

##### TFDCX32348-32789: Table (System Requirement)
| # | Name | Initilize @ Battery Connect / Cold Reset | Initialize @ Module Wake-Up | IgnMode change from 1[Off] to 1[ON] | Init Value | Remark |
| --- | --- | --- | --- | --- | --- | --- |
| 1 | HMI_Power_Level | 〇 | 〇 | 〇 | "ReadyOff" |  |
| 2 | HMI_PWR_MARK | 〇 | 〇 | 〇 | 0[Off(Gray-out)] |  |
| 3 | HMI_CHG_MARK | 〇 | 〇 | 〇 | 0[Off(Gray-out)] |  |
| 4 | HMI_Limit_Output | 〇 | 〇 | 〇 | 0[None] |  |
| 5 | HMI_Limit_Output_Highlight | 〇 | 〇 | 〇 | 0[Off] |  |
| 6 | HMI_Limit_Regenerative | 〇 | 〇 | 〇 | 0[None] |  |
| 7 | HMI_Limit_Regenerative_Highlight | 〇 | 〇 | 〇 | 0[Off] |  |
| 8 | SampleBuffer[] | 〇 | 〇 | 〇 | Set all data to 0[0%] |  |
| 9 | BufferIndex | 〇 | 〇 | 〇 | 0 |  |
| 10 | BufferFullFlag | 〇 | 〇 | 〇 | 0[Off] |  |
| 11 | ReadyOffFlag | 〇 | 〇 | 〇 | 1[On] |  |
| 12 | CANMesJudgeFlag | 〇 | 〇 | 〇 | 0[Invalid] |  |
| 13 | PowerAverageLevel | 〇 | 〇 | 〇 | "ReadyOff" |  |
| 14 | PMEVCR_In | 〇 | 〇 | 〇 | 0 | Used by “[C] Sampling process“ |
| 15 | PMPWRTH_247 | 〇 | 〇 | 〇 | 000h | Used by “[F] Power limit process“ |
| 16 | PMCHGTH_247 | 〇 | 〇 | 〇 | 00h | Used by “[G] Regeneration limit process“ |
- System Requirement State: Rejected

#### TFDCX32348-32781: [B] GAU_Power functional presence/absence determination (Heading)

##### TFDCX32348-32893: Table (System Requirement)
| # | Input |  | Output |
| --- | --- | --- | --- |
| # | InternalSignal - PTSysTypeFlag | Meaning | Power meter applicability |
| 1 | 0101b | EV | 1[Applicable] |
| 2 | 0111b | FCV | 1[Applicable] |
| 7 | Other than above | Other (Conv, HV, etc) | 0[Not applicable] |
Note (Below is what is written in Toyota specification [MET-H_PWRMET-CSTD-A0-03-A-C0.xlsm] ) :
- Power Indicator(power limit, system power output) shall be displayed at all times.
To meet the following requirements
･ laws and regulations of China GB/T18384.2-2015 [4.3.1 Low output indication]
･ laws and regulations of China GB/T19836-2019 [4.3.2 Instantaneous power of braking energy regeneration system]
When "Power meter applicability" is "Not applicable", set “Blank” as HMI_Power_Level and do not perform the processing after this chapter.
- System Requirement State: Rejected

#### TFDCX32348-32782: [C] Sampling process (Heading)

##### TFDCX32348-32819: Table - Sampling (System Requirement)
| # | Input |  |  |  |  |  | Output |  |  |  |  |  |
| --- | --- | --- | --- | --- | --- | --- | --- | --- | --- | --- | --- | --- |
| # | IgnMode | CAN Signal Communication Status - PMEVCR | CANSignal - PMEVCR | CAN Signal Communication Status - IECOHV_PMEV_CR | CANSignal - IECOHV_PMEV_CR | BufferIndex | PMEVCR_In | SampleBuffer[BufferIndex] | BufferIndex [*1] | BufferFullFlag | ReadyOffFlag | CANMesJudgeFlag |
| 1 | 1[Off] | X | X |  |  | X | No change (Initialization is performed with "[A] initialization".) |  |  |  |  | 0[Invalid] |
| 2 | 1[On] | Communication starting ”Never Received: 1” OR ”Communication Failure: 1” | X | Communication starting ”Never Received: 1” OR ”Communication Failure: 1” | X | X | No change | No change | No change | No change | 1[On] | 0[Invalid] |
| 3 | 1[On] | Communication starting ”Never Received: 1” OR ”Communication Failure: 1” | X | Communication establishment Never Received: 0 Communication Failure: 0 | 201h | X | 0 | No change | No change | No change | 1[On] | 1[$247 Valid] |
| 4 | 1[On] | Communication starting ”Never Received: 1” OR ”Communication Failure: 1” | X | Communication establishment Never Received: 0 Communication Failure: 0 | 200h or 202h to 39Bh | BufferIndex < “【N】-1” | 0 | Store PMEVCR_In value | increment by 1 | No change | 0[Off] | 1[$247 Valid] |
| 5 | 1[On] | Communication starting ”Never Received: 1” OR ”Communication Failure: 1” | X | Communication establishment Never Received: 0 Communication Failure: 0 | 200h or 202h to 39Bh | 【N】-1 | 0 | Store PMEVCR_In value | 0 | 1[On] | 0[Off] | 1[$247 Valid] |
| 6 | 1[On] | Communication starting ”Never Received: 1” OR ”Communication Failure: 1” | X | Communication establishment Never Received: 0 Communication Failure: 0 | 39Ch[-100%] to 3FFh[-1%] | BufferIndex < “【N】-1” | -100 to -1 | Store PMEVCR_In value | increment by 1 | No change | 0[Off] | 1[$247 Valid] |
| 7 | 1[On] | Communication starting ”Never Received: 1” OR ”Communication Failure: 1” | X | Communication establishment Never Received: 0 Communication Failure: 0 | 39Ch[-100%] to 3FFh[-1%] | 【N】-1 | -100 to -1 | Store PMEVCR_In value | 0 | 1[On] | 0[Off] | 1[$247 Valid] |
| 8 | 1[On] | Communication starting ”Never Received: 1” OR ”Communication Failure: 1” | X | Communication establishment Never Received: 0 Communication Failure: 0 | 0h[0%] to 1FFh[511%] | BufferIndex < “【N】-1” | 0 to 511 | Store PMEVCR_In value | increment by 1 | No change | 0[Off] | 1[$247 Valid] |
| 9 | 1[On] | Communication starting ”Never Received: 1” OR ”Communication Failure: 1” | X | Communication establishment Never Received: 0 Communication Failure: 0 | 0h[0%] to 1FFh[511%] | 【N】-1 | 0 to 511 | Store PMEVCR_In value | 0 | 1[On] | 0[Off] | 1[$247 Valid] |
| 10 | 1[On] | Communication establishment Never Received: 0 Communication Failure: 0 | 201h | X | X | X | 0 | No change | No change | No change | 1[On] | 2[$0D9 Valid] |
| 11 | 1[On] | Communication establishment Never Received: 0 Communication Failure: 0 | 200h or 202h to 39Bh | X | X | BufferIndex < “【N】-1” | 0 | Store PMEVCR_In value | increment by 1 | No change | 0[Off] | 2[$0D9 Valid] |
| 12 | 1[On] | Communication establishment Never Received: 0 Communication Failure: 0 | 200h or 202h to 39Bh | X | X | 【N】-1 | 0 | Store PMEVCR_In value | 0 | 1[On] | 0[Off] | 2[$0D9 Valid] |
| 13 | 1[On] | Communication establishment Never Received: 0 Communication Failure: 0 | 39Ch[-100%] to 3FFh[-1%] | X | X | BufferIndex < “【N】-1” | -100 to -1 | Store PMEVCR_In value | increment by 1 | No change | 0[Off] | 2[$0D9 Valid] |
| 14 | 1[On] | Communication establishment Never Received: 0 Communication Failure: 0 | 39Ch[-100%] to 3FFh[-1%] | X | X | 【N】-1 | -100 to -1 | Store PMEVCR_In value | 0 | 1[On] | 0[Off] | 2[$0D9 Valid] |
| 15 | 1[On] | Communication establishment Never Received: 0 Communication Failure: 0 | 0h[0%] to 1FFh[511%] | X | X | BufferIndex < “【N】-1” | 0 to 511 | Store PMEVCR_In value | increment by 1 | No change | 0[Off] | 2[$0D9 Valid] |
| 16 | 1[On] | Communication establishment Never Received: 0 Communication Failure: 0 | 0h[0%] to 1FFh[511%] | X | X | 【N】-1 | 0 to 511 | Store PMEVCR_In value | 0 | 1[On] | 0[Off] | 2[$0D9 Valid] |
X : Don’t care.
[*1] : Update BufferIndex after updating SampleBuffer.
- System Requirement State: Rejected

#### TFDCX32348-32784: [D] Averaging process (Heading)

##### TFDCX32348-32897: Table (System Requirement)
| # | Input |  |  | Output |
| --- | --- | --- | --- | --- |
| # | IgnMode | ReadyOffFlag | BufferFullFlag | PowerAverageLevel |
| 1 | Off | x | X | No change (Initialization is performed with "[A] initialization".) |
| 2 | On | 1[On] | X | "ReadyOff" |
| 3 | On | 0[Off] | 1[On] | Round("Average of all data in SampleBuffer", 0) |
| 4 | On | 0[Off] | 0[Off] | Round("Average data from 0th data to “BufferIndex-1“ data in SampleBuffer", 0) |
- System Requirement State: Rejected

#### TFDCX32348-32785: [E] Power meter level process (Heading)

##### TFDCX32348-32939: Table (System Requirement)
| # | Input |  |  | Output |  |  |
| --- | --- | --- | --- | --- | --- | --- |
| # | IgnMode | PTSysTypeFlag | PowerAverageLevel | HMI_Power_Level | HMI_PWR_MARK | HMI_CHG_MARK |
| 1 | Off | X | X | No change (Initialization is performed with "[A] initialization".) |  |  |
| 2 | On | 0101b[EV] | "ReadyOff" | "ReadyOff" | 0[Off(Gray-out)] | 0[Off(Gray-out)] |
| 3 | On | 0101b[EV] | 0 <= PowerAverageLevel <= 511 | PowerAverageLevel | 1[PWR-on] | 0[Off(Gray-out)] |
| 4 | On | 0101b[EV] | 0 > PowerAverageLevel >= -100 | PowerAverageLevel | 0[Off(Gray-out)] | 1[CHG-on] |
| 5 | On | 0111b[FCV] | "ReadyOff" | PowerAverageLevel | 0[Off(Gray-out)] | 0[Off(Gray-out)] |
| 6 | On | 0111b[FCV] | 0 <= PowerAverageLevel <= 100 | PowerAverageLevel | 2[ECO-on] | 0[Off(Gray-out)] |
| 7 | On | 0111b[FCV] | 100 < PowerAverageLevel <= 511 | PowerAverageLevel | 1[PWR-on] | 0[Off(Gray-out)] |
| 8 | On | 0111b[FCV] | 0 > PowerAverageLevel >= -100 | PowerAverageLevel | 0[Off(Gray-out)] | 1[CHG-on] |
X : Don’t care.
- System Requirement State: Rejected

#### TFDCX32348-32787: [F] Power limit process (Heading)

##### TFDCX32348-33324: The case of "CANMesJudgeFlag = 2[$0D9 Valid]": (Heading)

###### TFDCX32348-32940 (System Requirement)
If "CANMesJudgeFlag = 2[$0D9 Valid]", the cluster shall control according to the table below.
| # | Input |  |  |  | Output |  |
| --- | --- | --- | --- | --- | --- | --- |
| # | IgnMode | PowerAverageLevel | CANSignal - PMPWRTH | CANSignal - PMPWRHL | HMI_Limit_Output | HMI_Limit_Output_Highlight |
| 1 | Off | X | X | X | No change (Initialization is performed with "[A] initialization".) |  |
| 2 | On | "ReadyOff" | X | X | 0[None] | 0[Off] |
| 3 | On | Other than “ReadyOff“ | 000h | X | 0[None] | 0[Off] |
| 4 | On | Other than “ReadyOff“ | 001h to 1FFh | 0b | PMPWRTH (1[1%] to 511[511%]) | 0[Off] |
| 5 | On | Other than “ReadyOff“ | 001h to 1FFh | 1b | PMPWRTH (1[1%] to 511[511%]) | 1[On] |
X : Don’t care.
- System Requirement State: Rejected

##### TFDCX32348-33326: The case of "CANMesJudgeFlag = other than 2[$0D9 Valid]": (Heading)

###### TFDCX32348-33329 (System Requirement)
If "CANMesJudgeFlag = other than 2[$0D9 Valid]", the cluster shall control according to the 2 step below.
<Spep1>
PMPWRTH_247 = (“CANSignal - EHV1F04_BYTE3_4” & 0xFF80) >> 7
<Spep2>
| # | Input |  |  |  | Output |  |
| --- | --- | --- | --- | --- | --- | --- |
| # | IgnMode | PowerAverageLevel | CANMesJudgeFlag | PMPWRTH_247 | HMI_Limit_Output | HMI_Limit_Output_Highlight |
| 1 | Off | X | X | X | No change (Initialization is performed with "[A] initialization".) |  |
| 2 | On | "ReadyOff" | X | X | 0[None] | 0[Off] |
| 3 | On | Other than “ReadyOff“ | 0[Invalid] | X | 0[None] | 0[Off] |
| 4 | On | Other than “ReadyOff“ | Other than “0[Invalid]“ | 000h | 0[None] | 0[Off] |
| 5 | On | Other than “ReadyOff“ | Other than “0[Invalid]“ | 001h to 1FFh | PMPWRTH_247 (1[1%] to 511[511%]) | 0[Off] |
X : Don’t care.
- System Requirement State: Rejected

#### TFDCX32348-32788: [G] Regeneration limit process (Heading)

##### TFDCX32348-33338: The case of "CANMesJudgeFlag = 2[$0D9 Valid]": (Heading)

###### TFDCX32348-33341 (System Requirement)
If "CANMesJudgeFlag = 2[$0D9 Valid]", the cluster shall control according to the table below.
| # | Input |  |  |  | Output |  |
| --- | --- | --- | --- | --- | --- | --- |
| # | IgnMode | PowerAverageLevel | CANSignal - PMCHGTH | CANSignal - PMCHGHL | HMI_Limit_Regenerative | HMI_Limit_Regenerative_Highlight |
| 1 | Off | X | X | X | No change (Initialization is performed with "[A] initialization".) |  |
| 2 | On | "ReadyOff" | X | X | 0[None] | 0[Off] |
| 3 | On | Other than “ReadyOff“ | 00h or 65h to 7Fh | X | 0[None] | 0[Off] |
| 4 | On | Other than “ReadyOff“ | 01h to 64h | 0b | CANSignal - PMCHGTH (1[-1%] to 100[-100%]) | 0[Off] |
| 5 | On | Other than “ReadyOff“ | 01h to 64h | 1b | CANSignal - PMCHGTH (1[-1%] to 100[-100%]) | 1[On] |
X : Don’t care.
- System Requirement State: Rejected

##### TFDCX32348-33340: The case of "CANMesJudgeFlag = other than 2[$0D9 Valid]": (Heading)

###### TFDCX32348-32941 (System Requirement)
If "CANMesJudgeFlag = other than 2[$0D9 Valid]", the cluster shall control according to the 2 step below.
<Spep1>
PMCHGTH_247 = (“CAN Signal - EHV1F04_BYTE3_4” & 0x007F)
<Spep2>
| # | Input |  |  |  | Output |  |
| --- | --- | --- | --- | --- | --- | --- |
| # | IgnMode | PowerAverageLevel | CANMesJudgeFlag | PMCHGTH_247 | HMI_Limit_Regenerative | HMI_Limit_Regenerative_Highlight |
| 1 | Off | X | X | X | No change (Initialization is performed with "[A] initialization".) |  |
| 2 | On | "ReadyOff" | X | X | 0[None] | 0[Off] |
| 3 | On | Other than “ReadyOff“ | 0[Invalid] | X | 0[None] | 0[Off] |
| 4 | On | Other than “ReadyOff“ | Other than “0[Invalid]“ | 00h or 65h to 7Fh | 0[None] | 0[Off] |
| 5 | On | Other than “ReadyOff“ | Other than “0[Invalid]“ | 01h to 64h | PMCHGTH_247 (1[-1%] to 100[-100%]) | 0[Off] |
X : Don’t care.
- System Requirement State: Rejected

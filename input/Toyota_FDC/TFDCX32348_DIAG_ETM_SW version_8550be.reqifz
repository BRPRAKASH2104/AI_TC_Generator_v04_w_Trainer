# Json2ReqIF Transformation

# Specification: DIAG_ETM_SW version
- JDA Snapshot Date: 2025-09-04 02:39:55

## TFDCX32348-10589: ETM_SW version (Heading)
- System Requirement State: Draft
- Primary Discipline: TBD
- ASIL Rating: TBD

## TFDCX32348-10591: History (Heading)
- System Requirement State: Draft
- Primary Discipline: TBD
- ASIL Rating: TBD

### TFDCX32348-12296: Version... (Information)
| Version | Date | Name | Description of change | SRD Baseline |
| --- | --- | --- | --- | --- |
| 0.1 | 2024/4/9 | Takeshi Yamane | New created TFDCX32348-23231 [SYS][12.3FDC][APP] ETM | BL_20240521_01 |
| 0.2 | 2024/10/01 | Mathieu Lenoble | Update of switch input to navigate into the ETM panel TFDCX32348-41765: [SYS][12.3FDC][APP][ETM] Update of the steps to enter in ETM | BL_20241018_01 |
| 0.3 | 2025/02/28 | Mathieu Lenoble | TFDCX32348-74557: [SYS][12.3FDC][APP][ETM] Addition of SW version and DTC Update of the whole section under : - TFDCX32348-10599: Performance Requirements - TFDCX32348-12300: NVM | BL_20250328 |
| 0.4 | 2025/06/16 | Baviskar Tejaswini | Added NVM_SoftwarePartNumber_LB7. [TFDCX32348-92966] [SYS][12.3FDC][OIL][APP][ETM][Diagnostics] Update Logical blocks for ETM and Data Identifier SRD - Jira | BL_20250624_01 |
- System Requirement State: Draft
- Primary Discipline: TBD
- ASIL Rating: TBD

## TFDCX32348-10593: Overview (Heading)
- System Requirement State: Draft
- Primary Discipline: TBD
- ASIL Rating: TBD

### TFDCX32348-12298: This SRD defines the requirement for ... (Information)
This SRD defines the requirement for SW version screen of ETM, within this screen the different software part numbers for both Toyota and Visteon will be shown. This functional is executed in ETM mode only.
- System Requirement State: Draft
- Primary Discipline: TBD
- ASIL Rating: TBD

## TFDCX32348-10595: Input Requirements (Heading)
- System Requirement State: Draft
- Primary Discipline: TBD
- ASIL Rating: TBD

### TFDCX32348-42891: Switch Input (Heading)
- System Requirement State: Draft
- Primary Discipline: TBD
- ASIL Rating: TBD

#### TFDCX32348-42892: H/W DI - ODO_TripKnobInput (System Interface)
- System Requirement State: Draft
- Primary Discipline: TBD
- ASIL Rating: TBD

### TFDCX32348-12300: NVM (Heading)
- System Requirement State: Draft
- Primary Discipline: TBD
- ASIL Rating: TBD

#### TFDCX32348-17185: NVM - Software version for BOOT (System Requirement)
- Verification Criteria: Verify by design review
- Verification Method: TBD
- Verification Owner: SW
- System Requirement State: Approved
- Secondary Disciplines: TBD
- Primary Discipline: SW
- ASIL Rating: QM

#### TFDCX32348-17187: NVM - Software version for APL (System Interface)
- Verification Criteria: Verify by design review
- Verification Method: TBD
- Verification Owner: SW
- System Requirement State: Approved
- Secondary Disciplines: TBD
- Primary Discipline: SW
- ASIL Rating: QM

#### TFDCX32348-17189: NVM_VisteonPartNumber... (System Interface)
NVM_VisteonPartNumber
Description : Represented as " Supplier Serial number" in ETM Plant.
Size : 5 Digits ASCII Value
DID:0xFD01
- Verification Method: TBD
- Verification Owner: SW
- System Requirement State: Approved
- Secondary Disciplines: TBD
- Primary Discipline: SW
- ASIL Rating: QM

#### TFDCX32348-17191: NVM_EcuPartNumber Description... (System Interface)
NVM_EcuPartNumber
Description: Represented as "Serial Number" in ETM Plant.
Size : 20 digits ASCII Value
DID:0xF18C
- Verification Method: TBD
- Verification Owner: SW
- System Requirement State: Approved
- Secondary Disciplines: TBD
- Primary Discipline: SW
- ASIL Rating: QM

#### TFDCX32348-17193: NVM_SoftwarePartNumber... (System Requirement)
NVM_SoftwarePartNumber
Description: Customer part number for the 2nd logical block
Size: 16 digits ASCII Value
Display first 12 bytes of NVM_SoftwarePartNumber in ETM Plant.
DID:0xF188
- Verification Method: TBD
- Verification Owner: SW
- System Requirement State: Approved
- Secondary Disciplines: TBD
- Primary Discipline: SW
- ASIL Rating: QM

#### TFDCX32348-71779: NVM_SoftwarePartNumber_LB2... (System Requirement)
NVM_SoftwarePartNumber_LB2
Description: Customer part number for the 2nd logical block
Size: 16 digits ASCII Value
Display first 12 bytes of NVM_SoftwarePartNumber_LB2 in ETM Plant.
DID:0xF188
- Verification Method: TBD
- Verification Owner: SW
- System Requirement State: Approved
- Secondary Disciplines: TBD
- Primary Discipline: SW
- ASIL Rating: QM

#### TFDCX32348-71780: NVM_SoftwarePartNumber_LB3... (System Requirement)
NVM_SoftwarePartNumber_LB3
Description: Customer part number for the 3rd logical block
Size: 16 digits ASCII Value
Display first 12 bytes of NVM_SoftwarePartNumber_LB3 in ETM Plant.
DID:0xF188
- Verification Method: TBD
- Verification Owner: SW
- System Requirement State: Approved
- Secondary Disciplines: TBD
- Primary Discipline: SW
- ASIL Rating: QM

#### TFDCX32348-71781: NVM_SoftwarePartNumber_LB4... (System Requirement)
NVM_SoftwarePartNumber_LB4
Description: Customer part number for the 4th logical block
Size: 16 digits ASCII Value
Display first 12 bytes of NVM_SoftwarePartNumber_LB4 in ETM Plant.
DID:0xF188
- Verification Method: TBD
- Verification Owner: SW
- System Requirement State: Approved
- Secondary Disciplines: TBD
- Primary Discipline: SW
- ASIL Rating: QM

#### TFDCX32348-71782: NVM_SoftwarePartNumber_LB5... (System Requirement)
NVM_SoftwarePartNumber_LB5
Description: Customer part number for the 5th logical block
Size: 16 digits ASCII Value
Display first 12 bytes of NVM_SoftwarePartNumber_LB5 in ETM Plant.
DID:0xF188
- Verification Method: TBD
- Verification Owner: SW
- System Requirement State: Approved
- Secondary Disciplines: TBD
- Primary Discipline: SW
- ASIL Rating: QM

#### TFDCX32348-71783: NVM_SoftwarePartNumber_LB6... (System Requirement)
NVM_SoftwarePartNumber_LB6
Description: Customer part number for the 6th logical block
Size: 16 digits ASCII Value
Display first 12 bytes of NVM_SoftwarePartNumber_LB6 in ETM Plant.
DID:0xF188
- Verification Method: TBD
- Verification Owner: SW
- System Requirement State: Approved
- Secondary Disciplines: TBD
- Primary Discipline: SW
- ASIL Rating: QM

#### TFDCX32348-93249: NVM_SoftwarePartNumber_LB7... (System Requirement)
NVM_SoftwarePartNumber_LB7
Description: Customer part number for the 7th logical block
Size: 16 digits ASCII Value
Display first 12 bytes of NVM_SoftwarePartNumber_LB7 in ETM Plant.
DID:0xF188
- Verification Method: TBD
- Verification Owner: SW
- System Requirement State: Approved
- Secondary Disciplines: TBD
- Primary Discipline: SW
- ASIL Rating: QM

#### TFDCX32348-17197: NVM - NVM_TFTDutyNightCal Type... (System Interface)
NVM - NVM_TFTDutyNightCal
Type : UINT16 Resolution: 0.01% Range : 0 to 100%
- Verification Method: TBD
- Verification Owner: SW
- System Requirement State: Approved
- Secondary Disciplines: TBD
- Primary Discipline: SW
- ASIL Rating: QM

#### TFDCX32348-17199: NVM - NVM_TFTDutyDayCal Type... (System Interface)
NVM - NVM_TFTDutyDayCal
Type : UINT16 Resolution: 0.01% Range : 0 to 100%
- Verification Method: TBD
- Verification Owner: SW
- System Requirement State: Approved
- Secondary Disciplines: TBD
- Primary Discipline: SW
- ASIL Rating: QM

## TFDCX32348-10597: Output Requirements (Heading)
- System Requirement State: Draft
- Primary Discipline: TBD
- ASIL Rating: TBD

### TFDCX32348-12305: HMI (Heading)
- System Requirement State: Draft
- Primary Discipline: TBD
- ASIL Rating: TBD

#### TFDCX32348-17231: HMI - HMI_IN_APLVer_High (System Interface)
- Verification Criteria: Verify by design review
- Verification Method: TBD
- Verification Owner: SW
- System Requirement State: Approved
- Secondary Disciplines: TBD
- Primary Discipline: SW
- ASIL Rating: QM

#### TFDCX32348-17233: HMI - HMI_IN_APLVer_Middle (System Interface)
- Verification Criteria: Verify by design review
- Verification Method: TBD
- Verification Owner: SW
- System Requirement State: Approved
- Secondary Disciplines: TBD
- Primary Discipline: SW
- ASIL Rating: QM

#### TFDCX32348-17235: HMI - HMI_IN_APLVer_Low (System Interface)
- Verification Criteria: Verify by design review
- Verification Method: TBD
- Verification Owner: SW
- System Requirement State: Approved
- Secondary Disciplines: TBD
- Primary Discipline: SW
- ASIL Rating: QM

#### TFDCX32348-17237: HMI - HMI_IN_BOOTVer_High (System Interface)
- Verification Criteria: Verify by design review
- Verification Method: TBD
- Verification Owner: SW
- System Requirement State: Approved
- Secondary Disciplines: TBD
- Primary Discipline: SW
- ASIL Rating: QM

#### TFDCX32348-17238: HMI - HMI_IN_BOOTVer_Middle (System Interface)
- Verification Criteria: Verify by design review
- Verification Method: TBD
- Verification Owner: SW
- System Requirement State: Approved
- Secondary Disciplines: TBD
- Primary Discipline: SW
- ASIL Rating: QM

#### TFDCX32348-17240: HMI - HMI_IN_BOOTVer_Low (System Interface)
- Verification Criteria: Verify by design review
- Verification Method: TBD
- Verification Owner: SW
- System Requirement State: Approved
- Secondary Disciplines: TBD
- Primary Discipline: SW
- ASIL Rating: QM

#### TFDCX32348-49078: HMI - HMI_IN_GUIVer_High (System Interface)
- Verification Criteria: Verify by design review
- Verification Method: TBD
- Verification Owner: SW
- System Requirement State: Approved
- Secondary Disciplines: TBD
- Primary Discipline: SW
- ASIL Rating: QM

#### TFDCX32348-49079: HMI - HMI_IN_GUIVer_Middle (System Interface)
- Verification Criteria: Verify by design review
- Verification Method: TBD
- Verification Owner: SW
- System Requirement State: Approved
- Secondary Disciplines: TBD
- Primary Discipline: SW
- ASIL Rating: QM

#### TFDCX32348-49080: HMI - HMI_IN_GUIVer_Low (System Interface)
- Verification Criteria: Verify by design review
- Verification Method: TBD
- Verification Owner: SW
- System Requirement State: Approved
- Secondary Disciplines: TBD
- Primary Discipline: SW
- ASIL Rating: QM

## TFDCX32348-10599: Performance Requirements (Heading)
- System Requirement State: Draft
- Primary Discipline: TBD
- ASIL Rating: TBD

### TFDCX32348-12309: APL, GUI and BOOT versions (Heading)
- System Requirement State: Draft
- Primary Discipline: TBD
- ASIL Rating: TBD

#### TFDCX32348-17242: The version of the APL, GUI and... (System Requirement)
The version of the APL, GUI and BOOT shall be handled as follow:
| Parameter | Default value | Set Data | Format |
| --- | --- | --- | --- |
| HMI_IN_APLVer_High | 00 | Software version for VIP (High byte) | BCD → HEX |
| HMI_IN_APLVer_Middle | 00 | Software version for VIP (Middle byte) | BCD → HEX |
| HMI_IN_APLVer_Low | 00 | Software version for VIP (Low byte) | BCD → HEX |
| HMI_IN_BOOTVer_High | 00 | Software version for BOOT (High byte) | BCD → HEX |
| HMI_IN_BOOTVer_Middle | 00 | Software version for BOOT (Middle byte) | BCD → HEX |
| HMI_IN_BOOTVer_Low | 00 | Software version for BOOT (Low byte) | BCD → HEX |
| HMI_IN_GUIVer_High | 00 | Software version for GIP (High byte) | BCD → HEX |
| HMI_IN_GUIVer_Middle | 00 | Software version for GIP (Middle byte) | BCD → HEX |
| HMI_IN_GUIVer_Low | 00 | Software version for GIP (Low byte) | BCD → HEX |
Notes:
1. Software version for APL, GUI and BOOT is stored in NVM using BCD format hence when displaying those value in ETM screen they should be converted to hexadecimal from BCD.
2. When Cluster can’t read SW version or change BCD to HEX correctly, each SW Version symbol (High/Middle/Low) shall be set to initial value (0x00), i.e. 00.00.00” will be displayed. It is applicable for APL, GUI and BOOT SW versions.
- Verification Criteria: Verify by executing test cases
- Verification Method: Software Qualification Test, System Qualification Test, Unit Test
- Verification Owner: SW
- System Requirement State: Approved
- Secondary Disciplines: FV, SW
- Primary Discipline: SW
- ASIL Rating: QM

### TFDCX32348-71809: Other software versions (Heading)
- System Requirement State: Draft
- Primary Discipline: TBD
- ASIL Rating: TBD

#### TFDCX32348-17244: The customer software versions ... (System Requirement)
- The customer software versions shall be read out from following NVM parameters and displayed as shown in TFDCX32348-17350: Please refer...
- NVM_SoftwarePartNumber (*)
- NVM_SoftwarePartNumber_LB2
- NVM_SoftwarePartNumber_LB3
- NVM_SoftwarePartNumber_LB4
- NVM_SoftwarePartNumber_LB5
- NVM_SoftwarePartNumber_LB6
- NVM_SoftwarePartNumber_LB7
(*) This correspond to LB1 Software part number in TFDCX32348-17350: Please refer...
- The Visteon part number and serial number shall be read out from the following NVM parameters and displayed as shown in TFDCX32348-17350: Please refer...
- NVM_EcuPartNumber
- NVM_VisteonPartNumber
Note: all these part numbers are ASCII encoded hence when displayed in ETM screen they shall be converted to characters.
- Verification Criteria: Verify by executing test cases
- Verification Method: Software Qualification Test, System Qualification Test, Unit Test
- Verification Owner: FV, SW
- System Requirement State: Approved
- Secondary Disciplines: FV, SW
- Primary Discipline: SW
- ASIL Rating: QM

### TFDCX32348-71811: TFT parameters (Heading)
- System Requirement State: Draft
- Primary Discipline: TBD
- ASIL Rating: TBD

#### TFDCX32348-17347 (System Requirement)
The TFT parameters used are listed below and shall be displayed as indicated in TFDCX32348-17350: Please refer...
NVM_TFTDutyDayCal : XX% represents current calibration value of NVM T38XD29284-36636: NVM_TFTDutyDayCal with Fixed point resolution of 0.01% .
NVM_TFTDutyNightCal : XX% represents current calibration value of NVM TFDCX32348-12045: NVM_TFTDutyNightCal with Fixed point resolution of 0.01% .
- Verification Criteria: Verify by executing test cases
- Verification Method: Software Qualification Test, System Qualification Test, Unit Test
- Verification Owner: FV, SW
- System Requirement State: Approved
- Secondary Disciplines: FV, SW
- Primary Discipline: SW
- ASIL Rating: QM

### TFDCX32348-12311: SW Versions Display... (Heading)
SW Versions Display
- System Requirement State: Draft
- Primary Discipline: TBD
- ASIL Rating: TBD

#### TFDCX32348-17350: Please refer... (System Requirement)
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Please refer T38XD29284-27938 for checking NVM Values of all NVMs.
- Verification Criteria: Verify by executing test cases
- Verification Method: Functional Verification / Validation
- Verification Owner: FV, SW
- System Requirement State: Draft
- Primary Discipline: SW
- ASIL Rating: QM

# Json2ReqIF Transformation

# Specification: MM_ETC
- JDA Snapshot Date: 2025-09-04 03:03:53

## TFDCX32348-54945: MM_ETC Coordination (Heading)

## TFDCX32348-54946: History (Heading)

### TFDCX32348-54955: Version Date Name Description of chan... (Information)
| Version | Date | Name | Description of change | Baseline |
| --- | --- | --- | --- | --- |
| 0.1 | 6/Nov/2024 | ybai7 | Newly create [SYS-Task] TFDCX32348-34281: [SYS][12.3FDC][APP][MM] [Common] ETC Coordination | BL_20241115_01 |

## TFDCX32348-54947: Reference Document (Heading)

### TFDCX32348-54954: 【別紙】3.3.07.1 ETC情報(車両連携Level2)_METXMM-RSETC-X23-400.doc (Information)
【Attached file】3.3.07.1 ETC information (level 2)_METXMM-RSETC-X23-410_en.doc
【Attached file】3.3.07.2 ETC display screen spec v1.4_en.xls
【Attached file】3.3.07.3 ETC style parts definition v010_en.xls
【Attached file】3.3.07.4 (appendix) MM-SUB-BUS ETC Status notifiction v110_en.xls
【別紙】3.3.07.1 ETC情報(車両連携Level2)_METXMM-RSETC-X23-400.doc
【別紙】3.3.07.2 ETCディスプレイ画面仕様書 v1.3.xls
【別紙】3.3.07.3 ETC意匠部品定義書 v000.xls
【別紙】3.3.07.4 (appendix) MM-SUB-BUS ETCステータス通知 v100.xls

## TFDCX32348-54948: Overview (Heading)

### TFDCX32348-54953: This SRD defines ETC Coordination VMID. (Information)

## TFDCX32348-54949: Input Requirements (Heading)

### TFDCX32348-54959: InternalSignal (Heading)

#### TFDCX32348-54975: InternalSignal - IgnMode (System Interface)
- Verification Criteria: Verify by code review
- Verification Method: Unit Test
- Verification Owner: SW
- System Requirement State: Approved
- Primary Discipline: SW
- ASIL Rating: QM

### TFDCX32348-54963: Msg. Label：AVNMS56 (Heading)

#### TFDCX32348-54974: MMCANSignal – ETC_CARDSTA (System Interface)
- Verification Criteria: Verify by code review
- Verification Method: Unit Test
- Verification Owner: SW
- System Requirement State: Approved
- Primary Discipline: SW
- ASIL Rating: QM

#### TFDCX32348-54979: MMCANSignal – ETC_ERRNUM (System Interface)
- Verification Criteria: Verify by code review
- Verification Method: Unit Test
- Verification Owner: SW
- System Requirement State: Approved
- Primary Discipline: SW
- ASIL Rating: QM

#### TFDCX32348-54986: MMCANSignal – ETC_INTREQ (System Interface)
- Verification Criteria: Verify by code review
- Verification Method: Unit Test
- Verification Owner: SW
- System Requirement State: Approved
- Primary Discipline: SW
- ASIL Rating: QM

### TFDCX32348-54965: HMI parameters (Heading)

#### TFDCX32348-54973: HMI - HMI_InterruptType (System Interface)
- Verification Criteria: Verify by code review
- Verification Method: Unit Test
- Verification Owner: SW
- System Requirement State: Approved
- Primary Discipline: SW
- ASIL Rating: QM

#### TFDCX32348-54982: HMI - HMI_MMInterruptID (System Interface)
- Verification Criteria: Verify by code review
- Verification Method: Unit Test
- Verification Owner: SW
- System Requirement State: Approved
- Primary Discipline: SW
- ASIL Rating: QM

## TFDCX32348-54950: Output Requirements (Heading)

### TFDCX32348-54962: InternalSignal - MMETCInterrupt (System Interface)
InternalSignal - MMETCInterrupt
Range: OFF, ON1, ON2
- Verification Criteria: Verify by code review
- Verification Method: Unit Test
- Verification Owner: SW
- System Requirement State: Approved
- Primary Discipline: SW
- ASIL Rating: QM

### TFDCX32348-54970: HMI- HMI_ETC_ERR_NUM (System Interface)
HMI- HMI_ETC_ERR_NUM
Range: 0 ~ 63 (decimal number)
- Verification Criteria: Verify by code review
- Verification Method: Unit Test
- Verification Owner: SW
- System Requirement State: Approved
- Primary Discipline: SW
- ASIL Rating: QM

### TFDCX32348-54971: HMI - HMI_ETC_DISPLAY_Status (System Interface)
HMI - HMI_ETC_DISPLAY_Status
Range: OFF, NoCard, otherthanNoCard
- Verification Criteria: Verify by code review
- Verification Method: Unit Test
- Verification Owner: SW
- System Requirement State: Approved
- Primary Discipline: SW
- ASIL Rating: QM

## TFDCX32348-54952: Performance Requirements (Heading)

### TFDCX32348-54961: Display Control Requirements (Heading)

#### TFDCX32348-54993: Determining the equipment of ETC [1/2] (System Requirement)
（*）Each time a CAN signal is received, the following process be performed.
| Input |  |  |  |  | Output |  |  |
| --- | --- | --- | --- | --- | --- | --- | --- |
| InternalSignal -IgnMode | Communication Status for NAVI signals(Refer to TFDCX32348-54964) | MMCANSignal - _INTREQ | MMCANSignal - ETC_CARDSTA | MMCANSignal - ETC_ERRNUM | Internal Signal – MMETCInterrupt(*4,*5) | HMI - HMI_ETC_DISPLAY_Status | HMI- HMI_ETC_ERR_NUM |
| (Initialization at CPU reset or wakeup) |  |  |  |  | OFF | OFF | 0x000000b |
| OFF | X | X | X | X | OFF | OFF | 0x000000b |
| ON | Starting | X | X | X | OFF | OFF | 0x000000b |
| ON | Failure | X | X | X | OFF | OFF | 0x000000b |
| ON | Established | 00b | X | X | no change | no change | no change |
| ON | Established | other than 01b->01b | 0b | 000000b～111111b | ON1(*1) | NoCard | same value with ETC_ERRNUM |
| ON | Established | other than 01b->01b | 1b | 000000b～111111b | ON1(*1) | otherthanNoCard | same value with ETC_ERRNUM |
| ON | Established | 01b->01b | 0b | 000000b～111111b | ON(*2) (refer toTFDCX32348-54997) | NoCard | same value with ETC_ERRNUM |
| ON | Established | 01b->01b | 1b | 000000b～111111b | ON(*2) (refer toTFDCX32348-54997) | otherthanNoCard | same value with ETC_ERRNUM |
| ON | Established | 10b | X | X | OFF(*3) | OFF | 0x000000b |
| ON | Established | other than above |  |  | no change | no change | no change |
Note:
*1 The warning display will turn off after 6 seconds when the condition is met( When MMETCInterrupt=ON, 6s counter start. after 6 seconds, MMETCInterrupt=OFF )
*2 If ETC_INTREQ=01b→01b, the display will be displayed again as an interrupt for 6 seconds. (6s counter restart)
*3 If ETC_INTREQ=10b, immediately turn off the warning display(MMETCInterrupt=OFF).
*4 If ETC_INTREQ changes from other than 01b to 01b while a high-priority warning is being displayed,and the high-priority warning goes off within 6 seconds, the interrupt display will be displayed for the remaining time.
*5 If a high-priority warning occurs during an ETC interrupt display within 6 seconds after ETC_INTREQ warning from other than 01b to 01b, and the high-priority warning goes off immediately afterwards, if it is within 6 seconds after ETC_INTREQ changes from other than 01bb to 01b, the warning will be displayed for the remaining time.
- Verification Criteria: Verify by executing test cases
- Verification Method: Software Qualification Test, System Qualification Test, Unit Test
- Verification Owner: FV
- System Requirement State: Approved
- Primary Discipline: SW
- ASIL Rating: QM

#### TFDCX32348-54997: Determining the equipment of ETC [2/2] (System Requirement)
| Input |  | Output |
| --- | --- | --- |
| MMCANSignal - _INTREQ | Internal Signal – MMETCInterrupt(Current) | Internal Signal – MMETCInterrupt |
| 01b->01b | ON 1 | ON 2(*2) |
| 01b->01b | ON2 | ON 1(*2) |
- Verification Criteria: Verify by executing test cases
- Verification Method: Software Qualification Test, System Qualification Test, Unit Test
- Verification Owner: FV
- System Requirement State: Approved
- Primary Discipline: SW
- ASIL Rating: QM

#### TFDCX32348-54994: Sample (Information)
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
### TFDCX32348-54964: Processing for fail (Heading)

#### TFDCX32348-54978: Input Judgement Condition Process Rec... (Information)
| Input | Output |
| --- | --- |
| Communication Status for any of NAVI target Signals(*) (*) Applicable MMCAN signal ETC_CARDSTA(Message Label: AVNMS56) ETC_ERRNUM(Message Label: AVNMS56) ETC_INTREQ(Message Label: AVNMS56) Note: Strictly speaking, MMCAN Frame communication status should be checked. But MM CAN signals in each of the frame share the same timeout time (30s), You can check only the above four signals instead of MMCAN Frame. | Communication Status for NAVI signals |
| MM-CAN Never received status of any signal above is 1 AND MM-CAN Communication failure status of all of the signals listed above is 0 | Starting |
| MM-CAN Communication failure status of any signal above is 1 | Failure |
| MM-CAN Never received status of all signals above is 0 AND MM-CAN Communication failure status of all of the signals listed above is 0 | Established |

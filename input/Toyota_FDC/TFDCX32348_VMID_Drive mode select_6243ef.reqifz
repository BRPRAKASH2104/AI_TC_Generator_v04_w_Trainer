# Json2ReqIF Transformation

# Specification: VMID_Drive mode select
- JDA Snapshot Date: 2025-09-09 09:14:00

## TFDCX32348-57847: VMID_Drive mode select (Heading)

## TFDCX32348-57848: History (Heading)

### TFDCX32348-57854: Table - Version history (Information)
| Version | Date | Name | Description of change | Baseline |
| --- | --- | --- | --- | --- |
| 0.1 | 2/Dec/2024 | Kubo, Masaki | Newly create TFDCX32348-34224 | BL_20241223_01 |
| 0.2 | 13/May/2025 | Kubo, Masaki | Added the judgment of ON/OFF condition for added the warning type6 of screen navigation TFDCX32348-85068 | BL_20250519_01 |
| 0.3 | 12/May/2025 | Kubo, Masaki | Added the snow extra mode TFDCX32348-78920 | BL_20250627_01 |
| 0.4 | 11/July/2025 | Kubo, Masaki | Update the Drive mode condition B TFDCX32348-97202 | BL_20250714_01 |

## TFDCX32348-57849: Reference Document (Heading)

### TFDCX32348-57855: MET-C_DRIMOD-CSTD... (Information)
MET-C_DRIMOD-CSTD-A0-10-A-C0.xlsm
DMS_MET-C_DRIMOD-CSTD-A0-10-A-C0.xlsx

## TFDCX32348-57850: Overview (Heading)

### TFDCX32348-57856: This SRD defines Drive mode select for VMID. (Information)

## TFDCX32348-57851: Input Requirements (Heading)

### TFDCX32348-57857: InternalSignal – IgnMode (System Interface)
- Verification Criteria: Verify by design review
- Verification Method: Code/Design Review
- Verification Owner: SW
- System Requirement State: Approved
- Primary Discipline: SW
- ASIL Rating: QM

### TFDCX32348-57861: CANSignal - B_DMODE (Message Label: ENG1G90) (System Interface)
- Verification Criteria: Verify by design review
- Verification Method: Code/Design Review
- Verification Owner: SW
- System Requirement State: Approved
- Primary Discipline: SW
- ASIL Rating: QM

### TFDCX32348-57863: CANSignal - FSITRG (Message Label: ENG1G90) (System Interface)
- Verification Criteria: Verify by design review
- Verification Method: Code/Design Review
- Verification Owner: SW
- System Requirement State: Approved
- Primary Discipline: SW
- ASIL Rating: QM

### TFDCX32348-57866: CANSignal - FSIKIND (Message Label: ENG1G90) (System Interface)
- Verification Criteria: Verify by design review
- Verification Method: Code/Design Review
- Verification Owner: SW
- System Requirement State: Approved
- Primary Discipline: SW
- ASIL Rating: QM

### TFDCX32348-57867: CANSignal - FSILSTTP (Message Label: ENG1G90) (System Interface)
- Verification Criteria: Verify by design review
- Verification Method: Code/Design Review
- Verification Owner: SW
- System Requirement State: Approved
- Primary Discipline: SW
- ASIL Rating: QM

### TFDCX32348-57956: CANSignal - B_DMINF3 (Message Label: ENG1S60) (System Interface)
- Verification Criteria: Verify by design review
- Verification Method: Code/Design Review
- Verification Owner: SW
- System Requirement State: Approved
- Primary Discipline: SW
- ASIL Rating: QM

### TFDCX32348-57957: MCUCONST - MCUID0025 (System Interface)
- Verification Criteria: Verify by design review
- Verification Method: Code/Design Review
- Verification Owner: SW
- System Requirement State: Approved
- Primary Discipline: SW
- ASIL Rating: QM

## TFDCX32348-57852: Output Requirements (Heading)

### TFDCX32348-57858: HMI - HMI_DRIVE MODE_DISPLAY_TYPE (System Interface)
HMI - HMI_DRIVE MODE_DISPLAY_TYPE
Meaning: This parameter indicates the drive mode select display type.
Range: 0(OFF), 1(MODE_DIAL), 2(MODE_TOGGLE), 3(MODE_PUSH)
- Verification Criteria: Verify by design review
- Verification Method: Code/Design Review
- Verification Owner: SW
- System Requirement State: Approved
- Primary Discipline: SW
- ASIL Rating: QM

### TFDCX32348-57860: HMI - HMI_DRIVE MODE_LIST[] (System Interface)
HMI - HMI_DRIVE MODE_LIST[]
Meaning: This parameter indicates the drive mode available item in array.
Range: 0(NORMAL), 1(SPORT), 2(ECO), 3(CUSTOM), 4(RANGE), 5(REAR COMFORT), 6(SNOW), 7(TRACK)), 8(SNOW_EXTRA)
- Verification Criteria: Verify by design review
- Verification Method: Code/Design Review
- Verification Owner: SW
- System Requirement State: Approved
- Primary Discipline: SW
- ASIL Rating: QM

### TFDCX32348-57959: HMI - HMI_DRIVE_MODE_LIST_COUNT (System Interface)
HMI - HMI_DRIVE_MODE_LIST_COUNT
Meaning: This parameter indicates the number of items in HMI_DRIVE_MODE_LIST[] array.
Range: 0 - 8
- Verification Criteria: Verify by design review
- Verification Method: Code/Design Review
- Verification Owner: SW
- System Requirement State: Approved
- Primary Discipline: SW
- ASIL Rating: QM

### TFDCX32348-57864: HMI - HMI_DRIVE MODE_SELECT (System Interface)
HMI - HMI_DRIVE MODE_SELECT
Meaning: This parameter indicates the drive mode selected item.
Range: 0(OFF), 1(NORMAL), 2(SPORT), 3(ECO), 4(CUSTOM), 5(RANGE), 6(REAR COMFORT), 7(SNOW), 8(TRACK), 9(SNOW_EXTRA)
- Verification Criteria: Verify by design review
- Verification Method: Code/Design Review
- Verification Owner: SW
- System Requirement State: Approved
- Primary Discipline: SW
- ASIL Rating: QM

### TFDCX32348-58015: InternalSignal - DM_Condition A (System Interface)
InternalSignal - DM_Condition A
Meaning: This parameter indicates the drive mode condition A.
Range: 0(OFF), 1(ON_A1), 2(ON_A2), 3(ON_A3)
- Verification Criteria: Verify by design review
- Verification Method: Code/Design Review
- Verification Owner: SW
- System Requirement State: Approved
- Primary Discipline: SW
- ASIL Rating: QM

### TFDCX32348-58018: InternalSignal - DM_Condition D (System Interface)
InternalSignal - DM_Condition D
Meaning: This parameter indicates the drive mode condition D.
Range: 0(OFF), 1(ON)
- Verification Criteria: Verify by design review
- Verification Method: Code/Design Review
- Verification Owner: SW
- System Requirement State: Approved
- Primary Discipline: SW
- ASIL Rating: QM

### TFDCX32348-60627: warningID - WRN_NORM_DRIMOD_03 (System Interface)
warningID - WRN_NORM_DRIMOD_03
Range: (OFF, ON)
- Verification Criteria: Verify by design review
- Verification Method: Code/Design Review
- Verification Owner: SW
- System Requirement State: Approved
- Primary Discipline: SW
- ASIL Rating: QM

### TFDCX32348-60628: warningID - WRN_NORM_DRIMOD_04 (System Interface)
warningID - WRN_NORM_DRIMOD_04
Range: (OFF, ON)
- Verification Criteria: Verify by design review
- Verification Method: Code/Design Review
- Verification Owner: SW
- System Requirement State: Approved
- Primary Discipline: SW
- ASIL Rating: QM

### TFDCX32348-60629: warningID - WRN_NORM_DRIMOD_05 (System Interface)
warningID - WRN_NORM_DRIMOD_05
Range: (OFF, ON)
- Verification Criteria: Verify by design review
- Verification Method: Code/Design Review
- Verification Owner: SW
- System Requirement State: Approved
- Primary Discipline: SW
- ASIL Rating: QM

## TFDCX32348-57853: Performance Requirements (Heading)

### TFDCX32348-57859: Screen Configuration (Heading)

#### TFDCX32348-57868: Information (Information)
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
### TFDCX32348-57862: Display Control (Heading)

#### TFDCX32348-57869: Control of display the driver mode condition (Heading)

##### TFDCX32348-57874: Table - Condition A (System Requirement)
| # | Input |  | Output |
| --- | --- | --- | --- |
| # | CAN Signal Communication Status – FSILSTTP | CAN Signal Value–FSILSTTP | InternalSignal - DM_Condition A |
| 1 | Initial |  | OFF |
| 2 | Communication starting Never Received: 1 Communication Failure: 0 | X | OFF |
| 3 | Communication starting Never Received: X Communication Failure: 1 | X | No change |
| 4 | Communication starting Never Received: 0 Communication Failure: 0 | 01b | ON_A1 |
| 5 | Communication starting Never Received: 0 Communication Failure: 0 | 10b | ON_A2 |
| 6 | Communication starting Never Received: 0 Communication Failure: 0 | 00b | ON_A3 |
| 7 | Communication starting Never Received: 0 Communication Failure: 0 | Other than above | OFF |
- Verification Criteria: Verify by design review Verify all of conditions in the table (need fault injection)
- Verification Method: Code/Design Review, System Qualification Test, Unit Test
- Verification Owner: FV, SW
- System Requirement State: Approved
- Primary Discipline: SW
- ASIL Rating: QM

##### TFDCX32348-57968: Table - Condition B (System Requirement)
| # | Input |  | Output |
| --- | --- | --- | --- |
| # | CAN Signal Communication Status – B_DMODE | CAN Signal Value–B_DMODE | InternalSignal - DM_Condition B |
| 1 | Initial |  | OFF |
| 2 | Communication starting Never Received: 1 Communication Failure: 0 | X | OFF |
| 3 | Communication starting Never Received: X Communication Failure: 1 | X | ON |
| 4 | Communication starting Never Received: 0 Communication Failure: 0 | 0000b or 0010b or 0110b or 0111b or 1001b or 1011b or 1100b or 1010b or 1101b | ON |
| 5 | Communication starting Never Received: 0 Communication Failure: 0 | Other than above | OFF |
- Verification Criteria: Verify by design review Verify all of conditions in the table (need fault injection)
- Verification Method: Code/Design Review, System Qualification Test, Unit Test
- Verification Owner: FV, SW
- System Requirement State: Approved
- Primary Discipline: SW
- ASIL Rating: QM

##### TFDCX32348-57969: Table - Condition C (System Requirement)
| # | Input |  | Output |
| --- | --- | --- | --- |
| # | CAN Signal Communication Status – FSIKIND | CAN Signal Value–FSIKIND | InternalSignal - DM_Condition C |
| 1 | Initial |  | OFF |
| 2 | Communication starting Never Received: 1 Communication Failure: 0 | X | OFF |
| 3 | Communication starting Never Received: X Communication Failure: 1 | X | No change |
| 4 | Communication starting Never Received: 0 Communication Failure: 0 | 00b | ON |
| 5 | Communication starting Never Received: 0 Communication Failure: 0 | Other than above | OFF |
- Verification Criteria: Verify by design review Verify all of conditions in the table (need fault injection)
- Verification Method: Code/Design Review, System Qualification Test, Unit Test
- Verification Owner: FV, SW
- System Requirement State: Approved
- Primary Discipline: SW
- ASIL Rating: QM

##### TFDCX32348-57970: Table - Condition D (System Requirement)
| # | Input |  |  | Output |
| --- | --- | --- | --- | --- |
| # | InternalSignal-IgnMode | CAN Signal Communication Status – FSITRG | CAN Signal Value–FSITRG (*1) | InternalSignal - DM_Condition D |
| 1 | Initial |  |  | OFF |
| 2 | OFF | X | X | OFF |
| 3 | ON | Communication starting Never Received: 1 Communication Failure: 0 | X | No change |
| 4 | ON | Communication starting Never Received: X Communication Failure: 1 | X | No change |
| 5 | ON | Communication starting Never Received: 0 Communication Failure: 0 | 0b to 1b change 0b to 1b & received the 0b or 1b more than twice. | ON |
| 6 | ON | Communication starting Never Received: 0 Communication Failure: 0 | 1b to 0b change 1b to 0b & received the 0b or 1b more than twice. | ON |
| 7 | ON | Communication starting Never Received: 0 Communication Failure: 0 | Other than above | No change OFF |
*1: The first FSITRG after IGR (IG2) is turned ON should be discarded.
- Verification Criteria: Verify by design review Verify all of conditions in the table (need fault injection)
- Verification Method: Code/Design Review, System Qualification Test, Unit Test
- Verification Owner: FV, SW
- System Requirement State: Approved
- Primary Discipline: SW
- ASIL Rating: QM

##### TFDCX32348-57971: Table - Judgment the display type (System Requirement)
| # | Input |  |  |  |  | Output |  |  |  |
| --- | --- | --- | --- | --- | --- | --- | --- | --- | --- |
| # | MCUCONST - MCUID0025 | InternalSignal - DM_Condition A | InternalSignal - DM_Condition B | InternalSignal - DM_Condition C | InternalSignal - DM_Condition D | HMI_DRIVE MODE_DISPLAY_TYPE | WRN_NORM_DRIMOD_03 | WRN_NORM_DRIMOD_04 | WRN_NORM_DRIMOD_05 |
| 1 | Other than "2:GR or 3:GRMN" | ON_A1 | ON | ON | ON | MODE_DIAL | ON1 or ON2 (*1) | OFF | OFF |
| 2 | Other than "2:GR or 3:GRMN" | ON_A2 | ON | ON | ON | MODE_TOGGLE | OFF | ON1 or ON2 (*1) | OFF |
| 3 | Other than "2:GR or 3:GRMN" | ON_A3 | ON | ON | ON | MODE_PUSH | OFF | OFF | ON1 or ON2 (*1) |
| 4 | Other than "2:GR or 3:GRMN" | Other than above |  |  |  | OFF | OFF | OFF | OFF |
| 5 | Other than above |  |  |  |  | OFF | OFF | OFF | OFF |
*1: After 6 seconds have passed since the warning display, it will be set the ON to OFF.
*1: Output parameter should switch between output values ​​ON1 and ON2 alternating. First output is ON1, and once CAN signal received will be set the ON2 -> ON1 alternating.
- Verification Criteria: Verify by design review Verify all of conditions in the table (need fault injection)
- Verification Method: Code/Design Review, System Qualification Test, Unit Test
- Verification Owner: FV, SW
- System Requirement State: Approved
- Primary Discipline: SW
- ASIL Rating: QM

#### TFDCX32348-57872: Control of Title and Mode list (Heading)

##### TFDCX32348-57877: Table (System Requirement)
| # | Input |  |  | Output |  |  |  |  |  |  |  |  |
| --- | --- | --- | --- | --- | --- | --- | --- | --- | --- | --- | --- | --- |
| # | InternalSignal-IgnMode | CAN Signal Communication Status – B_DMINF3 | CAN Signal Value–B_DMINF3 | HMI_DRIVE MODE_LIST[], HMI_DRIVE_MODE_LIST_COUNT (*1) |  |  |  |  |  |  |  |  |
| # | InternalSignal-IgnMode | CAN Signal Communication Status – B_DMINF3 | CAN Signal Value–B_DMINF3 | NORMAL | SPORT | ECO | CUSTOM | RANGE | REAR COMFORT | SNOW | TRACK | SNOW_EXTRA |
| 1 | OFF | X | X | OFF | OFF | OFF | OFF | OFF | OFF | OFF | OFF | OFF |
| 2 | ON | Communication starting Never Received: 1 Communication Failure: 0 | X | OFF | OFF | OFF | OFF | OFF | OFF | OFF | OFF | OFF |
| 3 | ON | Communication starting Never Received: X Communication Failure: 1 | X | No change | No change | No change | No change | No change | No change | No change | No change | No change |
| 4 | ON | Communication starting Never Received: 0 Communication Failure: 0 | ***************1b | ON | No change | No change | No change | No change | No change | No change | No change | No change |
| 5 | ON | Communication starting Never Received: 0 Communication Failure: 0 | **************1*b | No change | ON | No change | No change | No change | No change | No change | No change | No change |
| 6 | ON | Communication starting Never Received: 0 Communication Failure: 0 | *************1**b | No change | No change | ON | No change | No change | No change | No change | No change | No change |
| 7 | ON | Communication starting Never Received: 0 Communication Failure: 0 | ************1***b | No change | No change | No change | ON | No change | No change | No change | No change | No change |
| 8 | ON | Communication starting Never Received: 0 Communication Failure: 0 | ***********1****b | No change | No change | No change | No change | ON | No change | No change | No change | No change |
| 9 | ON | Communication starting Never Received: 0 Communication Failure: 0 | **********1*****b | No change | No change | No change | No change | No change | ON | No change | No change | No change |
| 10 | ON | Communication starting Never Received: 0 Communication Failure: 0 | *********1******b | No change | No change | No change | No change | No change | No change | ON | No change | No change |
| 11 | ON | Communication starting Never Received: 0 Communication Failure: 0 | ********1*******b | No change | No change | No change | No change | No change | No change | No change | ON | No change |
| 12 | ON | Communication starting Never Received: 0 Communication Failure: 0 | *******1********b | No change | No change | No change | No change | No change | No change | No change | No change | ON |
| 13 | ON | Communication starting Never Received: 0 Communication Failure: 0 | Other than above | No change | No change | No change | No change | No change | No change | No change | No change | No change |
*1: if each drive mode is ON, add the available mode to HMI_DRIVE MODE_LIST[] array. The number of available modes is added to HMI_DRIVE_MODE_LIST_COUNT.
Case1
B_DMINF3 = 0000 0000 0001 0101b
(NORMAL=ON, SPORT=OFF, ECO=ON, CUSTOM=OFF, RANGE=ON, REAR COMFORT=OFF, SNOW=OFF, TRACK=OFF)
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HMI_DRIVE_MODE_LIST_COUNT=3
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- Verification Criteria: Verify by design review Verify all of conditions in the table (need fault injection)
- Verification Method: Code/Design Review, System Qualification Test, Unit Test
- Verification Owner: FV, SW
- System Requirement State: Approved
- Primary Discipline: SW
- ASIL Rating: QM

#### TFDCX32348-57873: Control of Mode select (Heading)

##### TFDCX32348-57878: Table (System Requirement)
| # | Input |  |  | Output |
| --- | --- | --- | --- | --- |
| # | InternalSignal-IgnMode | CAN Signal Communication Status – B_DMODE | CAN Signal Value–B_DMODE | HMI_DRIVE MODE_SELECT |
| 1 | OFF | X | X | OFF |
| 2 | ON | Communication starting Never Received: 1 Communication Failure: 0 | X | OFF |
| 3 | ON | Communication starting Never Received: X Communication Failure: 1 | X | NORMAL |
| 4 | ON | Communication starting Never Received: 0 Communication Failure: 0 | 0000b | NORMAL |
| 5 | ON | Communication starting Never Received: 0 Communication Failure: 0 | 0010b | SPORT |
| 6 | ON | Communication starting Never Received: 0 Communication Failure: 0 | 0110b | ECO |
| 7 | ON | Communication starting Never Received: 0 Communication Failure: 0 | 0111b | CUSTOM |
| 8 | ON | Communication starting Never Received: 0 Communication Failure: 0 | 1001b | RANGE |
| 9 | ON | Communication starting Never Received: 0 Communication Failure: 0 | 1011b | REAR COMFORT |
| 10 | ON | Communication starting Never Received: 0 Communication Failure: 0 | 1100b | SNOW |
| 11 | ON | Communication starting Never Received: 0 Communication Failure: 0 | 1010b | TRACK |
| 12 | ON | Communication starting Never Received: 0 Communication Failure: 0 | 1101b | SNOW_EXTRA |
| 13 | ON | Communication starting Never Received: 0 Communication Failure: 0 | Other than above | OFF |
- Verification Criteria: Verify by design review Verify all of conditions in the table (need fault injection)
- Verification Method: Code/Design Review, System Qualification Test, Unit Test
- Verification Owner: FV, SW
- System Requirement State: Approved
- Primary Discipline: SW
- ASIL Rating: QM

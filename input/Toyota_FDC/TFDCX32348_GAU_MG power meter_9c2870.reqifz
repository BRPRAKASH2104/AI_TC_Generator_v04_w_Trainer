# Json2ReqIF Transformation

# Specification: GAU_MG power meter
- JDA Snapshot Date: 2025-09-04 02:41:43

## TFDCX32348-76048: GAU_MG power meter (Heading)

## TFDCX32348-76049: History (Heading)

### TFDCX32348-76050: Table (Information)
| Version | Date | Name | Description of change | Baseline |
| --- | --- | --- | --- | --- |
| 0.1 | Mar/18/2025 | Hiromune Wachi | Newly create for 12.3inch FDC. [SYS-Story] : TFDCX32348-64398: [SYS][12.3FDC][R4][APP][Gauges] MG power meter | BL_20250401_01 |
| 0.2 | Jul/7/2025 | Hiromune Wachi | Deleted “[B] Function presence/absence judgment” process block. [SYS-Story] : TFDCX32348-96644: [SYS][12.3FDC][R4][IMP][APP][Gauges] MG power meter (changed by TFDCX32348-90688) | BL_20250710_01 |

## TFDCX32348-76055: Overview (Heading)

### TFDCX32348-76056: This SRD defines the requirements for MG power meter. (Information)

## TFDCX32348-76057: Reference Document (Heading)

### TFDCX32348-76058: External Sources (Heading)

#### TFDCX32348-76059: MET-P_MGPWR-CSTD-2-00-A-C1 (Information)

## TFDCX32348-76060: Input Requirements (Heading)

### TFDCX32348-76546: InternalSignal - IgnMode (System Interface)
- System Requirement State: Approved

### TFDCX32348-76547: CANSignal - MGPWRMET (System Interface)
- System Requirement State: Approved

### TFDCX32348-76558: MCUCONST - MCUID1119 (System Interface)
- System Requirement State: Approved

### TFDCX32348-76559: MCUCONST - MCUID1121 (System Interface)
- System Requirement State: Approved

## TFDCX32348-76061: Output Requirements (Heading)

### TFDCX32348-76560: HMI - HMI_MGPWR_ASSIST_GAUGE (System Interface)
HMI - HMI_MGPWR_ASSIST_GAUGE
Range : 0[0%], 1[1%], ..., 100[100%]
- System Requirement State: Approved

### TFDCX32348-76561: HMI - HMI_MGPWR_LOGO_MARK (System Interface)
HMI - HMI_MGPWR_LOGO_MARK
Range : 0[No display MG gauge logo mark], 1[Display MG gauge logo mark]
- System Requirement State: Approved

### TFDCX32348-76752: InternalSignal - MGPowerGauge_Prsnt (System Interface)
InternalSignal - MGPowerGauge_Prsnt
Range : 0[NOT_PRSNT], 1[PRSNT]
- System Requirement State: Approved

## TFDCX32348-76062: Performance Requirements (Heading)

### TFDCX32348-76562: General (Heading)

#### TFDCX32348-76710: Processing block structure (Heading)

##### TFDCX32348-76711: Figure (System Requirement)
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- Verification Criteria: Verify by design review
- Verification Method: Code/Design Review
- Verification Owner: SW
- System Requirement State: Approved
- Primary Discipline: SW
- ASIL Rating: QM

##### TFDCX32348-76716: Table (System Requirement)
| # | Signal name | Range |
| --- | --- | --- |
| ①-1 | MGPWRMET_in | 80h[-128%], 81h[-127%], …, FFh[-1%], 00h[0%], 01h[1%], … 7Eh[126%], 7Fh[127%] |
| ②-2 | MGPWRMET_Status_Flag | 0[Never Received], 1[Communication Failure], 2[Normal] |
| ② | AverageMGAssistValue | 80h[-128%], 81h[-127%], …, FFh[-1%], 00h[0%], 01h[1%], … 7Eh[126%], 7Fh[127%] |
- Verification Criteria: Verify by design review
- Verification Method: Code/Design Review
- Verification Owner: SW
- System Requirement State: Approved
- Primary Discipline: SW
- ASIL Rating: QM

### TFDCX32348-76563: Process (Heading)

#### TFDCX32348-76745: [A] Initialization (Heading)

##### TFDCX32348-76746: Table - Initialization (System Requirement)
| # | Name | Initilize @ Battery Connect / Cold Reset | Initialize @ Module Wake-Up | IgnMode change from ON to OFF | Init Value | Remark |
| --- | --- | --- | --- | --- | --- | --- |
| 1 | HMI - HMI_MGPWR_ASSIST_GAUGE | 〇 | 〇 | 〇 | 0[0%] | Output signal of this module |
| 2 | HMI - HMI_MGPWR_LOGO_MARK | 〇 | 〇 | X | [*1] | Output signal of this module |
| 3 | InternalSignal - MGPowerGauge_Prsnt | 〇 | 〇 | X | [*2] | Output signal of this module |
| 4 | MGPWRMET_in | 〇 | 〇 | 〇 | 00h[0%] | Output of [C] block |
| 5 | SampleBuffer[8] | 〇 | 〇 | 〇 | Clear all data (Set 00h[0%] to all data) | Variable of [D] block (Range of each data : 80h[-128%], 81h[-127%], …, FFh[-1%], 00h[0%], 01h[1%], … 7Eh[126%], 7Fh[127%]) |
| 6 | BufferIndex | 〇 | 〇 | 〇 | 0 | Variable of [D] block (Range : 0, 1, …, 7) |
| 7 | BufferStatusFlag | 〇 | 〇 | 〇 | -1[No data] | Variable of [D] block (Range : -1[No data], 0[Not full], 1[Full]) |
| 8 | AverageMGAssistValue | 〇 | 〇 | 〇 | 00h[0%] | Output of [D] block |
[*1] : Follow the table below.
| # | Input | Output |
| --- | --- | --- |
| # | MCUCONST - MCUID1121 | HMI - HMI_MGPWR_LOGO_MARK |
| 1 | 2[MG gauge logo present] | 1[Display MG gauge logo mark] |
| 2 | 3[boost gauge/MG gauge logo present] | 1[Display MG gauge logo mark] |
| 3 | Other than above | 0[No display MG gauge logo mark] |
[*2] : Follow the table below.
| # | Input | Output |
| --- | --- | --- |
| # | MCUID1119 | InternalSignal - MGPowerGauge_Prsnt |
| 1 | 1[MG gauge function present] | 1[PRSNT] |
| 2 | Other than above | 0[NOT_PRSNT] |
- Verification Criteria: Verify by executing test cases
- Verification Method: System Qualification Test, Unit Test
- Verification Owner: FV, SW
- System Requirement State: Approved
- Primary Discipline: SW
- ASIL Rating: QM

#### TFDCX32348-76753: [B] Function presence/absence judgment (Heading)
- System Requirement State: Rejected

##### TFDCX32348-76754: Table - MGPowerGauge_Prsnt (System Requirement)
Table - MGPowerGauge_Prsnt
| # | Input |  | Output |
| --- | --- | --- | --- |
| # | IgnMode | MCUID1119 | InternalSignal - MGPowerGauge_Prsnt |
| 1 | OFF → ON | 1[MG gauge function present] | 1[PRSNT] |
| 2 | OFF → ON | Other than above | 0[NOT_PRSNT] |
| 3 | Other than above |  | No change |
- System Requirement State: Rejected

##### TFDCX32348-76762: Table - HMI_MGPWR_LOGO_MARK (System Requirement)
Table - HMI_MGPWR_LOGO_MARK
| # | Input |  | Output |
| --- | --- | --- | --- |
| # | IgnMode | MCUID1121 | HMI - HMI_MGPWR_LOGO_MARK |
| 1 | OFF → ON | 2[MG gauge logo present] | 1[Display MG gauge logo mark] |
| 2 | OFF → ON | 3[boost gauge/MG gauge logo present] | 1[Display MG gauge logo mark] |
| 3 | OFF → ON | Other than above | 0[No display MG gauge logo mark] |
| 4 | Other than above |  | No change |
- System Requirement State: Rejected

#### TFDCX32348-76763: Main operation (Heading)

##### TFDCX32348-76764 (System Requirement)
Each block of the main operation shall be executed when all of the following conditions are met.
- MGPowerGauge_Prsnt == 1[PRSNT]
- IgnMode == ON
- Verification Criteria: Verify by executing test cases
- Verification Method: System Qualification Test, Unit Test
- Verification Owner: FV, SW
- System Requirement State: Approved
- Primary Discipline: SW
- ASIL Rating: QM

##### TFDCX32348-76765: [B] Sampling process (Heading)

###### TFDCX32348-76766: Table - Sampling process (System Requirement)
| # | Input | Output |  |
| --- | --- | --- | --- |
| # | CAN Signal Communication Status - MGPWRMET | MGPWRMET_In | MGPWRMET_Status_Flag |
| 1 | Never received (Never Received: 1 Communication Failure: 0) | 00h[0%] | 0[Never Received] |
| 2 | Communication failure (Never Received: x Communication Failure: 1) | 00h[0%] | 1[Communication Failure] |
| 3 | Normal (Never Received: 0 Communication Failure: 0) | CANSignal - MGPWRMET | 2[Normal] |
- Verification Criteria: Verify by executing test cases
- Verification Method: System Qualification Test, Unit Test
- Verification Owner: FV, SW
- System Requirement State: Approved
- Primary Discipline: SW
- ASIL Rating: QM

##### TFDCX32348-76767: [C] Averaging process (Heading)

###### TFDCX32348-76768: Table - Averaging process (System Requirement)
| # | Input |  |  | Output |  |  |
| --- | --- | --- | --- | --- | --- | --- |
| # | MGPWRMET_Status_Flag | BufferIndex | BufferStatusFlag | SampleBuffer[] | BufferIndex [*1] | BufferStatusFlag |
| 1 | 0[Never Received] | X | X | Clear all data (Set -1[No data] to all data) | 0 | -1[No data] |
| 2 | Other than 0[Never Received] | BufferIndex >= 7 | X | Store MGPWRMET_In value in SampleBuffer[7] | 0 | 1[Full] |
| 3 | Other than 0[Never Received] | BufferIndex < 7 | 1[Full] | Store MGPWRMET_In value in SampleBuffer[BufferIndex] | Increment by 1 | No change |
| 4 | Other than 0[Never Received] | BufferIndex < 7 | Other than 1[Full] | Store MGPWRMET_In value in SampleBuffer[BufferIndex] | Increment by 1 | 0[Not full] |
[*1] : Update BufferIndex after updating SampleBuffer.
- Verification Criteria: Verify by executing test cases
- Verification Method: System Qualification Test, Unit Test
- Verification Owner: FV, SW
- System Requirement State: Approved
- Primary Discipline: SW
- ASIL Rating: QM

###### TFDCX32348-76769: Calculation of average data (System Requirement)
Cluster shall calculate the averaged data according to the following calculation:
Case of “BufferStatusFlag == -1[No data]“
AverageMGAssistValue = 00h[0%]
Case of “BufferStatusFlag == 0[Not full]“
AverageMGAssistValue = Round{(“Sum of SampleBuffer[0] to SampleBuffer[BufferIndex - 1]” / BufferIndex), 0}
Case of “BufferStatusFlag == 1[Full]“
AverageMGAssistValue = Round{(“Sum of SampleBuffer[0] to SampleBuffer[7]” / 8), 0}
- Verification Criteria: Verify by executing test cases
- Verification Method: System Qualification Test, Unit Test
- Verification Owner: FV, SW
- System Requirement State: Approved
- Primary Discipline: SW
- ASIL Rating: QM

##### TFDCX32348-76770: [D] Update display data (Heading)

###### TFDCX32348-76771: Table - HMI_MGPWR_ASSIST_GAUGE (System Requirement)
| # | Input | Output |
| --- | --- | --- |
| # | AverageMGAssistValue | HMI_MGPWR_ASSIST_GAUGE |
| 1 | 80h[-128%] to FFh[-1%] | 0[0%] |
| 2 | 65h[101%] to 7Fh[127%] | 0[0%] |
| 3 | 00h[0%] to 64h[100%] | The value of AverageMGAssistValue |
- Verification Criteria: Verify by executing test cases
- Verification Method: System Qualification Test, Unit Test
- Verification Owner: FV, SW
- System Requirement State: Approved
- Primary Discipline: SW
- ASIL Rating: QM

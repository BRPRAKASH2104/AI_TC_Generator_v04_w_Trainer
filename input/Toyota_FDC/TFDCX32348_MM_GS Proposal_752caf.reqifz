# Json2ReqIF Transformation

# Specification: MM_GS Proposal
- JDA Snapshot Date: 2025-09-04 03:03:59

## TFDCX32348-10639: MM_GS Proposal (Heading)

## TFDCX32348-10640: History (Heading)

### TFDCX32348-10642: Table (Information)
| Version | Date | Name | Description of change | SRD Baseline |
| --- | --- | --- | --- | --- |
| 0.1 | Oct/30/2024 | Hiromune Wachi | Newly create for 12.3inch FDC (Carry over from 38xD with no changes). [SYS-Story] : TFDCX32348-34278: [SYS][12.3FDC][APP][MM] [Common] GS (gas station) proposal | BL_20241112_02 |

## TFDCX32348-10644: References (Heading)

### TFDCX32348-14720: External Sources (Heading)

#### TFDCX32348-18500 (Information)
【Attached file】3.4.1 GS (gas station) proposal (level 1,2) METXMM-RSGS-X123-340_en.doc
(【別紙】3.4.1 GS(ガソリンスタンド)検索提案(車両連携Level1,2)_METXMM-RSGS-X123-340.doc)

## TFDCX32348-10646: Overview (Heading)

### TFDCX32348-14722: This SRD defines the GS Proposal coor... (Information)
This SRD defines the GS Proposal coordination function.

## TFDCX32348-10648: Input Requirements (Heading)

### TFDCX32348-14724: InternalSignal – IgnMode (System Interface)
- System Requirement State: Approved

### TFDCX32348-14726: InternalSignal – ACCStatus (System Interface)
- System Requirement State: Approved

### TFDCX32348-14728: InternalSignal – Fuel_Enpty_Warn (System Interface)
- System Requirement State: Approved

### TFDCX32348-14730: InternalSignal – Refuel_Judge (System Interface)
- System Requirement State: Approved

## TFDCX32348-10650: Output Requirements (Heading)

### TFDCX32348-14732: CANSignal – RQ_GSSRC (Message Label: ... (System Interface)
CANSignal – RQ_GSSRC (Message Label: MET1S19)
- System Requirement State: Approved

## TFDCX32348-10652: Performance Requirements (Heading)

### TFDCX32348-14734: Function Structure (Heading)

#### TFDCX32348-18502: Function structure is below. (Information)
Function structure is below.
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
### TFDCX32348-14736: Control Logic (Heading)

#### TFDCX32348-18504: Refueled_flag Logic (Heading)

##### TFDCX32348-20725: Refer to TFDCX32348-5490 (System Requirement)
Refer to TFDCX32348-5490
T38XD29284-45268: Refueled_flag logic
- Verification Criteria: Verify by code review Verify by executing under all conditions
- Verification Method: Code/Design Review, System Qualification Test, Unit Test
- Verification Owner: FV, SW
- System Requirement State: Approved
- Primary Discipline: SW
- ASIL Rating: QM

#### TFDCX32348-18505: Table - Request GS search logic (Heading)

##### TFDCX32348-20727: Refer to TFDCX32348-5492 (System Requirement)
Refer to TFDCX32348-5492
T38XD29284-45270: Table - Request GS search logic
- Verification Criteria: Verify by code review Verify by executing under all conditions
- Verification Method: Code/Design Review, System Qualification Test, Unit Test
- Verification Owner: FV, SW
- System Requirement State: Approved
- Primary Discipline: SW
- ASIL Rating: QM
